/*
 * Copyright (c) 2026 Juniper Networks, Inc.
 * All rights reserved.
 */
 module junos-rpc-interfaces {
   namespace "http://yang.juniper.net/junos/rpc/interfaces";

   prefix interfaces;

   import junos-common-ddl-extensions {
     prefix junos;
     revision-date 2026-01-01;
   }

   import junos-common-types {
     prefix jt;
     revision-date 2026-01-01;
   }

   organization "Juniper Networks, Inc.";

   contact "yang-support@juniper.net";

   description "Junos RPC YANG module for interfaces command(s)";

   revision 2026-01-01 {
     description "Junos: 26.2R1.7";
   }

   rpc get-interface-information {
     description "Show interface information";
     junos:command "show interfaces";
     input {
       uses command-forwarding;
       leaf routing-instance {
         description "Name of routing instance";
         type string;
       }
       leaf satellite-device {
         description "Name of satellite device";
         type string;
       }
       leaf ifl-class {
         description "IFL classification";
         type enumeration {
           enum "rtsock" {
             description "Display rtsock ifls";
           }
           enum "flow" {
             description "Display flow ifls";
           }
         }
       }
       leaf smart-sfp-channel-defects {
         description "Smart SFP defect status of each channels";
         type string;
       }
       leaf smart-sfp-channel-configurations {
         description "Smart SFP channel configs";
         type string;
       }
       leaf smart-sfp-statistics {
         description "Smart SFP counters";
         type empty;
       }
       leaf smart-sfp-defects {
         description "Smart SFP defect status";
         type empty;
       }
       leaf smart-sfp-channel-statistics {
         description "Smart SFP channel counters";
         type string;
       }
       leaf aggregation-device {
         description "Aggregation device interface list";
         type empty;
       }
       leaf zone {
         description "Interface's zone";
         type empty;
       }
       leaf level {
         junos:cli-feature "nokeyword";
         type enumeration {
           enum "extensive" {
             description "Display extensive output";
           }
           enum "statistics" {
             description "Display statistics and detailed output";
           }
           enum "media" {
             description "Display media information";
           }
         }
       }
       leaf level-extra {
         junos:cli-feature "nokeyword";
         type enumeration {
           enum "detail" {
             description "Display detailed output";
           }
           enum "terse" {
             description "Display terse output";
           }
           enum "brief" {
             description "Display brief output";
           }
           enum "descriptions" {
             description "Display interface description strings";
           }
           enum "prbs-stats" {
             description "Display PRBS Stats";
           }
         }
       }
       leaf snmp-index {
         description "SNMP index of interface";
         type union {
           type uint32;
           type string {
             pattern "<.*>|$.*";
           }
         }
       }
       leaf switch-port {
         description "Front end port number";
         type union {
           type string {
             pattern "<.*>|$.*";
           }
           type uint32 {
             range "0 .. 15";
           }
         }
       }
       leaf interface-name {
         description "Name of physical or logical interface";
         junos:cli-feature "nokeyword";
         type string;
       }
     }
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-mc-ae-interface-information {
     description "Show MC-AE configured interface information";
     junos:command "show interfaces mc-ae";
     input {
       leaf id {
         description "MC-AE id";
         type union {
           type uint16;
           type string {
             pattern "<.*>|$.*";
           }
         }
       }
       leaf unit {
         description "Logical interface unit number";
         type union {
           type string {
             pattern "<.*>|$.*";
           }
           type uint32 {
             range "0 .. 16385";
           }
         }
       }
       leaf extensive {
         description "Show mcae information in detail";
         type empty;
       }
     }
     output {
       choice output-tags {
         case actual-tag {
           container mc-ae-status-information-list {
             uses mc-ae-status-information-list-block;
           }
         }
         case multichassis-tag {
           container multi-routing-engine-results {
             list multi-routing-engine-item {
               leaf re-name {
                 type string;
               }
               choice output-tags {
                 case actual-tag {
                   container mc-ae-status-information-list {
                     uses mc-ae-status-information-list-block;
                   }
                 }
               }
             }
           }
         }
       }
     }
   }
   rpc get-mc-ae-revertive-information {
     description "Show mc-ae revertive information";
     junos:command "show interfaces mc-ae revertive-info";
     input {
       leaf id {
         description "MC-AE id";
         type union {
           type uint16;
           type string {
             pattern "<.*>|$.*";
           }
         }
       }
     }
     output {
       choice output-tags {
         case actual-tag {
           container mc-ae-status-information-list {
             uses mc-ae-status-information-list-block;
           }
         }
         case multichassis-tag {
           container multi-routing-engine-results {
             list multi-routing-engine-item {
               leaf re-name {
                 type string;
               }
               choice output-tags {
                 case actual-tag {
                   container mc-ae-status-information-list {
                     uses mc-ae-status-information-list-block;
                   }
                 }
               }
             }
           }
         }
       }
     }
   }
   rpc get-interfaces-summary {
     description "Display Logical Interfaces summary output";
     junos:command "show interfaces summary";
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-interface-controller-information {
     description "Show controller information";
     junos:command "show interfaces controller";
     input {
       leaf interface-name {
         description "Name of controller";
         junos:cli-feature "nokeyword";
         type string;
       }
     }
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-interface-set-information {
     description "Show interface set information";
     junos:command "show interfaces interface-set";
     input {
       leaf level {
         junos:cli-feature "nokeyword";
         type enumeration {
           enum "terse" {
             description "Display terse output";
           }
           enum "detail" {
             description "Display detailed output";
           }
         }
       }
       leaf interface-set-name {
         description "Name of interface set";
         junos:cli-feature "nokeyword";
         type string;
       }
     }
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-interface-set-queue-information {
     description "Show queue statistics for this interface-set";
     junos:command "show interfaces interface-set queue";
     input {
       leaf forwarding-class {
         description "Name of forwarding class";
         type string;
       }
       leaf traffic-direction {
         description "Show statistics for ingress, egress or both";
         junos:cli-feature "nokeyword";
         default "both-ingress-egress";
         type enumeration {
           enum "ingress" {
             description "Display ingress queue statistics";
           }
           enum "egress" {
             description "Display egress queue statistics";
           }
           enum "both-ingress-egress" {
             description "Display both ingress and egress queue statistics";
           }
         }
       }
       leaf node-type {
         description "Show statistics for aggregate or remaining-traffic";
         junos:cli-feature "nokeyword";
         default "aggregate";
         type enumeration {
           enum "aggregate" {
             description "Display aggregate queue statistics";
           }
           enum "remaining-traffic" {
             description "Display remaining-traffic queue statistics";
           }
         }
       }
       leaf interface-set-name {
         description "Name of interface set";
         junos:cli-feature "nokeyword";
         type string;
       }
     }
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-voq-counters {
     description "Show VOQ statistics for the interface-set";
     junos:command "show interfaces interface-set voq";
     input {
       leaf forwarding-class {
         description "Name of forwarding class";
         type string;
       }
       leaf traffic {
         description "Show statistics for aggregate or remaining-traffic";
         junos:cli-feature "nokeyword";
         default "aggregate";
         type enumeration {
           enum "aggregate" {
             description "Display aggregate queue statistics";
           }
           enum "remaining-traffic" {
             description "Display remaining-traffic queue statistics";
           }
         }
       }
       leaf interface-set-name {
         description "Name of interface set";
         junos:cli-feature "nokeyword";
         type string;
       }
     }
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-interfaces-interval {
     description "Show interval statistics";
     junos:command "show interfaces interval";
     input {
       leaf interface-name {
         description "Name of physical interface";
         junos:cli-feature "nokeyword";
         type string;
         mandatory true;
       }
     }
     output {
       choice output-tags {
         case output-tag {
           leaf output {
             type string;
           }
         }
         case actual-tag {
           anyxml interfaces-interval;
         }
         case multichassis-tag {
           anyxml multi-routing-engine-results;
         }
       }
     }
   }
   rpc get-interface-transport-information {
     description "Show interface transport information";
     junos:command "show interfaces transport";
     input {
       leaf interface-name {
         description "Name of physical interface";
         junos:cli-feature "nokeyword";
         type string;
         mandatory true;
       }
     }
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-information {
     description "Show interface transport performance monitoring (pm) information";
     junos:command "show interfaces transport pm";
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-otn-information {
     description "Show interface transport otn pm information";
     junos:command "show interfaces transport pm otn";
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-otn-c-information {
     description "Show interface transport pm otn current information";
     junos:command "show interfaces transport pm otn current";
     input {
       leaf interface-name {
         description "Name of physical interface";
         junos:cli-feature "nokeyword";
         type string;
         mandatory true;
       }
     }
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-otn-c-all-information {
     description "Show interface transport pm otn current all information";
     junos:command "show interfaces transport pm otn current all";
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-otn-int-information {
     description "Show interface transport pm otn interval information";
     junos:command "show interfaces transport pm otn interval";
     input {
       leaf interface-name {
         description "Name of physical interface";
         junos:cli-feature "nokeyword";
         type string;
         mandatory true;
       }
     }
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-otn-int-all-information {
     description "Show interface transport pm otn interval all information";
     junos:command "show interfaces transport pm otn interval all";
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-otn-cday-information {
     description "Show interface transport pm otn current day information";
     junos:command "show interfaces transport pm otn currentday";
     input {
       leaf interface-name {
         description "Name of physical interface";
         junos:cli-feature "nokeyword";
         type string;
         mandatory true;
       }
     }
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-otn-cday-all-information {
     description "Show interface transport pm otn current day all information";
     junos:command "show interfaces transport pm otn currentday all";
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-otn-pday-information {
     description "Show interface transport pm otn previous day information";
     junos:command "show interfaces transport pm otn previousday";
     input {
       leaf interface-name {
         description "Name of physical interface";
         junos:cli-feature "nokeyword";
         type string;
         mandatory true;
       }
     }
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-otn-pday-all-information {
     description "Show interface transport pm otn previous day all information";
     junos:command "show interfaces transport pm otn previousday all";
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-otn-all-information {
     description "Show interface transport pm otn all information";
     junos:command "show interfaces transport pm otn all";
     input {
       leaf interface-name {
         description "Name of physical interface";
         junos:cli-feature "nokeyword";
         type string;
         mandatory true;
       }
     }
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-otn-all-all-information {
     description "Show interface transport pm otn all all information";
     junos:command "show interfaces transport pm otn all all";
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-optics-information {
     description "Show interface transport pm optics information";
     junos:command "show interfaces transport pm optics";
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-optics-c-information {
     description "Show interface transport pm optics current information";
     junos:command "show interfaces transport pm optics current";
     input {
       leaf interface-name {
         description "Name of physical interface";
         junos:cli-feature "nokeyword";
         type string;
         mandatory true;
       }
     }
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-optics-c-all-information {
     description "Show interface transport pm optics current all information";
     junos:command "show interfaces transport pm optics current all";
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-optics-int-information {
     description "Show interface transport pm optics interval information";
     junos:command "show interfaces transport pm optics interval";
     input {
       leaf interface-name {
         description "Name of physical interface";
         junos:cli-feature "nokeyword";
         type string;
         mandatory true;
       }
     }
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-optics-int-all-information {
     description "Show interface transport pm optics interval all information";
     junos:command "show interfaces transport pm optics interval all";
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-optics-cday-information {
     description "Show interface transport pm optics current day information";
     junos:command "show interfaces transport pm optics currentday";
     input {
       leaf interface-name {
         description "Name of physical interface";
         junos:cli-feature "nokeyword";
         type string;
         mandatory true;
       }
     }
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-optics-cday-all-information {
     description "Show interface transport pm optics current day all information";
     junos:command "show interfaces transport pm optics currentday all";
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-optics-pday-information {
     description "Show interface transport pm optics previous day information";
     junos:command "show interfaces transport pm optics previousday";
     input {
       leaf interface-name {
         description "Name of physical interface";
         junos:cli-feature "nokeyword";
         type string;
         mandatory true;
       }
     }
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-optics-pday-all-information {
     description "Show interface transport pm optics previous day all information";
     junos:command "show interfaces transport pm optics previousday all";
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-optics-all-information {
     description "Show interface transport pm optics all information";
     junos:command "show interfaces transport pm optics all";
     input {
       leaf interface-name {
         description "Name of physical interface";
         junos:cli-feature "nokeyword";
         type string;
         mandatory true;
       }
     }
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-optics-all-all-information {
     description "Show interface transport pm optics all all information";
     junos:command "show interfaces transport pm optics all all";
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-all-information {
     description "Show interface transport pm all information";
     junos:command "show interfaces transport pm all";
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-all-all-information {
     description "Show interface transport pm all all information";
     junos:command "show interfaces transport pm all all";
     input {
       leaf interface-name {
         description "Name of physical interface";
         junos:cli-feature "nokeyword";
         type string;
         mandatory true;
       }
     }
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-all-all-all-information {
     description "Show interface transport pm all all all information";
     junos:command "show interfaces transport pm all all all";
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-all-c-information {
     description "Show interface transport pm all current information";
     junos:command "show interfaces transport pm all current";
     input {
       leaf interface-name {
         description "Name of physical interface";
         junos:cli-feature "nokeyword";
         type string;
         mandatory true;
       }
     }
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-all-c-all-information {
     description "Show interface transport pm all current all information";
     junos:command "show interfaces transport pm all current all";
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-all-int-information {
     description "Show interface transport pm all interval information";
     junos:command "show interfaces transport pm all interval";
     input {
       leaf interface-name {
         description "Name of physical interface";
         junos:cli-feature "nokeyword";
         type string;
         mandatory true;
       }
     }
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-all-int-all-information {
     description "Show interface transport pm all interval all information";
     junos:command "show interfaces transport pm all interval all";
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-all-cday-information {
     description "Show interface transport pm all currentday information";
     junos:command "show interfaces transport pm all currentday";
     input {
       leaf interface-name {
         description "Name of physical interface";
         junos:cli-feature "nokeyword";
         type string;
         mandatory true;
       }
     }
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-all-cday-all-information {
     description "Show interface transport pm all currentday all information";
     junos:command "show interfaces transport pm all currentday all";
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-all-pday-information {
     description "Show interface transport pm all previousday information";
     junos:command "show interfaces transport pm all previousday";
     input {
       leaf interface-name {
         description "Name of physical interface";
         junos:cli-feature "nokeyword";
         type string;
         mandatory true;
       }
     }
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interface-transport-pm-all-pday-all-information {
     description "Show interface transport pm all previousday all information";
     junos:command "show interfaces transport pm all previousday all";
     output {
       choice output-tags {
         case actual-tag {
           container interface-transport-information {
             uses interface-transport-information-block;
           }
         }
         case multichassis-tag {
           container multi-routing-engine-results {
             list multi-routing-engine-item {
               leaf re-name {
                 type string;
               }
               choice output-tags {
                 case actual-tag {
                   container interface-transport-information {
                     uses interface-transport-information-block;
                   }
                 }
               }
             }
           }
         }
       }
     }
   }
   rpc get-interfaces-far-end-interval {
     description "Show far end interval statistics";
     junos:command "show interfaces far-end-interval";
     input {
       leaf interface-name {
         description "Name of physical interface";
         junos:cli-feature "nokeyword";
         type string;
         mandatory true;
       }
     }
     output {
       choice output-tags {
         case output-tag {
           leaf output {
             type string;
           }
         }
         case actual-tag {
           anyxml interfaces-far-end-interval;
         }
         case multichassis-tag {
           anyxml multi-routing-engine-results;
         }
       }
     }
   }
   rpc get-mac-database {
     description "Show media access control database information";
     junos:command "show interfaces mac-database";
     input {
       leaf interface-name {
         description "Name of physical or logical interface";
         junos:cli-feature "nokeyword";
         type string;
         mandatory true;
       }
       leaf mac-address {
         description "MAC address";
         type string;
       }
     }
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-load-balance-statistics {
     description "Show load balance statistics information";
     junos:command "show interfaces lb-stats";
     input {
       leaf interface-name {
         description "Name of AF interface";
         junos:cli-feature "nokeyword";
         type string {
           junos:posix-pattern "^(af)";
           junos:pattern-message "Only AF interface is supported";
         }
         mandatory true;
       }
     }
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-interface-queue-information {
     description "Show queue statistics for this interface";
     junos:command "show interfaces queue";
     input {
       leaf forwarding-class {
         description "Name of forwarding class";
         type string;
       }
       leaf slice {
         description "Network-slice name";
         type string;
       }
       leaf traffic-direction {
         description "Show statistics for ingress, egress or both";
         junos:cli-feature "nokeyword";
         default "both-ingress-egress";
         type enumeration {
           enum "ingress" {
             description "Display ingress queue statistics";
           }
           enum "egress" {
             description "Display egress queue statistics";
           }
           enum "both-ingress-egress" {
             description "Display both ingress and egress queue statistics";
           }
         }
       }
       leaf node-type {
         description "Show statistics for aggregate or remaining-traffic";
         junos:cli-feature "nokeyword";
         default "aggregate";
         type enumeration {
           enum "aggregate" {
             description "Display aggregate queue statistics";
           }
           enum "remaining-traffic" {
             description "Display remaining-traffic queue statistics";
           }
         }
       }
       leaf l2-statistics {
         description "Display layer-2 level queue stats for lsq interface";
         type empty;
       }
       leaf interface-name {
         description "Name of physical interface";
         junos:cli-feature "nokeyword";
         type string;
       }
     }
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-interface-voq-information {
     description "Show VOQ drop statistics for this interface";
     junos:command "show interfaces voq";
     input {
       leaf forwarding-class {
         description "Name of forwarding class";
         type string;
       }
       leaf source-fpc {
         description "Source FPC for which to show details";
         type union {
           type string {
             pattern "<.*>|$.*";
           }
           type int32 {
             range "0 .. 15";
           }
         }
       }
       leaf display-filter {
         description "Show VOQ statistics for stats-all or stats-non-zero counters";
         junos:cli-feature "nokeyword";
         type enumeration {
           enum "non-zero" {
             description "Display only non-zero VOQ statistics counters";
           }
         }
       }
       leaf interface-name {
         description "Name of physical interface";
         junos:cli-feature "nokeyword";
         type string;
       }
     }
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-interface-fc-counters-information {
     description "Show forwarding-class statistics for this interface";
     junos:command "show interfaces forwarding-class-counters";
     input {
       leaf interface-name {
         description "Name of physical interface";
         junos:cli-feature "nokeyword";
         type string;
       }
     }
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-interface-filter-information {
     description "Show interface filters information";
     junos:command "show interfaces filters";
     input {
       leaf interface-name {
         description "Name of physical or logical interface";
         junos:cli-feature "nokeyword";
         type string;
       }
     }
     output {
       choice output-tags {
         case actual-tag {
           container interface-filter-information {
             uses interface-filter-information-block;
           }
         }
         case multichassis-tag {
           container multi-routing-engine-results {
             list multi-routing-engine-item {
               leaf re-name {
                 type string;
               }
               choice output-tags {
                 case actual-tag {
                   container interface-filter-information {
                     uses interface-filter-information-block;
                   }
                 }
               }
             }
           }
         }
       }
     }
   }
   rpc get-interface-policer-information {
     description "Show interface policers information";
     junos:command "show interfaces policers";
     input {
       leaf interface-name {
         description "Name of physical or logical interface";
         junos:cli-feature "nokeyword";
         type string;
       }
     }
     output {
       choice output-tags {
         case actual-tag {
           container interface-policer-information {
             uses interface-policer-information-block;
           }
         }
         case multichassis-tag {
           container multi-routing-engine-results {
             list multi-routing-engine-item {
               leaf re-name {
                 type string;
               }
               choice output-tags {
                 case actual-tag {
                   container interface-policer-information {
                     uses interface-policer-information-block;
                   }
                 }
               }
             }
           }
         }
       }
     }
   }
   rpc get-interface-port-profile-information {
     description "Display interface operating speed information";
     junos:command "show interfaces port-profile";
     input {
       leaf interface-name {
         description "Name of physical interface";
         junos:cli-feature "nokeyword";
         type string;
       }
     }
     output {
       choice output-tags {
         case actual-tag {
           container interface-port-profile-information {
             uses interface-port-profile-information-block;
           }
         }
         case multichassis-tag {
           container multi-routing-engine-results {
             list multi-routing-engine-item {
               leaf re-name {
                 type string;
               }
               choice output-tags {
                 case actual-tag {
                   container interface-port-profile-information {
                     uses interface-port-profile-information-block;
                   }
                 }
               }
             }
           }
         }
       }
     }
   }
   rpc get-interface-optics-diagnostics-information {
     description "Show interface optics-diagnostics information";
     junos:command "show interfaces diagnostics optics";
     input {
       leaf interface-name {
         description "Name of physical interface";
         junos:cli-feature "nokeyword";
         type string;
       }
     }
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-interfaces-optics-vendor-extension {
     description "Show interface optics vendor specific information";
     junos:command "show interfaces diagnostics optics vendor-extension";
     input {
       leaf interface-name {
         description "Name of physical interface";
         junos:cli-feature "nokeyword";
         type string;
       }
     }
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-interface-optics-diagnostics-satellite {
     description "Name of physical interface in satellite device";
     junos:command "show interfaces diagnostics optics satellite";
     input {
       leaf fpc-slot {
         description "Satellite slot number";
         type union {
           type string {
             pattern "<.*>|$.*";
           }
           type uint32 {
             range "65 .. 254";
           }
         }
       }
       leaf device-alias {
         description "Device alias";
         type string;
       }
       leaf interface-name {
         description "Name of physical interface";
         junos:cli-feature "nokeyword";
         type string;
       }
     }
     output {
       choice output-tags {
         case output-tag {
           leaf output {
             type string;
           }
         }
         case multichassis-tag {
           anyxml multi-routing-engine-results;
         }
       }
     }
   }
   rpc get-interface-optics-chromatic-diagnostics {
     description "Show supported chromatic dispersion";
     junos:command "show interfaces diagnostics optics chromatic-dispersion";
     input {
       leaf interface-name {
         description "Name of physical interface";
         junos:cli-feature "nokeyword";
         type string;
       }
     }
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-interface-optics-profile-diagnostics {
     description "Show interfaces diagnostics optics-profile information";
     junos:command "show interfaces diagnostics optics-profile";
     input {
       leaf interface-name {
         description "Name of physical interface";
         junos:cli-feature "nokeyword";
         type string;
       }
     }
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-interface-optics-applications-diagnostics {
     description "Shows advertised application information";
     junos:command "show interfaces diagnostics optics-applications";
     input {
       leaf interface-name {
         description "Name of physical interface";
         junos:cli-feature "nokeyword";
         type string;
       }
     }
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-destination-class-statistics {
     description "Show statistics for destination class";
     junos:command "show interfaces destination-class";
     input {
       leaf class-name {
         description "Name of destination class";
         junos:cli-feature "nokeyword";
         type string;
         mandatory true;
       }
       leaf interface-name {
         description "Name of logical interface";
         junos:cli-feature "nokeyword";
         type string;
       }
     }
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-all-destination-class-statistics {
     description "Display all destination class usage";
     junos:command "show interfaces destination-class all";
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-source-class-statistics {
     description "Show statistics for source class";
     junos:command "show interfaces source-class";
     input {
       leaf class-name {
         description "Name of source class";
         junos:cli-feature "nokeyword";
         type string;
         mandatory true;
       }
       leaf interface-name {
         description "Name of logical interface";
         junos:cli-feature "nokeyword";
         type string;
       }
     }
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-all-source-class-statistics {
     description "Display all source class usage";
     junos:command "show interfaces source-class all";
     output {
       choice output-tags {
         case actual-tag {
           container interface-information {
             uses interface-information-block;
           }
         }
         case multichassis-tag {
           container multi-routing-engine-results {
             list multi-routing-engine-item {
               leaf re-name {
                 type string;
               }
               choice output-tags {
                 case actual-tag {
                   container interface-information {
                     uses interface-information-block;
                   }
                 }
               }
             }
           }
         }
       }
     }
   }
   rpc get-targeting-information {
     description "Show Distribution information of a bundle";
     junos:command "show interfaces targeting";
     input {
       leaf bundle-name {
         description "Name of the bundle";
         junos:cli-feature "nokeyword";
         type string;
       }
     }
     output {
       choice output-tags {
         case actual-tag {
           container targeting-information {
             uses targeting-information-block;
           }
         }
         case multichassis-tag {
           container multi-routing-engine-results {
             list multi-routing-engine-item {
               leaf re-name {
                 type string;
               }
               choice output-tags {
                 case actual-tag {
                   container targeting-information {
                     uses targeting-information-block;
                   }
                 }
               }
             }
           }
         }
       }
     }
   }
   rpc get-l2-vlan-info {
     description "Show l2 routing instance data structure";
     junos:command "show interfaces l2-routing-instance";
     input {
       leaf routing-instance {
         description "Name of the routing-instance";
         junos:cli-feature "nokeyword";
         type string;
         mandatory true;
       }
     }
     output {
       choice output-tags {
         case actual-tag {
           container l2-vlan-info {
             uses l2-vlan-info-block;
           }
         }
         case multichassis-tag {
           container multi-routing-engine-results {
             list multi-routing-engine-item {
               leaf re-name {
                 type string;
               }
               choice output-tags {
                 case actual-tag {
                   container l2-vlan-info {
                     uses l2-vlan-info-block;
                   }
                 }
               }
             }
           }
         }
       }
     }
   }
   rpc get-distribution-list-information {
     description "Show distribution list information of a bundle";
     junos:command "show interfaces distribution-list";
     input {
       leaf bundle-name {
         description "Name of the bundle";
         junos:cli-feature "nokeyword";
         type string;
       }
     }
     output {
       choice output-tags {
         case actual-tag {
           container distribution-list-information {
             uses distribution-list-information-block;
           }
         }
         case multichassis-tag {
           container multi-routing-engine-results {
             list multi-routing-engine-item {
               leaf re-name {
                 type string;
               }
               choice output-tags {
                 case actual-tag {
                   container distribution-list-information {
                     uses distribution-list-information-block;
                   }
                 }
               }
             }
           }
         }
       }
     }
   }
   rpc get-dcd-lib-client-data {
     description "Show library clients of DCD ";
     junos:command "show interfaces lib-clients";
     output {
       choice output-tags {
         case actual-tag {
           container dcd-lib-client-data {
             uses dcd-lib-client-data-block;
           }
         }
         case multichassis-tag {
           container multi-routing-engine-results {
             list multi-routing-engine-item {
               leaf re-name {
                 type string;
               }
               choice output-tags {
                 case actual-tag {
                   container dcd-lib-client-data {
                     uses dcd-lib-client-data-block;
                   }
                 }
               }
             }
           }
         }
       }
     }
   }
   rpc get-interfaces-routing {
     description "Show routing status";
     junos:command "show interfaces routing";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf level {
         junos:cli-feature "nokeyword";
         default "brief";
         type enumeration {
           enum "brief" {
             description "Display brief output (default)";
           }
           enum "detail" {
             description "Display detailed output";
           }
           enum "summary" {
             description "Display summary output";
           }
         }
       }
       leaf interface-name {
         description "Name of interface";
         junos:cli-feature "nokeyword";
         type union {
           type jt:interface-wildcard;
           type string {
             pattern "<.*>|$.*";
           }
         }
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output-tags {
         case output-tag {
           leaf output {
             type string;
           }
         }
         case multichassis-tag {
           anyxml multi-routing-engine-results;
         }
       }
     }
   }
   rpc get-interfaces-snooping {
     description "Show snooping interfaces status";
     junos:command "show interfaces snooping";
     input {
       leaf level {
         junos:cli-feature "nokeyword";
         default "brief";
         type enumeration {
           enum "brief" {
             description "Display brief output (default)";
           }
           enum "detail" {
             description "Display detailed output";
           }
           enum "summary" {
             description "Display summary output";
           }
         }
       }
       leaf interface-name {
         description "Name of interface";
         junos:cli-feature "nokeyword";
         type union {
           type jt:interface-wildcard;
           type string {
             pattern "<.*>|$.*";
           }
         }
       }
     }
     output {
       choice output-tags {
         case output-tag {
           leaf output {
             type string;
           }
         }
         case multichassis-tag {
           anyxml multi-routing-engine-results;
         }
       }
     }
   }
   rpc get-redundancy-status {
     description "Show redundancy status";
     junos:command "show interfaces redundancy";
     input {
       leaf interface-name {
         description "Name of interface";
         junos:cli-feature "nokeyword";
         type union {
           type jt:interface-wildcard;
           type string {
             pattern "<.*>|$.*";
           }
         }
       }
     }
     output {
       choice output-tags {
         case actual-tag {
           container interface-redundancy-information {
             uses interface-redundancy-information-block;
           }
         }
         case multichassis-tag {
           container multi-routing-engine-results {
             list multi-routing-engine-item {
               leaf re-name {
                 type string;
               }
               choice output-tags {
                 case actual-tag {
                   container interface-redundancy-information {
                     uses interface-redundancy-information-block;
                   }
                 }
               }
             }
           }
         }
       }
     }
   }
   rpc get-redundancy-status-details {
     description "Show redundancy status details";
     junos:command "show interfaces redundancy detail";
     input {
       leaf interface-name {
         description "Name of interface";
         junos:cli-feature "nokeyword";
         type union {
           type jt:interface-wildcard;
           type string {
             pattern "<.*>|$.*";
           }
         }
       }
     }
     output {
       choice output-tags {
         case actual-tag {
           container interface-redundancy-detail-information {
             uses interface-redundancy-detail-information-block;
           }
         }
         case multichassis-tag {
           container multi-routing-engine-results {
             list multi-routing-engine-item {
               leaf re-name {
                 type string;
               }
               choice output-tags {
                 case actual-tag {
                   container interface-redundancy-detail-information {
                     uses interface-redundancy-detail-information-block;
                   }
                 }
               }
             }
           }
         }
       }
     }
   }
   rpc interface-load-balancing {
     description "Show load-balancing status";
     junos:command "show interfaces load-balancing";
     input {
       leaf interface-name {
         description "Name of interface";
         junos:cli-feature "nokeyword";
         type union {
           type jt:interface-wildcard;
           type string {
             pattern "<.*>|$.*";
           }
         }
       }
       leaf detail {
         description "Show load-balancing status details";
         type empty;
       }
     }
     output {
       choice output-tags {
         case actual-tag {
           container interface-load-balancing-information {
             uses interface-load-balancing-information-block;
           }
         }
         case multichassis-tag {
           container multi-routing-engine-results {
             list multi-routing-engine-item {
               leaf re-name {
                 type string;
               }
               choice output-tags {
                 case actual-tag {
                   container interface-load-balancing-information {
                     uses interface-load-balancing-information-block;
                   }
                 }
               }
             }
           }
         }
       }
     }
   }
   rpc get-interface-anchor-group {
     description "Show information regarding anchoring pfe/fpc group";
     junos:command "show interfaces anchor-group";
     input {
       leaf interface-name {
         description "Name of interface";
         junos:cli-feature "nokeyword";
         type union {
           type jt:interface-wildcard;
           type string {
             pattern "<.*>|$.*";
           }
         }
       }
       leaf verbosity_level {
         description "Verbosity of output.";
         junos:cli-feature "nokeyword";
         default "brief";
         type enumeration {
           enum "brief" {
             description "Display brief output (default)";
           }
           enum "detail" {
             description "Display detailed output";
           }
         }
       }
     }
     output {
       choice output-tags {
         case actual-tag {
           container aggregated-anchor-group-information {
             uses aggregated-anchor-group-information-block;
           }
         }
         case multichassis-tag {
           container multi-routing-engine-results {
             list multi-routing-engine-item {
               leaf re-name {
                 type string;
               }
               choice output-tags {
                 case actual-tag {
                   container aggregated-anchor-group-information {
                     uses aggregated-anchor-group-information-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping interface-information-block {
     list physical-interface {
       key "name interface-name logical-interface-name";
       description
         "Information about a single physical interface";
       leaf cascade-port-satellite-device-slot-identifier {
         type int32;
         description
           "Slot id of a Satellite Device on a Cascade Port";
       }
       leaf lcp-state {
         type string;
         description
           "State of the Line Control Protocol";
       }
       leaf chap-state {
         type string;
         description
           "State of the Challenge Handshake Authentication Protocol";
       }
       leaf pap-state {
         type string;
         description
           "State of the Password Authentication Protocol";
       }
       leaf name {
         type string;
         description
           "Name of this item";
       }
       leaf mc-ae-status {
         type string;
       }
       leaf admin-status {
         type string;
         description
           "Desired state of the interface";
       }
       leaf oper-status {
         type string;
         description
           "Current operational state of the interface";
       }
       leaf extended-port-multi-homed {
         type string;
         description
           "EP Mutli-homed information";
       }
       leaf local-index {
         type int32;
         description
           "Local kernel index for this interface";
       }
       leaf snmp-index {
         type int32;
         description
           "SNMP ifIndex for this interface";
       }
       leaf generation {
         type string;
         description
           "Generation number used to distinguish between successive 
           instances of this interface";
       }
       leaf description {
         type string;
         description
           "Description of this interface";
       }
       leaf if-type {
         type string;
       }
       leaf link-level-type {
         type string;
         description
           "Encapsulation being used on the physical interface";
       }
       leaf link-media-type {
         type string;
         description
           "PHY Medium type on the physical interface";
       }
       leaf mtu {
         type string;
         description
           "MTU size on this interface";
       }
       leaf mru {
         type string;
         description
           "MRU size on this interface";
       }
       leaf clocking {
         type string;
         description
           "Reference clock source";
       }
       leaf max-speed {
         type string;
         description
           "Maximum speed at which interface can run";
       }
       leaf sonet-mode {
         type string;
         description
           "Whether the interface is in SDH or SONET mode";
       }
       leaf physical-mode {
         type string;
         description
           "Physical mode";
       }
       leaf l2circuit-mode {
         type string;
         description
           "Indicates if the interface is in L2 circuit AAL5 or Cell mode";
       }
       leaf ifd-cell-bundle-size {
         type string;
         description
           "Cell bundle size for physical interface";
       }
       leaf ifd-cell-bundle-timeout {
         type string;
         description
           "Cell bundle timeout for physical interface";
       }
       leaf link-mode {
         type string;
         description
           "Link mode of the interface";
       }
       leaf mac-mode {
         type string;
         description
           "MAC Mode of the interface";
       }
       leaf speed {
         type string;
         description
           "Speed at which the interface is running";
       }
       leaf duplex {
         type string;
         description
           "Duplex at which the interface is running";
       }
       leaf if-unidirectional {
         type string;
       }
       leaf bpdu-error {
         type string;
       }
       leaf ld-pdu-error {
         type string;
       }
       leaf eth-switch-error {
         type string;
       }
       leaf remote-bounce {
         type string;
       }
       leaf anchor-point {
         type string;
       }
       leaf l2pt-error {
         type string;
       }
       leaf loopback {
         type string;
         description
           "Whether loopback is enabled and the type of loopback";
       }
       leaf optics-loopback {
         type string;
         description
           "Whether optical loopback is enabled";
       }
       leaf sonet-loopback {
         type string;
         description
           "SONET loopback setting on channelized OC12 interface";
       }
       leaf crc {
         type string;
         description
           "Frame checksum on the interface (either 16 or 32)";
       }
       leaf payload-scrambler {
         type string;
         description
           "Whether payload scrambling is enabled";
       }
       leaf source-filtering {
         type string;
         description
           "Whether source filtering is enabled or disabled";
       }
       leaf if-flow-control {
         type string;
       }
       leaf if-speed-cfg {
         type string;
       }
       leaf if-configured-flow-control-rx-buffers {
         type string;
       }
       leaf if-configured-flow-control-tx-buffers {
         type string;
       }
       leaf if-auto-negotiation {
         type string;
         description
           "Status of auto-negotiation";
       }
       leaf if-remote-fault {
         type string;
         description
           "Status of remote fault";
       }
       leaf if-media-type {
         type string;
         description
           "Media-type copper or fiber";
       }
       leaf if-speed-auto-negotiation {
         type string;
         description
           "Status of Speed auto-negotiation";
       }
       leaf ieee-802-3az-eee {
         type string;
         description
           "IEEE 802.3az Energy Efficient Ethernet";
       }
       leaf if-auto-mdix {
         type string;
         description
           "Status of Auto MDIX";
       }
       leaf ingress-rate-limit {
         type int32;
         description
           "Layer 2 rate limit on ingress traffic for the port";
       }
       leaf minimum-links-in-aggregate {
         type int32;
         description
           "Minimum number of links needed for the bundle to be up";
       }
       leaf minimum-bandwidth-in-aggregate {
         type string;
         description
           "Minimum bandwidth needed for the bundle to be up";
       }
       leaf load-balance {
         type string;
         description
           "AE bundle load balance";
       }
       leaf ds3-mode {
         type string;
       }
       leaf ds3-long-buildout {
         type string;
       }
       leaf e3-framing {
         type string;
       }
       leaf ds1-framing {
         type string;
       }
       leaf atm-line-build-out {
         type int32;
         description
           "Line buildout";
       }
       leaf atm-encapsulation {
         type string;
         description
           "Type of ATM encapsulation";
       }
       leaf atm-e3-framing {
         type string;
         description
           "Type of framing";
       }
       leaf ih-parent {
         type string;
         description
           "Controller parent";
       }
       leaf physical-information {
         type string;
       }
       leaf link-type {
         type string;
       }
       leaf up-hold-time {
         type int32;
         description
           "Up hold-time for this interface (milliseconds)";
       }
       leaf down-hold-time {
         type int32;
         description
           "Down hold-time for this interface (milliseconds)";
       }
       leaf damp-half-life {
         type int32;
         description
           "Dampening half-life time for this interface (seconds)";
       }
       leaf damp-max-suppress {
         type int32;
         description
           "Dampening max suppress time for this interface (seconds)";
       }
       leaf damp-reuse-level {
         type int32;
         description
           "Reuse threshold";
       }
       leaf damp-suppress-level {
         type int32;
         description
           "Suppress threshold";
       }
       leaf damp-suppress-state {
         type string;
         description
           "Suppress state";
       }
       leaf time-to-reuse {
         type uint64;
         description
           "Time to reuse";
       }
       leaf current-physical-address {
         type string;
         description
           "Configured physical address for this interface";
       }
       leaf hardware-physical-address {
         type string;
         description
           "Hardware physical address for this interface";
       }
       leaf esi-value {
         type string;
         description
           "Ethernet segment identifier for this interface";
       }
       leaf esi-mode {
         type string;
         description
           "Ethernet segment mode for this interface";
       }
       leaf alternate-physical-address {
         type string;
         description
           "Alternate physical address for this interface";
       }
       leaf input-error-count {
         type int32;
         description
           "Sum of all input errors on this interface";
       }
       leaf output-error-count {
         type int32;
         description
           "Sum of all output errors on this interface";
       }
       leaf interface-flapped {
         type string;
         description
           "Time when the interface last flapped";
       }
       leaf statistics-cleared {
         type string;
         description
           "Time when statistics were last cleared";
       }
       leaf fec-mode {
         type string;
         description
           "Optics FEC mode";
       }
       leaf laser-enable {
         type string;
         description
           "Optics laser status";
       }
       leaf high-polarization {
         type string;
         description
           "Optics high polarization";
       }
       leaf interface-transmit-statistics {
         type string;
         description
           "Interface statistics based on transmitted packets";
       }
       leaf pad-to-minimum-frame-size {
         type string;
         description
           "Pad Tx vlan tagged frame to minimum of 68 bytes";
       }
       leaf preserve-interface {
         type string;
         description
           "Whether interface preservation is enabled or disabled";
       }
       leaf sonet-rx-overhead {
         type string;
       }
       leaf sonet-tx-overhead {
         type string;
       }
       leaf sonet-rx-path-trace {
         type string;
         description
           "Received SONET path trace";
       }
       leaf sonet-tx-path-trace {
         type string;
         description
           "Transmitted SONET path trace";
       }
       leaf otn-rx-overhead {
         type string;
       }
       leaf otn-tx-overhead {
         type string;
       }
       leaf otn-stats-counter {
         type string;
       }
       leaf otn-rx-tti {
         type string;
       }
       leaf otn-tx-tti {
         type string;
       }
       leaf port-forwarding-mode {
         type string;
         description
           "Port forwarding mode";
       }
       leaf cos-header {
         type empty;
       }
       leaf precl-header {
         type empty;
       }
       leaf esi-source-bmac {
         type jt:mac-addr;
         description
           "Ethernet segment source B-MAC for this interface";
       }
       leaf sonet-payload-pointer-curptr {
         type string;
         description
           "Value of the SONET/SDH payload pointer, derived from the H1 and 
           H2 overhead bytes";
       }
       leaf sonet-payload-pointer-ptrinc-count {
         type string;
         description
           "Number of times the value of the SONET/SDH payload pointer had 
           positive justification";
       }
       leaf sonet-payload-pointer-ptrdec-count {
         type string;
         description
           "Number of times the value of the SONET/SDH payload pointer had 
           negative justification";
       }
       leaf sonet-payload-pointer-newptr-ndf-count {
         type string;
         description
           "Number of times a new payload pointer was created with the New 
           Data Found flag set";
       }
       leaf link-partner-status {
         type string;
         description
           "Auto-negotiation status of link partner";
       }
       container optics-diagnostics {
         description
           "Optics diagnostics";
         leaf optic-diagnostics-not-available {
           type string;
           description
             "Optical diagnostics not supported by this transceiver";
         }
         leaf laser-bias-current-not-available {
           type string;
           description
             "Laser bias current measurement not available";
         }
         leaf soa-bias-current-not-available {
           type string;
           description
             "SOA bias current measurement not available";
         }
         leaf laser-tx-power-not-available {
           type string;
           description
             "Laser output power measurement not available";
         }
         leaf module-temperature-not-available {
           type string;
           description
             "Module temperature measurement not available";
         }
         leaf tx-module-temperature-not-available {
           type string;
           description
             "Tx module temperature measurement not available";
         }
         leaf rx-module-temperature-not-available {
           type string;
           description
             "Rx module temperature measurement not available";
         }
         leaf laser-rx-power-not-available {
           type string;
           description
             "Laser receiver optical power measurement not available";
         }
         leaf laser-tx-power-high-alarm-threshold-not-available {
           type string;
           description
             "Laser output power high alarm threshold not available";
         }
         leaf laser-tx-power-low-alarm-threshold-not-available {
           type string;
           description
             "Laser output power low alarm threshold not available";
         }
         leaf laser-tx-power-high-warning-threshold-not-available {
           type string;
           description
             "Laser output power high warning threshold not available";
         }
         leaf laser-tx-power-low-warning-threshold-not-available {
           type string;
           description
             "Laser output power low warning threshold not available";
         }
         leaf laser-bias-current-high-alarm-threshold-not-available {
           type string;
           description
             "Laser bias current high alarm threshold not available";
         }
         leaf laser-bias-current-low-alarm-threshold-not-available {
           type string;
           description
             "Laser bias current low alarm threshold not available";
         }
         leaf laser-bias-current-high-warning-threshold-not-available {
           type string;
           description
             "Laser bias current high warning threshold not available";
         }
         leaf laser-bias-current-low-warning-threshold-not-available {
           type string;
           description
             "Laser bias current low warning threshold not available";
         }
         leaf laser-bias-current {
           type string;
           description
             "Laser bias current (milliamperes)";
         }
         leaf soa-bias-current {
           type string;
           description
             "SOA bias current (milliamperes)";
         }
         leaf laser-output-power {
           type string;
           description
             "Laser output power (milliwatts)";
         }
         leaf laser-output-power-dbm {
           type string;
           description
             "Laser output power (dBm)";
         }
         leaf module-temperature {
           type string;
           description
             "Module temperature";
         }
         leaf tx-module-temperature {
           type string;
           description
             "Tx module temperature";
         }
         leaf rx-module-temperature {
           type string;
           description
             "Rx module temperature";
         }
         leaf host-id {
           type uint32;
           description
             "Host code of this interface";
         }
         leaf media-id {
           type uint32;
           description
             "Media code of this interface";
         }
         leaf host-code-desc {
           type string;
           description
             "Current optics host code";
         }
         leaf media-code-desc {
           type string;
           description
             "Current optics media code";
         }
         leaf module-voltage {
           type string;
           description
             "Module voltage";
         }
         leaf module-max-power {
           type string;
           description
             "Module max power";
         }
         leaf corrected-error-ratio {
           type string;
           description
             "Corrected error ratio";
         }
         leaf uncorrected-words-ratio {
           type string;
           description
             "Uncorrected words ratio";
         }
         leaf tx-module-voltage {
           type string;
           description
             "Tx module voltage";
         }
         leaf rx-module-voltage {
           type string;
           description
             "Rx module voltage";
         }
         leaf rx-signal-avg-optical-power {
           type string;
           description
             "Receiver signal average power (milliwatts)";
         }
         leaf rx-signal-avg-optical-power-dbm {
           type string;
           description
             "Receiver signal average power (dBm)";
         }
         leaf laser-rx-optical-power {
           type string;
           description
             "Laser receiver optical power (milliwatts)";
         }
         leaf laser-rx-optical-power-dbm {
           type string;
           description
             "Laser receiver optical power (dBm)";
         }
         leaf wavelength-channel {
           type string;
           description
             "Wavelength channel number set";
         }
         leaf wavelength-setpoint {
           type string;
           description
             "Wavelength point set";
         }
         leaf tx-dither {
           type string;
           description
             "Tx dither status";
         }
         leaf frequency-error {
           type string;
           description
             "Frequency error value";
         }
         leaf wavelength-error {
           type string;
           description
             "Wavelength error value";
         }
         leaf laser-bias-current-high-alarm {
           type string;
           description
             "Laser bias current high alarm";
         }
         leaf laser-bias-current-low-alarm {
           type string;
           description
             "Laser bias current low alarm";
         }
         leaf laser-bias-current-high-warn {
           type string;
           description
             "Laser bias current high warning";
         }
         leaf laser-bias-current-low-warn {
           type string;
           description
             "Laser bias current low warning";
         }
         leaf soa-bias-current-high-alarm {
           type string;
           description
             "SOA bias current high alarm";
         }
         leaf soa-bias-current-low-alarm {
           type string;
           description
             "SOA bias current low alarm";
         }
         leaf soa-bias-current-high-warn {
           type string;
           description
             "SOA bias current high warning";
         }
         leaf soa-bias-current-low-warn {
           type string;
           description
             "SOA bias current low warning";
         }
         leaf laser-tx-power-high-alarm {
           type string;
           description
             "Laser output power high alarm";
         }
         leaf laser-tx-power-low-alarm {
           type string;
           description
             "Laser output power low alarm";
         }
         leaf laser-tx-power-high-warn {
           type string;
           description
             "Laser output power high warning";
         }
         leaf laser-tx-power-low-warn {
           type string;
           description
             "Laser output power low warning";
         }
         leaf tx-power-high-alarm {
           type string;
           description
             "Tx power high alarm";
         }
         leaf tx-power-low-alarm {
           type string;
           description
             "Tx power low alarm";
         }
         leaf tx-power-high-warn {
           type string;
           description
             "Tx power high warning";
         }
         leaf tx-power-low-warn {
           type string;
           description
             "Tx power low warning";
         }
         leaf module-temperature-high-alarm {
           type string;
           description
             "Module temperature high alarm";
         }
         leaf module-temperature-low-alarm {
           type string;
           description
             "Module temperature low alarm";
         }
         leaf module-temperature-high-warn {
           type string;
           description
             "Module temperature high warning";
         }
         leaf module-temperature-low-warn {
           type string;
           description
             "Module temperature low warning";
         }
         leaf tx-module-temperature-high-alarm {
           type string;
           description
             "Tx module temperature high alarm";
         }
         leaf tx-module-temperature-low-alarm {
           type string;
           description
             "Tx module temperature low alarm";
         }
         leaf rx-module-temperature-high-alarm {
           type string;
           description
             "Rx module temperature high alarm";
         }
         leaf rx-module-temperature-low-alarm {
           type string;
           description
             "Rx module temperature low alarm";
         }
         leaf module-voltage-high-alarm {
           type string;
           description
             "Module voltage high alarm";
         }
         leaf module-voltage-low-alarm {
           type string;
           description
             "Module voltage low alarm";
         }
         leaf module-voltage-high-warn {
           type string;
           description
             "Module voltage high warning";
         }
         leaf module-voltage-low-warn {
           type string;
           description
             "Module voltage low warning";
         }
         leaf tx-module-voltage-high-alarm {
           type string;
           description
             "Tx module voltage high alarm";
         }
         leaf tx-module-voltage-low-alarm {
           type string;
           description
             "Tx module voltage low alarm";
         }
         leaf rx-module-voltage-high-alarm {
           type string;
           description
             "Rx module voltage high alarm";
         }
         leaf rx-module-voltage-low-alarm {
           type string;
           description
             "Rx module voltage low alarm";
         }
         leaf laser-rx-power-high-alarm {
           type string;
           description
             "Laser receiver power high alarm";
         }
         leaf laser-rx-power-low-alarm {
           type string;
           description
             "Laser receiver power low alarm";
         }
         leaf laser-rx-power-high-warn {
           type string;
           description
             "Laser receiver power high warning";
         }
         leaf laser-rx-power-low-warn {
           type string;
           description
             "Laser receiver power low warning";
         }
         leaf rx-power-high-alarm {
           type string;
           description
             "Receiver power high alarm";
         }
         leaf rx-power-low-alarm {
           type string;
           description
             "Receiver power low alarm";
         }
         leaf rx-power-high-warn {
           type string;
           description
             "Receiver power high warning";
         }
         leaf rx-power-low-warn {
           type string;
           description
             "Receiver power low warning";
         }
         leaf laser-end-of-life-alarm {
           type string;
           description
             "Laser end-of-life alarm";
         }
         leaf laser-wavelength-alarm {
           type string;
           description
             "Laser wavelength alarm";
         }
         leaf laser-bias-current-alarm {
           type string;
           description
             "Laser bias current alarm";
         }
         leaf module-temperature-alarm {
           type string;
           description
             "Module temperature alarm";
         }
         leaf laser-power-alarm {
           type string;
           description
             "Laser power alarm";
         }
         leaf modulator-temperature-alarm {
           type string;
           description
             "Modulator temperature alarm";
         }
         leaf modulator-bias-alarm {
           type string;
           description
             "Modulator bias alarm";
         }
         leaf module-not-ready-alarm {
           type string;
           description
             "Module not ready alarm";
         }
         leaf module-power-down-alarm {
           type string;
           description
             "Module power down alarm";
         }
         leaf module-not-init-done-alarm {
           type string;
           description
             "Module initialization not done alarm";
         }
         leaf module-not-high-power-on-alarm {
           type string;
           description
             "Module not high powered on alarm";
         }
         leaf module-fault-alarm {
           type string;
           description
             "Module in fault state alarm";
         }
         leaf pld-flash-init-fault-alarm {
           type string;
           description
             "PLD or Flash initialization fault alarm";
         }
         leaf power-supply-fault-alarm {
           type string;
           description
             "Power supply fault alarm";
         }
         leaf checksum-fault-alarm {
           type string;
           description
             "Checksum fault alarm";
         }
         leaf apd-supply-fault-alarm {
           type string;
           description
             "APD supply fault alarm";
         }
         leaf tec-fault-alarm {
           type string;
           description
             "TEC fault alarm";
         }
         leaf wavelength-unlocked-alarm {
           type string;
           description
             "Wavelength unlocked alarm";
         }
         leaf tx-tune-alarm {
           type string;
           description
             "Tx tune alarm";
         }
         leaf tx-mux-fifo-error-alarm {
           type string;
           description
             "Tx multiplexer fifo error alarm";
         }
         leaf tx-loss-of-pll-alarm {
           type string;
           description
             "Tx loss of PLL alarm";
         }
         leaf tx-data-not-ready-alarm {
           type string;
           description
             "Tx data not ready alarm";
         }
         leaf tx-not-ready-alarm {
           type string;
           description
             "Tx not ready alarm";
         }
         leaf tx-laser-fault-alarm {
           type string;
           description
             "Tx laser fault alarm";
         }
         leaf tx-laser-disabled-alarm {
           type string;
           description
             "Tx laser disabled alarm";
         }
         leaf tx-loss-of-signal-functionality-alarm {
           type string;
           description
             "Tx loss of signal functionality alarm";
         }
         leaf tx-cdr-loss-of-lock-alarm {
           type string;
           description
             "Tx CDR loss of lock alarm";
         }
         leaf rx-loss-avg-opt-power-alarm {
           type string;
           description
             "Receiver loss of average optical power alarm";
         }
         leaf rx-loss-ac-power-alarm {
           type string;
           description
             "Receiver loss of AC power alarm";
         }
         leaf rx-loss-of-pll-alarm {
           type string;
           description
             "Receiver loss of PLL alarm";
         }
         leaf rx-not-ready-alarm {
           type string;
           description
             "Receiver not ready alarm";
         }
         leaf rx-loss-of-signal-alarm {
           type string;
           description
             "Receiver loss of signal alarm";
         }
         leaf rx-cdr-loss-of-lock-alarm {
           type string;
           description
             "Receiver CDR loss of lock alarm";
         }
         leaf laser-bias-current-high-alarm-threshold {
           type string;
           description
             "Laser bias current high alarm threshold (milliamperes)";
         }
         leaf laser-bias-current-low-alarm-threshold {
           type string;
           description
             "Laser bias current low alarm threshold (milliamperes)";
         }
         leaf laser-bias-current-high-warn-threshold {
           type string;
           description
             "Laser bias current high warning threshold (milliamperes)";
         }
         leaf laser-bias-current-low-warn-threshold {
           type string;
           description
             "Laser bias current low warning threshold (milliamperes)";
         }
         leaf soa-bias-current-high-alarm-threshold {
           type string;
           description
             "SOA bias current high alarm threshold (milliamperes)";
         }
         leaf soa-bias-current-low-alarm-threshold {
           type string;
           description
             "SOA bias current low alarm threshold (milliamperes)";
         }
         leaf soa-bias-current-high-warn-threshold {
           type string;
           description
             "SOA bias current high warning threshold (milliamperes)";
         }
         leaf soa-bias-current-low-warn-threshold {
           type string;
           description
             "SOA bias current low warning threshold (milliamperes)";
         }
         leaf laser-tx-power-high-alarm-threshold {
           type string;
           description
             "Laser transmitter power high alarm threshold (milliwatts)";
         }
         leaf laser-tx-power-high-alarm-threshold-dbm {
           type string;
           description
             "Laser transmitter power high alarm threshold (dBm)";
         }
         leaf laser-tx-power-low-alarm-threshold {
           type string;
           description
             "Laser transmitter power low alarm threshold (milliwatts)";
         }
         leaf laser-tx-power-low-alarm-threshold-dbm {
           type string;
           description
             "Laser transmitter power low alarm threshold (dBm)";
         }
         leaf laser-tx-power-high-warn-threshold {
           type string;
           description
             "Laser transmitter power high warning threshold (milliwatts)";
         }
         leaf laser-tx-power-high-warn-threshold-dbm {
           type string;
           description
             "Laser transmitter power high warning threshold (dBm)";
         }
         leaf laser-tx-power-low-warn-threshold {
           type string;
           description
             "Laser transmitter power low warning threshold (milliwatts)";
         }
         leaf laser-tx-power-low-warn-threshold-dbm {
           type string;
           description
             "Laser transmitter power low warning threshold (dBm)";
         }
         leaf module-temperature-high-alarm-threshold {
           type string;
           description
             "Module temperature high alarm threshold";
         }
         leaf module-temperature-low-alarm-threshold {
           type string;
           description
             "Module temperature low alarm threshold";
         }
         leaf module-temperature-high-warn-threshold {
           type string;
           description
             "Module temperature high warning threshold";
         }
         leaf module-temperature-low-warn-threshold {
           type string;
           description
             "Module temperature low warning threshold";
         }
         leaf laser-temperature-high-alarm-threshold {
           type string;
           description
             "Laser temperature high alarm threshold";
         }
         leaf laser-temperature-low-alarm-threshold {
           type string;
           description
             "Laser temperature low alarm threshold";
         }
         leaf laser-temperature-high-warn-threshold {
           type string;
           description
             "Laser temperature high warning threshold";
         }
         leaf laser-temperature-low-warn-threshold {
           type string;
           description
             "Laser temperature low warning threshold";
         }
         leaf module-voltage-high-alarm-threshold {
           type string;
           description
             "Module voltage high alarm threshold (volts)";
         }
         leaf module-voltage-low-alarm-threshold {
           type string;
           description
             "Module voltage low alarm threshold (volts)";
         }
         leaf module-voltage-high-warn-threshold {
           type string;
           description
             "Module voltage high warning threshold (volts)";
         }
         leaf module-voltage-low-warn-threshold {
           type string;
           description
             "Module voltage low warning threshold (volts)";
         }
         leaf laser-rx-power-high-alarm-threshold {
           type string;
           description
             "Laser receiver power high alarm (milliwatts)";
         }
         leaf laser-rx-power-high-alarm-threshold-dbm {
           type string;
           description
             "Laser receiver power high alarm (dBm)";
         }
         leaf laser-rx-power-low-alarm-threshold {
           type string;
           description
             "Laser receiver power low alarm (milliwatts)";
         }
         leaf laser-rx-power-low-alarm-threshold-dbm {
           type string;
           description
             "Laser receiver power low alarm (dBm)";
         }
         leaf laser-rx-power-high-warn-threshold {
           type string;
           description
             "Laser receiver power high warning (milliwatts)";
         }
         leaf laser-rx-power-high-warn-threshold-dbm {
           type string;
           description
             "Laser receiver power high warning (dBm)";
         }
         leaf laser-rx-power-low-warn-threshold {
           type string;
           description
             "Laser receiver power low warning (milliwatts)";
         }
         leaf laser-rx-power-low-warn-threshold-dbm {
           type string;
           description
             "Laser receiver power low warning (dBm)";
         }
         leaf rx-power-high-alarm-threshold {
           type string;
           description
             "Receiver power high alarm (milliwatts)";
         }
         leaf rx-power-high-alarm-threshold-dbm {
           type string;
           description
             "Receiver power high alarm (dBm)";
         }
         leaf rx-power-low-alarm-threshold {
           type string;
           description
             "Receiver power low alarm (milliwatts)";
         }
         leaf rx-power-low-alarm-threshold-dbm {
           type string;
           description
             "Receiver power low alarm (dBm)";
         }
         leaf rx-power-high-warning-threshold {
           type string;
           description
             "Receiver power high warning (milliwatts)";
         }
         leaf rx-power-high-warning-threshold-dbm {
           type string;
           description
             "Receiver power high warning (dBm)";
         }
         leaf rx-power-low-warning-threshold {
           type string;
           description
             "Receiver power low warning (milliwatts)";
         }
         leaf rx-power-low-warning-threshold-dbm {
           type string;
           description
             "Receiver power low warning (dBm)";
         }
         leaf los-alarm-threshold {
           type string;
           description
             "LOS alarm threshold (milliwatts)";
         }
         leaf los-alarm-threshold-dbm {
           type string;
           description
             "LOS alarm threshold (dBm)";
         }
         leaf los-warning-threshold {
           type string;
           description
             "LOS warning threshold (milliwatts)";
         }
         leaf los-warning-threshold-dbm {
           type string;
           description
             "LOS warning threshold (dBm)";
         }
         leaf dsp-module-state {
           type string;
           description
             "DSP module state";
         }
         leaf rx-pow-manual-threshold-enabled {
           type string;
           description
             "Manual RX Power High Alarm Threshold";
         }
         leaf rx-pow-high-alarm-threshold-manual {
           type string;
           description
             "Manual RX Power High Alarm Threshold";
         }
         leaf rx-pow-high-warning-threshold-manual {
           type string;
           description
             "Manual RX Power High Warning Threshold";
         }
         leaf rx-pow-low-warning-threshold-manual {
           type string;
           description
             "Manual RX Power Low Warning Threshold";
         }
         leaf rx-pow-low-alarm-threshold-manual {
           type string;
           description
             "Manual RX Power Low Alarm Threshold";
         }
         leaf output-power {
           type string;
           description
             "Output power (milliwatts)";
         }
         leaf output-power-dbm {
           type string;
           description
             "Output power (dBm)";
         }
         leaf input-power {
           type string;
           description
             "Input power (milliwatts)";
         }
         leaf input-power-dbm {
           type string;
           description
             "Input power (dBm)";
         }
         leaf per-wave-rx-optical-power {
           type string;
           description
             "Per-wavelength receiver optical power (milliwatts)";
         }
         leaf per-wave-rx-optical-power-dbm {
           type string;
           description
             "Per-wavelength receiver optical power (dBm)";
         }
         leaf lane-laser-frequency-error {
           type string;
           description
             "Lane laser frequency error (MHz)";
         }
         leaf tec-current {
           type string;
           description
             "Tec current";
         }
         leaf residual-isi {
           type string;
           description
             "Residual ISI";
         }
         container optics-diagnostics-ot {
           description
             "OT interface optics diagnostics";
           leaf module-temp-fault {
             type string;
             description
               "Module temperature fault";
           }
           leaf specific-hw-fault {
             type string;
             description
               "Specific HW fault";
           }
           leaf internal-power-fault {
             type string;
             description
               "Internal power fault";
           }
           leaf post-therm-fault {
             type string;
             description
               "Power thermal fault";
           }
           leaf post-fault {
             type string;
             description
               "Post fault";
           }
           leaf command-error {
             type string;
             description
               "Command error";
           }
           leaf rx-pll-lock {
             type string;
             description
               "RX PLL lock";
           }
           leaf network-lane-los {
             type string;
             description
               "Network Lane LOS";
           }
           leaf network-lane-lof {
             type string;
             description
               "Network Lane LOF";
           }
           leaf network-lane-oof {
             type string;
             description
               "Network Lane OOF";
           }
           leaf network-lane-lom {
             type string;
             description
               "Network Lane LOM";
           }
           leaf network-lane-oom {
             type string;
             description
               "Network Lane OOM";
           }
           leaf network-lane-otu-bdi {
             type string;
             description
               "Network Lane OTU BDI";
           }
           leaf lane-rx-fifo-error {
             type string;
             description
               "Lane RX FIFO error";
           }
           leaf tx-reference-clock-fault {
             type string;
             description
               "TX reference clock fault";
           }
           leaf rx-modem-sync-fault {
             type string;
             description
               "Rx modem sync fault";
           }
           leaf rx-modem-loss-of-lock {
             type string;
             description
               "RX modem loss of lock";
           }
           leaf rx-loss-of-alignment {
             type string;
             description
               "RX loss of alignment";
           }
           leaf rx-out-of-alignment {
             type string;
             description
               "RX out of alignment";
           }
           leaf rx-timing-fault {
             type string;
             description
               "Rx timing fault";
           }
           leaf link-msg-data-available {
             type string;
             description
               "Link msg data available";
           }
           leaf modulator-bias-control-loop-fail {
             type string;
             description
               "Modulator Bias Control Loop Fail";
           }
           leaf itla-fault {
             type string;
             description
               "ITLA fault";
           }
           leaf dac-calib-fault {
             type string;
             description
               "DAC calib fault";
           }
           leaf adc-calib-fault {
             type string;
             description
               "ADC calib fault";
           }
           leaf prom-fault {
             type string;
             description
               "PROM fault";
           }
           leaf tx-mod-bias-voa-ctrl-loop-high-alarm {
             type string;
             description
               "TX mod bias VOA ctrl loop high alarm";
           }
           leaf tx-mod-bias-voa-ctrl-loop-low-alarm {
             type string;
             description
               "TX mod bias VOA ctrl loop low alarm";
           }
           leaf rx-phase-control-loop-high-alarm {
             type string;
             description
               "RX phase control loop high alarm";
           }
           leaf rx-phase-control-loop-low-alarm {
             type string;
             description
               "RX phase control loop low alarm";
           }
           leaf rx-phase-control-loop-high-warning {
             type string;
             description
               "RX phase control loop high warning";
           }
           leaf rx-phase-control-loop-low-warning {
             type string;
             description
               "RX phase control loop low warning";
           }
           leaf oa-pump-bias-current-high-alarm {
             type string;
             description
               "OA pump bias current high alarm";
           }
           leaf oa-pump-bias-current-low-alarm {
             type string;
             description
               "OA pump bias current low alarm";
           }
           leaf oa-pump-bias-current-high-warning {
             type string;
             description
               "OA pump bias current high warning";
           }
           leaf oa-pump-bias-current-low-warning {
             type string;
             description
               "OA pump bias current low warning";
           }
           leaf tx-jitter-pll-lol-input-nw-lane {
             type string;
             description
               "Tx jitter PLL LOL i/p nw lane";
           }
           leaf tx-out-of-alignment {
             type string;
             description
               "TX out of alignment";
           }
           leaf tx-cmu-lock-fault {
             type string;
             description
               "Tx CMU lock fault";
           }
           leaf adc-signal-below-threshold {
             type string;
             description
               "ADC signal below threshold";
           }
           leaf tx-output-power-adjustment-fault {
             type string;
             description
               "Tx output power adjustment fault";
           }
           leaf tx-output-mod-converge-fault {
             type string;
             description
               "TX output mod converge fault";
           }
           leaf tx-laser-ready-fault {
             type string;
             description
               "Tx laser ready fault";
           }
           leaf tx-laser-ready-off-fault {
             type string;
             description
               "Tx laser ready off fault";
           }
           leaf tx-asic-ready-fault {
             type string;
             description
               "Tx asic ready fault";
           }
           leaf tx-initialization-fault {
             type string;
             description
               "Tx initialization fault";
           }
           leaf rx-demodulator-lock-fault {
             type string;
             description
               "Rx demodulator lock fault";
           }
           leaf rx-dispersion-lock-fault {
             type string;
             description
               "Rx dispersion lock fault";
           }
           leaf rx-adc-output-fault {
             type string;
             description
               "Rx ADC output fault";
           }
           leaf rx-optical-input-fault {
             type string;
             description
               "Rx optical input fault";
           }
           leaf rx-asic-ready-fault {
             type string;
             description
               "Rx asic ready fault";
           }
           leaf rx-initialization-fault {
             type string;
             description
               "Rx initialization fault";
           }
           leaf tx-mod-bias-high-alarm {
             type string;
             description
               "TX modulator bias high alarm";
           }
           leaf tx-mod-bias-low-alarm {
             type string;
             description
               "TX modulator bias low alarm";
           }
           leaf tx-mod-bias-high-warning {
             type string;
             description
               "TX modulator bias high warning";
           }
           leaf tx-mod-bias-low-warning {
             type string;
             description
               "TX modulator bias low warning";
           }
           leaf rx-pwr-high-alarm {
             type string;
             description
               "RX power high alarm";
           }
           leaf rx-pwr-low-alarm {
             type string;
             description
               "RX power low alarm";
           }
           leaf rx-pwr-high-warn {
             type string;
             description
               "RX power high warning";
           }
           leaf rx-pwr-low-warn {
             type string;
             description
               "RX power low warning";
           }
           leaf tx-laser-power-high-alarm {
             type string;
             description
               "TX laser power high alarm";
           }
           leaf tx-laser-power-low-alarm {
             type string;
             description
               "TX laser power low alarm";
           }
           leaf tx-laser-power-high-warn {
             type string;
             description
               "TX laser power high warning";
           }
           leaf tx-laser-power-low-warn {
             type string;
             description
               "TX laser power low warning";
           }
           leaf tx-bias-high-alarm {
             type string;
             description
               "TX laser current high alarm";
           }
           leaf tx-bias-low-alarm {
             type string;
             description
               "TX laser current low alarm";
           }
           leaf tx-bias-high-warn {
             type string;
             description
               "TX laser current high warning";
           }
           leaf tx-bias-low-warn {
             type string;
             description
               "TX laser current low warning";
           }
           leaf tx-laser-temp-high-alarm {
             type string;
             description
               "TX laser temperature high alarm";
           }
           leaf tx-laser-temp-low-alarm {
             type string;
             description
               "TX laser temperature low alarm";
           }
           leaf tx-laser-temp-high-warn {
             type string;
             description
               "TX laser temperature high warning";
           }
           leaf tx-laser-temp-low-warn {
             type string;
             description
               "TX laser temperature low warning";
           }
         }
         list optics-diagnostics-lane-values {
           key "lane-index";
           leaf lane-index {
             type int32;
           }
           leaf laser-bias-current {
             type string;
             description
               "Laser bias current (milliamperes)";
           }
           leaf laser-bias-current-not-available {
             type string;
             description
               "Laser bias current measurement not available";
           }
           leaf laser-output-power {
             type string;
             description
               "Laser output power (milliwatts)";
           }
           leaf laser-output-power-dbm {
             type string;
             description
               "Laser output power (dBm)";
           }
           leaf output-power {
             type string;
             description
               "Output power (milliwatts)";
           }
           leaf output-power-dbm {
             type string;
             description
               "Output power (dBm)";
           }
           leaf laser-temperature {
             type string;
             description
               "Laser temperature";
           }
           leaf laser-module-temperature {
             type string;
             description
               "Module temperature";
           }
           leaf laser-tx-optical-power {
             type string;
             description
               "Laser transmitter optical power (milliwatts)";
           }
           leaf laser-tx-optical-power-dbm {
             type string;
             description
               "Laser transmitter optical power (dBm)";
           }
           leaf laser-rx-optical-power {
             type string;
             description
               "Laser receiver optical power (milliwatts)";
           }
           leaf laser-rx-optical-power-dbm {
             type string;
             description
               "Laser receiver optical power (dBm)";
           }
           leaf input-power {
             type string;
             description
               "Input power (milliwatts)";
           }
           leaf input-power-dbm {
             type string;
             description
               "Input power (dBm)";
           }
           leaf input-total-power {
             type string;
             description
               "Input power (total) (milliwatts)";
           }
           leaf input-total-power-dbm {
             type string;
             description
               "Input power (dBm)";
           }
           leaf per-wave-rx-optical-power {
             type string;
             description
               "Per-wavelength receiver optical power (milliwatts)";
           }
           leaf per-wave-rx-optical-power-dbm {
             type string;
             description
               "Per-wavelength receiver optical power (dBm)";
           }
           leaf lane-configured-cd {
             type string;
             description
               "Lane configured chromatic dispersion (ps/nm)";
           }
           leaf lane-chromatic-dispersion {
             type string;
             description
               "Lane chromatic dispersion (ps/nm)";
           }
           leaf lane-avg-chromatic-dispersion {
             type string;
             description
               "Lane avg chromatic dispersion (ps/nm)";
           }
           leaf lane-min-chromatic-dispersion {
             type string;
             description
               "Lane min chromatic dispersion (ps/nm)";
           }
           leaf lane-max-chromatic-dispersion {
             type string;
             description
               "Lane max chromatic dispersion (ps/nm)";
           }
           leaf lane-differential-group-delay {
             type string;
             description
               "Lane differential group delay (ps)";
           }
           leaf lane-avg-differential-group-delay {
             type string;
             description
               "Lane avg differential group delay (ps)";
           }
           leaf lane-min-differential-group-delay {
             type string;
             description
               "Lane min differential group delay (ps)";
           }
           leaf lane-max-differential-group-delay {
             type string;
             description
               "Lane max differential group delay (ps)";
           }
           leaf lane-sopmd {
             type string;
             description
               "Lane sopmd";
           }
           leaf lane-avg-sopmd {
             type string;
             description
               "Lane avg sopmd";
           }
           leaf lane-min-sopmd {
             type string;
             description
               "Lane min sopmd";
           }
           leaf lane-max-sopmd {
             type string;
             description
               "Lane max sopmd";
           }
           leaf q-factor {
             type string;
             description
               "Lane q-factor";
           }
           leaf q-factor-not-available {
             type string;
             description
               "Lane q-factor not available";
           }
           leaf q-margin {
             type string;
             description
               "Lane q-margin";
           }
           leaf q-margin-not-available {
             type string;
             description
               "Lane q-margin not available";
           }
           leaf lane-state-of-polarization {
             type string;
             description
               "Lane state of polarization (rad/s)";
           }
           leaf lane-avg-state-of-polarization {
             type string;
             description
               "Lane avg state of polarization (rad/s)";
           }
           leaf lane-min-state-of-polarization {
             type string;
             description
               "Lane min state of polarization (rad/s)";
           }
           leaf lane-max-state-of-polarization {
             type string;
             description
               "Lane max state of polarization (rad/s)";
           }
           leaf lane-polarization-dependent-loss {
             type string;
             description
               "Lane polarization dependent loss (dB)";
           }
           leaf lane-avg-polarization-dependent-loss {
             type string;
             description
               "Lane avg polarization dependent loss (dB)";
           }
           leaf lane-min-polarization-dependent-loss {
             type string;
             description
               "Lane min polarization dependent loss (dB)";
           }
           leaf lane-max-polarization-dependent-loss {
             type string;
             description
               "Lane max polarization dependent loss (dB)";
           }
           leaf lane-q2-factor {
             type string;
             description
               "Lane Q2 factor (dB)";
           }
           leaf lane-q-value {
             type string;
             description
               "Lane q value (dB)";
           }
           leaf lane-avg-q-value {
             type string;
             description
               "Lane avg q value (dB)";
           }
           leaf lane-min-q-value {
             type string;
             description
               "Lane min q value (dB)";
           }
           leaf lane-max-q-value {
             type string;
             description
               "Lane max q value (dB)";
           }
           leaf lane-carrier-frequency-offset {
             type string;
             description
               "Lane carrier frequency offset (MHz)";
           }
           leaf lane-avg-carrier-frequency-offset {
             type string;
             description
               "Lane avg carrier frequency offset (MHz)";
           }
           leaf lane-min-carrier-frequency-offset {
             type string;
             description
               "Lane min carrier frequency offset (MHz)";
           }
           leaf lane-max-carrier-frequency-offset {
             type string;
             description
               "Lane max carrier frequency offset (MHz)";
           }
           leaf lane-electrical-snr {
             type string;
             description
               "Lane electrical SNR (dB)";
           }
           leaf lane-snr {
             type string;
             description
               "Lane snr (dB)";
           }
           leaf lane-avg-snr {
             type string;
             description
               "Lane avg snr (dB)";
           }
           leaf lane-min-snr {
             type string;
             description
               "Lane min snr (dB)";
           }
           leaf lane-max-snr {
             type string;
             description
               "Lane max snr (dB)";
           }
           leaf lane-rx-laser-bias {
             type string;
             description
               "Lane rx laser bias (mA)";
           }
           leaf lane-rx-laser-power {
             type string;
             description
               "Lane rx laser power (dBm)";
           }
           leaf lane-rx-laser-temp {
             type string;
             description
               "Lane rx laser temp (C)";
           }
           leaf lane-tx-modulator-bias-x-i {
             type string;
             description
               "Lane tx modulator bias x i (mV)";
           }
           leaf lane-tx-modulator-bias-x-q {
             type string;
             description
               "Lane tx modulator bias x q (mV)";
           }
           leaf lane-tx-modulator-bias-y-i {
             type string;
             description
               "Lane tx modulator bias y i (mV)";
           }
           leaf lane-tx-modulator-bias-y-q {
             type string;
             description
               "Lane tx modulator bias y q (mV)";
           }
           leaf lane-tx-modulator-bias-x-phase {
             type string;
             description
               "Lane tx modulator bias x phase (mV)";
           }
           leaf lane-tx-modulator-bias-y-phase {
             type string;
             description
               "Lane tx modulator bias y phase (mV)";
           }
           leaf tx-input-equalization {
             type string;
             description
               "Tx input equalization";
           }
           leaf rx-output-amplitude {
             type string;
             description
               "Rx output amplitude";
           }
           leaf rx-output-pre-emphasis {
             type string;
             description
               "Rx output pre epmhasis";
           }
           leaf lane-laser-frequency-error {
             type string;
             description
               "Lane laser frequency error (MHz)";
           }
           leaf tec-current {
             type string;
             description
               "Tec current";
           }
           leaf residual-isi {
             type string;
             description
               "Residual ISI";
           }
           leaf pam-histogram {
             type string;
             description
               "PAM histogram";
           }
           leaf laser-bias-current-high-alarm {
             type string;
             description
               "Laser bias current high alarm";
           }
           leaf laser-bias-current-low-alarm {
             type string;
             description
               "Laser bias current low alarm";
           }
           leaf laser-bias-current-high-warn {
             type string;
             description
               "Laser bias current high warning";
           }
           leaf laser-bias-current-low-warn {
             type string;
             description
               "Laser bias current low warning";
           }
           leaf laser-tx-power-high-alarm {
             type string;
             description
               "Laser output power high alarm";
           }
           leaf laser-tx-power-low-alarm {
             type string;
             description
               "Laser output power low alarm";
           }
           leaf laser-tx-power-high-warn {
             type string;
             description
               "Laser output power high warning";
           }
           leaf laser-tx-power-low-warn {
             type string;
             description
               "Laser output power low warning";
           }
           leaf tx-power-high-alarm {
             type string;
             description
               "Tx power high alarm";
           }
           leaf tx-power-low-alarm {
             type string;
             description
               "Tx power low alarm";
           }
           leaf tx-power-high-warn {
             type string;
             description
               "Tx power high warning";
           }
           leaf tx-power-low-warn {
             type string;
             description
               "Tx power low warning";
           }
           leaf laser-temp-high-alarm {
             type string;
             description
               "Laser temperature high alarm";
           }
           leaf laser-temp-low-alarm {
             type string;
             description
               "Laser temperature low alarm";
           }
           leaf laser-temp-high-warn {
             type string;
             description
               "Laser temperature high warning";
           }
           leaf laser-temp-low-warn {
             type string;
             description
               "Laser temperature low warning";
           }
           leaf laser-rx-power-high-alarm {
             type string;
             description
               "Laser receiver power high alarm";
           }
           leaf laser-rx-power-low-alarm {
             type string;
             description
               "Laser receiver power low alarm";
           }
           leaf laser-rx-power-high-warn {
             type string;
             description
               "Laser receiver power high warning";
           }
           leaf laser-rx-power-low-warn {
             type string;
             description
               "Laser receiver power low warning";
           }
           leaf rx-power-high-alarm {
             type string;
             description
               "Receiver power high alarm";
           }
           leaf rx-power-low-alarm {
             type string;
             description
               "Receiver power low alarm";
           }
           leaf rx-power-high-warn {
             type string;
             description
               "Receiver power high warning";
           }
           leaf rx-power-low-warn {
             type string;
             description
               "Receiver power low warning";
           }
           leaf tx-loss-of-signal-functionality-alarm {
             type string;
             description
               "Tx loss of signal functionality alarm";
           }
           leaf rx-loss-of-signal-functionality-alarm {
             type string;
             description
               "Rx loss of signal functionality alarm";
           }
           leaf tx-cdr-loss-of-lock-alarm {
             type string;
             description
               "Tx CDR loss of lock alarm";
           }
           leaf tx-loss-of-signal-alarm {
             type string;
             description
               "Transmitter loss of signal alarm";
           }
           leaf rx-loss-of-signal-alarm {
             type string;
             description
               "Receiver loss of signal alarm";
           }
           leaf tx-laser-disabled-alarm {
             type string;
             description
               "Tx laser disabled alarm";
           }
           leaf rx-cdr-loss-of-lock-alarm {
             type string;
             description
               "Receiver CDR loss of lock alarm";
           }
           leaf tec-fault-alarm {
             type string;
             description
               "TEC fault alarm";
           }
           leaf wavelength-unlocked-alarm {
             type string;
             description
               "Wavelength unlocked alarm";
           }
           leaf apd-supply-fault-alarm {
             type string;
             description
               "APD supply fault alarm";
           }
           leaf tx-channel-disabled-alarm {
             type string;
             description
               "Tx channel disabled alarm";
           }
           leaf rx-channel-disabled-alarm {
             type string;
             description
               "Rx channel disabled alarm";
           }
           leaf tx-output-disabled-alarm {
             type string;
             description
               "Rx laser disabled alarm";
           }
           leaf rx-output-disabled-alarm {
             type string;
             description
               "Rx laser disabled alarm";
           }
           leaf tx-squelch-disabled-alarm {
             type string;
             description
               "Tx squelch disabled alarm";
           }
           leaf rx-squelch-disabled-alarm {
             type string;
             description
               "Rx squelch disabled alarm";
           }
           leaf laser-end-of-life-alarm {
             type string;
             description
               "Laser end-of-life alarm";
           }
           leaf lane-cd {
             type string;
             description
               "Lane chromatic dispersion";
           }
           leaf lane-dgd {
             type string;
             description
               "Lane differential group delay";
           }
           leaf lane-cfo {
             type string;
             description
               "Lane carrier frequency offset";
           }
           leaf lane-pdl {
             type string;
             description
               "Lane polarization dependent loss";
           }
           leaf lane-osnr {
             type string;
             description
               "Optical signal-to-noise ratio(dB)";
           }
         }
       }
       container optics-diagnostics-vendor-extension {
         description
           "Optics diagnostics vendor extension";
         leaf optics-vendor-part-number {
           type string;
           description
             "Optics component vendor part number";
         }
         leaf optics-vendor-material-number {
           type string;
           description
             "Optic component vendor material number";
         }
       }
       list optics-chromatics {
         key "optics-chromatic-diagnostics-support";
         leaf optics-chromatic-diagnostics-support {
           type string;
           description
             "Optics chromatic not supported for interface";
         }
         leaf opticstype {
           type string;
           description
             "Type of optical module";
         }
         list optics-chromatic {
           key "supported-cd supported-mediaid";
           leaf supported-speed {
             type string;
             description
               "Supported Speed";
           }
           leaf supported-cd {
             type string;
             description
               "Supported Chromatic Dispersion";
           }
           leaf supported-distance {
             type string;
             description
               "Supported Distance";
           }
           leaf supported-mediaid {
             type string;
             description
               "Supported Mediaid";
           }
         }
       }
       list jrr-optics-diagnostics {
         description
           "Optics diagnostics";
         leaf jrr-optics-diagnostics-not-available {
           type string;
           description
             "Optical diagnostics not available at this time for this 
             transceiver";
         }
         leaf laser-bias-current {
           type string;
           description
             "Laser bias current (milliamperes)";
         }
         leaf laser-output-power {
           type string;
           description
             "Laser output power (milliwatts)";
         }
         leaf module-temperature {
           type string;
           description
             "Module temperature";
         }
         leaf module-voltage {
           type string;
           description
             "Module voltage";
         }
         leaf module-max-power {
           type string;
           description
             "Module max power";
         }
         leaf rx-signal-avg-optical-power {
           type string;
           description
             "Receiver signal average power (milliwatts)";
         }
         leaf laser-bias-current-high-alarm {
           type string;
           description
             "Laser bias current high alarm";
         }
         leaf laser-bias-current-low-alarm {
           type string;
           description
             "Laser bias current low alarm";
         }
         leaf laser-bias-current-high-warn {
           type string;
           description
             "Laser bias current high warning";
         }
         leaf laser-bias-current-low-warn {
           type string;
           description
             "Laser bias current low warning";
         }
         leaf laser-tx-power-high-alarm {
           type string;
           description
             "Laser output power high alarm";
         }
         leaf laser-tx-power-low-alarm {
           type string;
           description
             "Laser output power low alarm";
         }
         leaf laser-tx-power-high-warn {
           type string;
           description
             "Laser output power high warning";
         }
         leaf laser-tx-power-low-warn {
           type string;
           description
             "Laser output power low warning";
         }
         leaf module-temperature-high-alarm {
           type string;
           description
             "Module temperature high alarm";
         }
         leaf module-temperature-low-alarm {
           type string;
           description
             "Module temperature low alarm";
         }
         leaf module-temperature-high-warn {
           type string;
           description
             "Module temperature high warning";
         }
         leaf module-temperature-low-warn {
           type string;
           description
             "Module temperature low warning";
         }
         leaf module-voltage-high-alarm {
           type string;
           description
             "Module voltage high alarm";
         }
         leaf module-voltage-low-alarm {
           type string;
           description
             "Module voltage low alarm";
         }
         leaf module-voltage-high-warn {
           type string;
           description
             "Module voltage high warning";
         }
         leaf module-voltage-low-warn {
           type string;
           description
             "Module voltage low warning";
         }
         leaf laser-rx-power-high-alarm {
           type string;
           description
             "Laser receiver power high alarm";
         }
         leaf laser-rx-power-low-alarm {
           type string;
           description
             "Laser receiver power low alarm";
         }
         leaf laser-rx-power-high-warn {
           type string;
           description
             "Laser receiver power high warning";
         }
         leaf laser-rx-power-low-warn {
           type string;
           description
             "Laser receiver power low warning";
         }
         leaf laser-bias-current-high-alarm-threshold {
           type string;
           description
             "Laser bias current high alarm threshold (milliamperes)";
         }
         leaf laser-bias-current-low-alarm-threshold {
           type string;
           description
             "Laser bias current low alarm threshold (milliamperes)";
         }
         leaf laser-bias-current-high-warn-threshold {
           type string;
           description
             "Laser bias current high warning threshold (milliamperes)";
         }
         leaf laser-bias-current-low-warn-threshold {
           type string;
           description
             "Laser bias current low warning threshold (milliamperes)";
         }
         leaf laser-tx-power-high-alarm-threshold {
           type string;
           description
             "Laser transmitter power high alarm threshold (milliwatts)";
         }
         leaf laser-tx-power-low-alarm-threshold {
           type string;
           description
             "Laser transmitter power low alarm threshold (milliwatts)";
         }
         leaf laser-tx-power-high-warn-threshold {
           type string;
           description
             "Laser transmitter power high warning threshold (milliwatts)";
         }
         leaf laser-tx-power-low-warn-threshold {
           type string;
           description
             "Laser transmitter power low warning threshold (milliwatts)";
         }
         leaf module-temperature-high-alarm-threshold {
           type string;
           description
             "Module temperature high alarm threshold";
         }
         leaf module-temperature-low-alarm-threshold {
           type string;
           description
             "Module temperature low alarm threshold";
         }
         leaf module-temperature-high-warn-threshold {
           type string;
           description
             "Module temperature high warning threshold";
         }
         leaf module-temperature-low-warn-threshold {
           type string;
           description
             "Module temperature low warning threshold";
         }
         leaf module-voltage-high-alarm-threshold {
           type string;
           description
             "Module voltage high alarm threshold (volts)";
         }
         leaf module-voltage-low-alarm-threshold {
           type string;
           description
             "Module voltage low alarm threshold (volts)";
         }
         leaf module-voltage-high-warn-threshold {
           type string;
           description
             "Module voltage high warning threshold (volts)";
         }
         leaf module-voltage-low-warn-threshold {
           type string;
           description
             "Module voltage low warning threshold (volts)";
         }
         leaf laser-rx-power-high-alarm-threshold {
           type string;
           description
             "Laser receiver power high alarm (milliwatts)";
         }
         leaf laser-rx-power-low-alarm-threshold {
           type string;
           description
             "Laser receiver power low alarm (milliwatts)";
         }
         leaf laser-rx-power-high-warn-threshold {
           type string;
           description
             "Laser receiver power high warning (milliwatts)";
         }
         leaf laser-rx-power-low-warn-threshold {
           type string;
           description
             "Laser receiver power low warning (milliwatts)";
         }
       }
       container if-device-flags {
         leaf ifdf-none {
           type empty;
         }
         leaf ifdf-present {
           type empty;
         }
         leaf ifdf-running {
           type empty;
         }
         leaf ifdf-duplex {
           type empty;
         }
         leaf ifdf-down {
           type empty;
         }
         leaf ifdf-no-carrier {
           type empty;
         }
         leaf ifdf-error1 {
           type empty;
         }
         leaf ifdf-error2 {
           type empty;
         }
         leaf ifdf-no-multicast {
           type empty;
         }
         leaf ifdf-loopback {
           type empty;
         }
         leaf ifdf-quench {
           type empty;
         }
         leaf ifdf-recv-all-multicasts {
           type empty;
         }
         leaf ifdf-promiscuous {
           type empty;
         }
         leaf ifdf-link-layer-down {
           type empty;
         }
         leaf ifdf-loop-detected {
           type empty;
         }
         leaf ifdf-pfe-disabled {
           type empty;
         }
         leaf ifdf-pfe-gone {
           type empty;
         }
         leaf ifdf-fabric-init-in-progress {
           type empty;
         }
         leaf ifdf-fabric-error {
           type empty;
         }
         leaf ifdf-xcvr-absent {
           type empty;
         }
         leaf ifdf-xcvr-unsupported-speed {
           type empty;
         }
         leaf ifdf-xcvr-error {
           type empty;
         }
         leaf ifdf-xcvr-rx-los {
           type empty;
         }
         leaf ifdf-xcvr-rx-alarm {
           type empty;
         }
         leaf ifdf-xcvr-tx-alarm {
           type empty;
         }
         leaf ifdf-xcvr-tx-disabled {
           type empty;
         }
         leaf ifdf-serdes-init-error {
           type empty;
         }
         leaf ifdf-serdes-tune-error {
           type empty;
         }
         leaf ifdf-retimer-line-tx-error {
           type empty;
         }
         leaf ifdf-retimer-line-rx-error {
           type empty;
         }
         leaf ifdf-retimer-sys-tx-error {
           type empty;
         }
         leaf ifdf-retimer-sys-rx-error {
           type empty;
         }
         leaf ifdf-admin-disabled {
           type empty;
         }
         leaf ifdf-xcvr-over-temperature {
           type empty;
         }
         leaf ifdf-hold-up-timer-running {
           type empty;
         }
         leaf generic-value {
           type int32;
           description
             "Hexadecimal value of unknown flag bits";
         }
       }
       container if-config-flags {
         leaf iff-none {
           type empty;
         }
         leaf iff-hardware-down {
           type empty;
         }
         leaf iff-down {
           type empty;
         }
         leaf iff-up {
           type empty;
         }
         leaf iff-admin-down {
           type empty;
         }
         leaf iff-admin-up {
           type empty;
         }
         leaf iff-link-down {
           type empty;
         }
         leaf iff-device-down {
           type empty;
         }
         leaf iff-point-to-point {
           type empty;
         }
         leaf iff-point-to-multipoint {
           type empty;
         }
         leaf plp-to-clp {
           type empty;
         }
         leaf iff-multiaccess {
           type empty;
         }
         leaf iff-change {
           type empty;
         }
         leaf iff-inverse-arp {
           type empty;
         }
         leaf iff-no-multicast {
           type empty;
         }
         leaf iff-multicast {
           type empty;
         }
         leaf iff-promiscuous {
           type empty;
         }
         leaf iff-all-multicast {
           type empty;
         }
         leaf iff-snmp-traps {
           type empty;
         }
         leaf iff-no-forwarding-viable {
           type empty;
         }
         leaf iff-macsec {
           type empty;
         }
         leaf iff-secure {
           type empty;
         }
         leaf iff-rx-passive {
           type empty;
         }
         leaf iff-tx-passive {
           type empty;
         }
         leaf iff-ccc-down {
           type empty;
         }
         leaf iff-clear-df {
           type empty;
         }
         leaf iff-tunnel-reassembly {
           type empty;
         }
         leaf iff-acfc {
           type empty;
         }
         leaf iff-pfc {
           type empty;
         }
         leaf iff-rdd {
           type empty;
         }
         leaf iff-looped {
           type empty;
         }
         leaf iff-framing-conflict {
           type empty;
         }
         leaf internal-flags {
           type string;
           description
             "Hexadecimal value of internal flag bits";
         }
       }
       container ifd-specific-config-flags {
         leaf ifdspf-none {
           type empty;
         }
         leaf ifdspf-multicast-statistics {
           type empty;
         }
         leaf ifdspf-oam-on-svlan {
           type empty;
         }
         leaf iff-rpf-counter-on-ifd {
           type empty;
         }
         leaf ifdspf-no-tunnel-services {
           type empty;
         }
         leaf internal-flags {
           type string;
           description
             "Hexadecimal value of internal flag bits";
         }
       }
       container shared-interface-physical-interface {
         description
           "Shared interface physical interface";
         leaf ownership {
           type string;
           description
             "Shared interface physical interface ownership";
         }
       }
       container if-media-flags {
         leaf ifmf-none {
           type empty;
         }
         leaf ifmf-autoselect {
           type empty;
         }
         leaf ifmf-scheduler {
           type empty;
         }
         leaf ifmf-shared-scheduler {
           type empty;
         }
         leaf ifmf-vlan-offload {
           type empty;
         }
         leaf ifmf-keepalives {
           type empty;
         }
         leaf ifmf-no-keepalives {
           type empty;
         }
         leaf ifmf-give-up {
           type empty;
         }
         leaf ifmf-loose-lcp {
           type empty;
         }
         leaf ifmf-loose-ncp {
           type empty;
         }
         leaf ifmf-ppp-acfc {
           type empty;
         }
         leaf ifmf-ppp-pfc {
           type empty;
         }
         leaf ifmf-loose-lmi {
           type empty;
         }
         leaf ifmf-dce {
           type empty;
         }
         leaf ifmf-dte {
           type empty;
         }
         leaf generic-value {
           type int32;
           description
             "Hexadecimal value of unknown flag bits";
         }
         leaf internal-flags {
           type string;
           description
             "Hexadecimal value of internal flag bits";
         }
       }
       container optics-properties {
         description
           "Optics properties";
         leaf wavelength {
           type string;
           description
             "Wavelength of optics in nanometers";
         }
         leaf frequency {
           type string;
           description
             "Frequency of optics in terahertz";
         }
         leaf optic-loopback {
           type string;
           description
             "Optic loopback status";
         }
         leaf optic-loopback-type {
           type string;
           description
             "Optic loopback type";
         }
         leaf media-code-desc {
           type string;
           description
             "Current optics media code";
         }
         leaf host-code-desc {
           type string;
           description
             "Current optics host code";
         }
       }
       container keepalive-config {
         description
           "Configured keepalive settings on this interface";
         leaf keepalive-interval {
           type int32;
         }
         leaf keepalive-up-count {
           type int32;
         }
         leaf keepalive-down-count {
           type int32;
         }
       }
       container lmi-dce-config {
         description
           "Configured LMI DCE setting on this interface";
         leaf lmi-type {
           type string;
         }
         leaf lmi-n392dce {
           type int32;
         }
         leaf lmi-n393dce {
           type int32;
         }
         leaf lmi-t392dce {
           type int32;
         }
       }
       container lmi-dte-config {
         description
           "Configured LMI DTE setting on this interface";
         leaf lmi-type {
           type string;
         }
         leaf lmi-n391dte {
           type int32;
         }
         leaf lmi-n392dte {
           type int32;
         }
         leaf lmi-n393dte {
           type int32;
         }
         leaf lmi-t391dte {
           type int32;
         }
       }
       container queue-counters {
         description
           "Queue counter statistics";
         leaf queue-counters-error-message {
           type string;
           description
             "Queue statistics not available for this interface";
         }
         container interface-cos-short-summary {
           description
             "Summary of queue information on an interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
         }
         list queue {
           key "queue-number";
           description
             "Counters for a single queue";
           leaf queue-number {
             type uint32;
             description
               "Queue number";
           }
           leaf queue-counters-queued-packets {
             type int32;
             description
               "Queued packet count";
           }
           leaf queue-counters-trans-packets {
             type int32;
             description
               "Total number of transmitted packets";
           }
           leaf queue-counters-total-drop-packets {
             type int32;
             description
               "Number of total packets dropped at the queue";
           }
           leaf forwarding-class-name {
             type string;
             description
               "Forwarding class name associated with queue";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-queued-packets-na {
             type string;
             description
               "Queued packets not available";
           }
           leaf queue-counters-queued-bytes-na {
             type string;
             description
               "Queued bytes not available";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets-na {
             type string;
             description
               "Number of packets dropped due to tail drop not available";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of packets dropped at tail drop of the queue";
           }
           leaf queue-counters-tail-drop-bytes-rate {
             type int32;
             description
               "Number of packets dropped at tail drop of the queue";
           }
           leaf queue-counters-ecn-ce-packets {
             type int32;
             description
               "Total number of ECN CE packets";
           }
           leaf queue-counters-ecn-ce-packets-rate {
             type int32;
             description
               "Rate at which ECN CE packets are transmitted";
           }
           leaf queue-counters-ecn-ce-bytes {
             type int32;
             description
               "Total number of ECN CE bytes";
           }
           leaf queue-counters-ecn-ce-bytes-rate {
             type int32;
             description
               "Rate at which ECN CE bytes are transmitted";
           }
           leaf queue-counters-rate-limit-drop-packets-na {
             type string;
             description
               "Number of packets dropped due to rate-limit drop not 
               available";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes-na {
             type string;
             description
               "Number of bytes dropped due to tail drop not available";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets-na {
             type string;
             description
               "Number of packets dropped due to RED not available";
           }
           leaf queue-counters-red-packets {
             type int32;
             description
               "Number of packets dropped due to RED";
           }
           leaf queue-counters-red-packets-rate {
             type int32;
             description
               "Rate at which packets are dropped due to RED";
           }
           leaf queue-counters-red-packets-ln {
             type int32;
             description
               "Number of RED dropped low-loss, non-TCP packets";
           }
           leaf queue-counters-red-packets-rate-ln {
             type int32;
             description
               "RED drop rate for low-loss, non-TCP packets";
           }
           leaf queue-counters-red-packets-lt {
             type int32;
             description
               "Number of RED dropped of low-loss, TCP packets";
           }
           leaf queue-counters-red-packets-rate-lt {
             type int32;
             description
               "RED drop rate for low-loss, TCP packets";
           }
           leaf queue-counters-red-packets-hn {
             type int32;
             description
               "Number of RED dropped high-loss, non-TCP packets";
           }
           leaf queue-counters-red-packets-rate-hn {
             type int32;
             description
               "RED drop rate for high-loss, non-TCP packets";
           }
           leaf queue-counters-red-packets-ht {
             type int32;
             description
               "Number of RED dropped high-loss, TCP packets";
           }
           leaf queue-counters-red-packets-rate-ht {
             type int32;
             description
               "RED drop rate for high-loss, TCP packets";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-medium {
             type int32;
             description
               "Number of RED dropped medium-loss packets";
           }
           leaf queue-counters-red-packets-rate-medium {
             type int32;
             description
               "RED drop rate for medium-loss packets";
           }
           leaf queue-counters-red-packets-high {
             type int32;
             description
               "Number of RED dropped high-loss packets";
           }
           leaf queue-counters-red-packets-rate-high {
             type int32;
             description
               "RED drop rate for high-loss packets";
           }
           leaf queue-counters-red-bytes-na {
             type string;
             description
               "Number of bytes dropped due to RED not available";
           }
           leaf queue-counters-red-bytes {
             type int32;
             description
               "Number of bytes dropped due to RED";
           }
           leaf queue-counters-red-bytes-rate {
             type int32;
             description
               "Rate at which bytes are dropped due to RED";
           }
           leaf queue-counters-red-bytes-ln {
             type int32;
             description
               "Number of RED dropped low-loss, non-TCP bytes";
           }
           leaf queue-counters-red-bytes-rate-ln {
             type int32;
             description
               "RED drop rate for low-loss, non-TCP bytes";
           }
           leaf queue-counters-red-bytes-lt {
             type int32;
             description
               "Number of RED dropped low-loss, TCP bytes";
           }
           leaf queue-counters-red-bytes-rate-lt {
             type int32;
             description
               "RED drop rate for low-loss, TCP bytes";
           }
           leaf queue-counters-red-bytes-hn {
             type int32;
             description
               "Number of RED dropped high-loss, non-TCP bytes";
           }
           leaf queue-counters-red-bytes-rate-hn {
             type int32;
             description
               "RED drop rate for high-loss, non-TCP bytes";
           }
           leaf queue-counters-red-bytes-ht {
             type int32;
             description
               "Number of RED dropped high-loss, TCP bytes";
           }
           leaf queue-counters-red-bytes-rate-ht {
             type int32;
             description
               "RED drop rate for high-loss, TCP bytes";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-medium {
             type int32;
             description
               "Number of RED dropped medium-loss bytes";
           }
           leaf queue-counters-red-bytes-rate-medium {
             type int32;
             description
               "RED drop rate for medium-loss bytes";
           }
           leaf queue-counters-red-bytes-high {
             type int32;
             description
               "Number of RED dropped high-loss bytes";
           }
           leaf queue-counters-red-bytes-rate-high {
             type int32;
             description
               "RED drop rate for high-loss bytes";
           }
           leaf queue-counters-timestamp {
             type int32;
             description
               "Last packet enqueued timestamp";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
           leaf queue-counters-reserved-buffer-packets {
             type int32;
             description
               "Queues's usage of reserved buffer pool in pkts";
           }
           leaf queue-counters-reserved-buffer-bytes {
             type int32;
             description
               "Queues's usage of reserved buffer pool in bytes";
           }
           leaf queue-counters-shared-buffer-packets {
             type int32;
             description
               "Queues's usage of shared buffer pool in pkts";
           }
           leaf queue-counters-shared-buffer-bytes {
             type int32;
             description
               "Queues's usage of shared buffer pool in bytes";
           }
           leaf queue-counters-depth-average {
             type int32;
             description
               "Time averaged queue depth";
           }
           leaf queue-counters-depth-current {
             type int32;
             description
               "Current instantaneous queue depth";
           }
           leaf queue-counters-depth-peak {
             type int32;
             description
               "Peak queue depth";
           }
           leaf queue-counters-depth-max {
             type int32;
             description
               "Maximum queue depth attained";
           }
           leaf queue-counters-srx-reserved-buffer-bytes {
             type int32;
             description
               "Queues's usage of reserved buffer pool in bytes";
           }
           leaf queue-counters-srx-depth-current {
             type int32;
             description
               "Current instantaneous queue depth";
           }
         }
         container interface-cos-summary {
           description
             "Summary of forwarding class and queue information on an 
             interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
           leaf intf-cos-burst-size-for-ifl {
             type int32;
             description
               "Burst size for the logical interface";
           }
         }
       }
       container voq-counters {
         description
           "VOQ counter statistics";
         leaf voq-counters-error-message {
           type string;
           description
             "VOQ statistics not available for this interface";
         }
         container voq {
           description
             "Counters for a single voq";
           container fpc {
             description
               "Counters for a single FPC";
             leaf fpc-no {
               type int32;
               description
                 "FPC number";
             }
             container pfe {
               description
                 "Counters for a single PFE";
               leaf-list pfe-no {
                 type int32;
                 description
                   "PFE number";
               }
               leaf voq-counters-tail-drop-packets {
                 type int32;
                 description
                   "Tail DROP packet count";
               }
               leaf voq-counters-tail-drop-packets-rate {
                 type int32;
                 description
                   "Rate at which tail packets are dropped";
               }
               leaf voq-counters-tail-drop-bytes {
                 type int32;
                 description
                   "Tail DROP bytes count";
               }
               leaf voq-counters-tail-drop-bytes-rate {
                 type int32;
                 description
                   "Rate at which tail bytes are dropped";
               }
               leaf voq-counters-drop-packets {
                 type int32;
                 description
                   "DROP packet count";
               }
               leaf voq-counters-drop-packets-rate {
                 type int32;
                 description
                   "Rate at which packets are dropped";
               }
               leaf voq-counters-drop-bytes {
                 type int32;
                 description
                   "DROP bytes count";
               }
               leaf voq-counters-drop-bytes-rate {
                 type int32;
                 description
                   "Rate at which bytes are dropped";
               }
               leaf voq-counters-queued-packets {
                 type int32;
                 description
                   "QUEUED packets count";
               }
               leaf voq-counters-queued-packets-rate {
                 type int32;
                 description
                   "Rate at which packets are queued";
               }
               leaf voq-counters-queued-bytes {
                 type int32;
                 description
                   "QUEUED bytes count";
               }
               leaf voq-counters-queued-bytes-rate {
                 type int32;
                 description
                   "Rate at which bytes are queued";
               }
               leaf voq-counters-transmitted-packets {
                 type int32;
                 description
                   "Transmitted packets count";
               }
               leaf voq-counters-transmitted-packets-rate {
                 type int32;
                 description
                   "Rate at which packets are transmitted";
               }
               leaf voq-counters-transmitted-bytes {
                 type int32;
                 description
                   "Transmitted bytes count";
               }
               leaf voq-counters-transmitted-bytes-rate {
                 type int32;
                 description
                   "Rate at which bytes are transmitted";
               }
               leaf voq-counters-queue-depth-bytes-current {
                 type int32;
                 description
                   "Current queue length";
               }
               leaf voq-counters-queue-depth-bytes-peak {
                 type int32;
                 description
                   "Peak queue length";
               }
               leaf voq-counters-queue-depth-bytes-average {
                 type int32;
                 description
                   "Average queue length";
               }
             }
           }
           leaf queue-number {
             type uint32;
             description
               "Queue number";
           }
           leaf forwarding-class-name {
             type string;
             description
               "Forwarding class name associated with queue";
           }
           leaf restricted-forwarding-class-name {
             type string;
           }
         }
       }
       container smart-sfp-av-titan-statistics {
         description
           "AimValley Smart SFP statistics";
         leaf smart-sfp-av-titan-error-message {
           type string;
           description
             "AV Smart SFP un-available";
         }
         container smart-sfp-av-titan-eth-port-statistics {
           leaf rx-crct-frames {
             type uint32;
           }
           leaf rx-crct-bytes {
             type uint32;
           }
           leaf rx-fragments {
             type uint32;
           }
           leaf rx-crct-unicast-frames {
             type uint32;
           }
           leaf rx-crct-multicast-frames {
             type uint32;
           }
           leaf rx-crct-broadcast-frames {
             type uint32;
           }
           leaf rx-err-fcs-frames {
             type uint32;
           }
           leaf rx-len-err-frames {
             type uint32;
           }
           leaf rx-undersize-frames {
             type uint32;
           }
           leaf rx-oversize-frames {
             type uint32;
           }
           leaf rx-inv-vlan-mismatch-frames {
             type uint32;
           }
           leaf rx-discarded-frames {
             type uint32;
           }
           leaf rx-dropped-q-overflow-frames {
             type uint32;
           }
           leaf tx-frames {
             type uint32;
           }
           leaf tx-bytes {
             type uint32;
           }
           leaf tx-unicast-frames {
             type uint32;
           }
           leaf tx-multicast-frames {
             type uint32;
           }
           leaf tx-broadcast-frames {
             type uint32;
           }
         }
         container smart-sfp-av-titan-iwf-statistics {
           leaf rx-packets {
             type uint32;
           }
           leaf tx-packets {
             type uint32;
           }
           leaf malformed-packets {
             type uint32;
           }
           leaf reordered-packets {
             type uint32;
           }
           leaf misordered-dropped-packets {
             type uint32;
           }
           leaf missing-packets {
             type uint32;
           }
           leaf played-out-packets {
             type uint32;
           }
           leaf jb-overrun {
             type uint32;
           }
           leaf jb-underrun {
             type uint32;
           }
         }
         container smart-sfp-av-titan-ds3-statistics {
           leaf rx-bpvexzerrors {
             type uint32;
           }
           leaf rx-cvperrors {
             type uint32;
           }
           leaf b3-errors {
             type uint32;
           }
         }
         container smart-sfp-av-titan-stm-statistics {
           leaf rx-b1-errors {
             type uint32;
           }
           leaf tx-b1-errors {
             type uint32;
           }
         }
       }
       container smart-sfp-av-titan-defects {
         description
           "AimValley Smart SFP defects";
         container smart-sfp-av-titan-defect-list {
           leaf sfp-tdm-defects {
             type string;
           }
           leaf sfp-system-defects {
             type string;
           }
         }
       }
       container forwarding-class-counters {
         description
           "Forwarding-class counter statistics";
         leaf forwarding-class-counters-error-message {
           type string;
           description
             "Forwarding-class statistics not available for this interface";
         }
         container ipv4-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container ipv6-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container mpls-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container layer2-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container other-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container protocol-aggregate-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container forwarding-class-statistics {
           container protocol-aggregate-forwarding-class-counters {
           }
           container ipv4-forwarding-class-counters {
           }
           container ipv6-forwarding-class-counters {
           }
           container mpls-forwarding-class-counters {
           }
           container layer2-forwarding-class-counters {
           }
           container other-forwarding-class-counters {
           }
         }
         container forwarding-class-accounting-parameters {
           leaf forwarding-class-accounting-for-protocol {
             type string;
           }
           leaf forwarding-class-accounting-for-traffic-direction {
             type string;
           }
           leaf forwarding-class-accounting-for-traffic-type {
             type string;
           }
           leaf forwarding-class-accounting-overhead-bytes {
             type uint32;
           }
         }
         container per-forwarding-class-counters {
           leaf fc_name_header {
             type string;
           }
           leaf forwarding-class-name {
             type string;
             description
               "Forwarding class name associated with queue";
           }
           leaf fc-input-bytes {
             type int32;
           }
           leaf fc-input-bytes-rate {
             type int32;
             description
               "Input bytes rate";
           }
           leaf fc-output-bytes {
             type int32;
           }
           leaf fc-output-bytes-rate {
             type int32;
             description
               "Output bytes rate";
           }
           leaf fc-input-packets {
             type int32;
           }
           leaf fc-input-packets-rate {
             type int32;
             description
               "Input packets rate";
           }
           leaf fc-output-packets {
             type int32;
           }
           leaf fc-output-packets-rate {
             type int32;
             description
               "Output packets rate";
           }
           leaf input-unicast-bytes {
             type int32;
           }
           leaf output-unicast-bytes {
             type int32;
           }
           leaf input-unicast-packets {
             type int32;
           }
           leaf output-unicast-packets {
             type int32;
           }
           leaf input-multicast-bytes {
             type int32;
           }
           leaf output-multicast-bytes {
             type int32;
           }
           leaf input-multicast-packets {
             type int32;
           }
           leaf output-multicast-packets {
             type int32;
           }
         }
       }
       container keepalive-statistics {
         description
           "Keepalive statistics for this interface";
         leaf keepalive-lmi-descriptor {
           type string;
         }
         leaf keepalive-input-count {
           type int32;
         }
         leaf keepalive-input-time {
           type string;
         }
         leaf keepalive-output-count {
           type int32;
         }
         leaf keepalive-output-time {
           type string;
         }
       }
       container ppp-flags {
         leaf iff-ppp-flags-acfc {
           type empty;
         }
         leaf iff-ppp-flags-pfc {
           type empty;
         }
       }
       list ncp-information {
         description
           "Network Control Protocol information";
         leaf ncp-protocol {
           type string;
           description
             "Network protocol for this NCP instance";
         }
         leaf ncp-state {
           type string;
           description
             "State of this NCP instance";
         }
       }
       container es-ifd-stats {
         description
           "ES PIC statistics";
         leaf total-anti-replay-count {
           type int32;
           description
             "Number of antireplay failures";
         }
         leaf total-authentication-failure-count {
           type int32;
           description
             "Number of authentication failures";
         }
       }
       container optics-bit-rate {
         leaf bit-rate {
           type string;
           description
             " Optics Bit Rate";
         }
       }
       container optics-fec-statistics {
         leaf fec-corrected-errors {
           type int32;
         }
         leaf fec-valid-time {
           type int32;
         }
         leaf fec-corrected-error-ratio {
           type int32;
         }
         leaf fec-uncorrected-words {
           type int32;
         }
       }
       container optic-fec-mode {
         leaf fec-mode {
           type string;
           description
             "Optics FEC mode";
         }
       }
       container optic-fec-statistics {
         leaf fec-corrected-errors {
           type int32;
         }
         leaf fec-uncorrected-words {
           type int32;
         }
         leaf fec-corrected-error-rate {
           type int32;
         }
         leaf fec-uncorrected-error-rate {
           type int32;
         }
         leaf optic-fec-uncorrected-error-ratio {
           type string;
         }
         leaf fec-valid-time {
           type int32;
         }
         leaf optic-fec-corrected-error-ratio {
           type string;
         }
       }
       container preserve-interface-statistics {
         description
           "Interface switchover statistics";
         leaf if-switchover-total {
           type int32;
           description
             "Total number of interface switchovers";
         }
         leaf if-switchover-last-attempt {
           type string;
           description
             "Interface on which the last switchover was attempted";
         }
         leaf if-switchover-last-time {
           type string;
           description
             "Time at which last interface switchover was attempted";
         }
         leaf if-switchover-min-max-avg-time {
           type string;
           description
             "Minimum, maximum and average interface switchover time";
         }
       }
       container extended-port-information {
         leaf local-port-id {
           type uint32;
           description
             "EP Local port id";
         }
         leaf internal-mc-ae-id {
           type uint32;
           description
             "Internal MC-AE id";
         }
         leaf internal-lacp-port-id {
           type uint32;
           description
             "Internal LACP port id";
         }
         leaf internal-mc-ae-redundancy-group {
           type uint32;
           description
             "Internal MC-AE Redundancy group";
         }
         leaf internal-mc-ae-mode {
           type string;
           description
             "Internal MC-AE Mode";
         }
       }
       container ngpe-ep-vxlan-info {
         leaf ngpe-ep-vtep-vni {
           type uint32;
           description
             "NGPE EP Vni Id";
         }
         leaf ngpe-ep-vtep-ip-address {
           type string;
           description
             "NGPE EP VxLAN Endpoint IP";
         }
         leaf ngpe-ep-vtep-ifl-index {
           type uint32;
           description
             "VTEP IFL Index";
         }
         leaf ngpe-ep-vtep-bd-index {
           type uint32;
           description
             "BD Index";
         }
         leaf ngpe-ep-vtep-address-family {
           type uint32;
           description
             "NGPE EP VxLAN Endpoint IP Address Familiy";
         }
       }
       container traffic-statistics {
         leaf input-bps {
           type int32;
         }
         leaf input-pps {
           type int32;
         }
         leaf output-bps {
           type int32;
         }
         leaf output-pps {
           type int32;
         }
         leaf input-packets {
           type uint64;
         }
         leaf output-packets {
           type uint64;
         }
         container ipv4-traffic-statistics {
           leaf input-bps {
             type int32;
           }
           leaf output-bps {
             type int32;
           }
           leaf input-pps {
             type int32;
           }
           leaf output-pps {
             type int32;
           }
           leaf input-bytes {
             type int32;
           }
           leaf output-bytes {
             type int32;
           }
           leaf input-packets {
             type uint64;
           }
           leaf output-packets {
             type uint64;
           }
         }
         leaf input-bytes {
           type int32;
         }
         leaf output-bytes {
           type int32;
         }
         container ipv6-transit-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-traffic-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-total-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
       }
       container multicast-statistics {
         description
           "Multicast statistics for interface";
         leaf multicast-statistics-header {
           type empty;
         }
         container ipv4-multicast-statistics {
           description
             "IPV4 multicast statistics for interface";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-multicast-statistics {
           description
             "IPV6 multicast statistics for interface";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
       }
       container ingress-traffic-statistics {
         description
           "Traffic statistics at ingress before entering Packet Forwarding 
           Engine";
         leaf input-bps {
           type int32;
         }
         leaf input-pps {
           type int32;
         }
         leaf input-drop-bps {
           type int32;
           description
             "Drop rate at ingress in bits per second ";
         }
         leaf input-drop-pps {
           type int32;
           description
             "Drop rate at ingress in packets per second ";
         }
         leaf input-bytes {
           type int32;
         }
         leaf input-packets {
           type uint64;
         }
         leaf input-drop-bytes {
           type int32;
           description
             "Drop statistics at ingress in bytes";
         }
         leaf input-drop-packets {
           type int32;
           description
             "Drop statistics at ingress in packets";
         }
       }
       container multilink-interface-errors {
         leaf oversized-frames {
           type int32;
           description
             "Number of oversized frames detected";
         }
         leaf input-error-frames {
           type int32;
           description
             "Number of frames for which an error occurred on input";
         }
         leaf input-disabled-bundle {
           type int32;
           description
             "Count of packets received on a disabled link or bundle";
         }
         leaf output-disabled-bundle {
           type int32;
           description
             "Count of packets transmitted on a disabled link or bundle";
         }
         leaf queuing-drops {
           type int32;
           description
             "Count of packets dropped by the output queue of the I/O 
             Manager ASIC";
         }
         leaf packet-buffer-overflow {
           type int32;
           description
             "Number of times the packet data buffer overflowed";
         }
         leaf fragment-buffer-overflow {
           type int32;
           description
             "Number of times the fragment data buffer overflowed";
         }
         leaf fragment-timeout {
           type int32;
           description
             "Fragments timed out during assembly";
         }
         leaf sequence-number-missing {
           type int32;
           description
             "Gap detected in sequence numbers";
         }
         leaf out-of-order-sequence-number {
           type int32;
           description
             "Fragments with an out-of-order sequence number";
         }
         leaf out-of-range-sequence-number {
           type int32;
           description
             "Fragments with an out-of-range sequence number";
         }
         leaf data-memory-error {
           type int32;
           description
             "Errors detected in data memory";
         }
         leaf control-memory-error {
           type int32;
           description
             "Errors detected in control memory";
         }
       }
       container mlfr-uni-nni-bundle-options {
         leaf mlfr-uni-nni-device-type {
           type string;
           description
             "LMI device type of this multilink Frame Relay UNI NNI bundle 
             instance";
         }
         leaf mlfr-uni-nni-mrru {
           type int32;
           description
             "Maximum RRU size of this multilink Frame Relay UNI NNI bundle 
             instance";
         }
         leaf mlfr-uni-nni-bandwidth {
           type string;
           description
             "Bandwidth of this multilink Frame Relay UNI NNI bundle";
         }
         leaf red-differential-delay {
           type int32;
           description
             "Maximum allowable differential delay of this multilink Frame 
             Relay UNI NNI bundle instance";
         }
         leaf red-differential-delay-action {
           type string;
           description
             "Action to perform (remove link from bundle or disable 
             transmit) when exceeding red limit";
         }
         leaf yellow-differential-delay {
           type int32;
           description
             "Maximum allowable differential delay of this multilink Frame 
             Relay UNI NNI bundle instance";
         }
         leaf mlfr-uni-nni-fragment-threshold {
           type int32;
           description
             "Fragment size of this multilink Frame Relay UNI NNI bundle 
             instance";
         }
         leaf mlfr-uni-nni-minimum-links {
           type int32;
           description
             "Minimum number of links to sustain this multilink Frame Relay 
             UNI NNI bundle instance";
         }
         leaf lip-hello-timer {
           type int32;
           description
             "Timer for sending periodic hello messages to the remote 
             endpoint";
         }
         leaf lip-ack-timer {
           type int32;
           description
             "How long to wait for a HELLO_ACK, ADD_LINK_ACK, or 
             REMOVE_LINK_ACK";
         }
         leaf lip-ack-retries {
           type int32;
           description
             "Maximum number of retransmissions for HELLO and LINK_ADD";
         }
         leaf bundle-class {
           type int32;
           description
             "Type of bundle class: A, B or C";
         }
         leaf mlfr-uni-nni-drop-timeout {
           type int32;
           description
             "How long to wait for all fragments of a complete packet to 
             arrive";
         }
         leaf mlfr-uni-nni-link-layer-overhead {
           type string;
           description
             "Multilink Frame Relay UNI NNI bundle link layer overhead";
         }
         leaf mlfr-uni-nni-lmi-type {
           type string;
           description
             "LMI type (ANSI or Q.933A) of this multilink Frame Relay UNI 
             NNI bundle instance";
         }
         leaf t391 {
           type int32;
           description
             "Multilink Frame Relay UNI NNI link integrity verify polling 
             timer";
         }
         leaf t392 {
           type int32;
           description
             "Multilink Frame Relay UNI NNI polling verification timer";
         }
         leaf n391 {
           type int32;
           description
             "Multilink Frame Relay UNI NNI full status polling counter";
         }
         leaf n392 {
           type int32;
           description
             "Multilink Frame Relay UNI NNI LMI error threshold";
         }
         leaf n393 {
           type int32;
           description
             "Multilink Frame Relay UNI NNI LMI monitored event count";
         }
       }
       container multilink-bundle-errors {
         description
           "Multilink bundle errors";
         leaf packet-drops {
           type int32;
           description
             "Number of packets dropped";
         }
         leaf packet-drop-bytes {
           type int32;
           description
             "Number of bytes in dropped packets";
         }
         leaf fragment-drops {
           type int32;
           description
             "Number of fragments dropped";
         }
         leaf fragment-drop-bytes {
           type int32;
           description
             "Number of bytes in dropped fragments";
         }
         leaf mrru-exceeded {
           type int32;
           description
             "Number of assembled packets that exceeded MRRU";
         }
         leaf processing-errors {
           type int32;
           description
             "Number of errors encountered in assembling packets";
         }
       }
       container input-error-list {
         description
           "Input errors on this interface";
         leaf input-errors {
           type int32;
         }
         leaf input-drops {
           type int32;
         }
         leaf invalid-vcs {
           type int32;
         }
         leaf framing-errors {
           type int32;
         }
         leaf input-runts {
           type int32;
         }
         leaf input-giants {
           type int32;
         }
         leaf input-bucket-drops {
           type int32;
         }
         leaf input-discards {
           type int32;
         }
         leaf input-l3-incompletes {
           type int32;
         }
         leaf input-l2-channel-errors {
           type int32;
         }
         leaf input-l2-mismatch-timeouts {
           type int32;
         }
         leaf input-fifo-errors {
           type int32;
         }
         leaf input-dma-errors {
           type int32;
         }
         leaf hs-link-crc-errors {
           type int32;
         }
         leaf hs-link-fifo-overflows {
           type int32;
         }
         leaf sram-errors {
           type int32;
         }
         leaf input-resource-errors {
           type int32;
         }
       }
       container output-error-list {
         description
           "Output errors on this interface";
         leaf carrier-transitions {
           type int32;
         }
         leaf output-errors {
           type int32;
         }
         leaf output-drops {
           type int32;
         }
         leaf output-collisions {
           type int32;
         }
         leaf output-hs-link-fifo-overflows {
           type int32;
         }
         leaf aged-packets {
           type int32;
         }
         leaf output-fifo-errors {
           type int32;
         }
         leaf output-dma-errors {
           type int32;
         }
         leaf hs-link-fifo-underflows {
           type int32;
         }
         leaf hs-link-crc-errors {
           type int32;
         }
         leaf mtu-errors {
           type int32;
         }
         leaf output-resource-errors {
           type int32;
         }
         leaf output-bucket-drops {
           type int32;
         }
         leaf ecn-marked-packets {
           type int32;
         }
       }
       container ber-threshold {
         description
           "Bit error rate (BER) threshold for SONET interface";
         leaf ber-sf {
           type string;
           description
             "BER-SF threshold";
         }
         leaf ber-sd {
           type string;
           description
             "BER-SD threshold";
         }
       }
       container ds1-crc-alarm-threshold {
         description
           "DS1 CRC alarm thresholds";
         leaf ds1-crc-alarm-threshold-major {
           type string;
           description
             "Threshold for CRC Major alarm";
         }
         leaf ds1-crc-alarm-threshold-minor {
           type string;
           description
             "Threshold for CRC Minor alarm";
         }
       }
       container active-alarms {
         leaf type {
           type string;
           description
             "Media type for associated interface alarms";
         }
         container interface-alarms {
           description
             "Container tag for interface alarms";
           leaf alarm-not-present {
             type empty;
             description
               "No alarm indicated";
           }
           leaf sonet-alarm-lol {
             type empty;
             description
               "Loss of light alarm";
           }
           leaf sonet-alarm-pll {
             type empty;
             description
               "PLL lock alarm";
           }
           leaf sonet-alarm-lof {
             type empty;
             description
               "Loss of frame alarm";
           }
           leaf sonet-alarm-los {
             type empty;
             description
               "Loss of signal alarm";
           }
           leaf sonet-alarm-sef {
             type empty;
             description
               "Severely errored frame alarm";
           }
           leaf sonet-alarm-lais {
             type empty;
             description
               "Line AIS alarm";
           }
           leaf sonet-alarm-pais {
             type empty;
             description
               "Path AIS alarm";
           }
           leaf sonet-alarm-lop {
             type empty;
             description
               "Loss of pointer alarm";
           }
           leaf sonet-alarm-berr-sd {
             type empty;
             description
               "Bit error rate alarm, defect";
           }
           leaf sonet-alarm-berr-sf {
             type empty;
             description
               "Bit error rate alarm, fault";
           }
           leaf sonet-alarm-lrdi {
             type empty;
             description
               "Line remote defect indicator alarm";
           }
           leaf sonet-alarm-prdi {
             type empty;
             description
               "Path remote defect indicator alarm";
           }
           leaf sonet-alarm-rei {
             type empty;
             description
               "Path remote error indicator alarm";
           }
           leaf sonet-alarm-uneq {
             type empty;
             description
               "Unequipped alarm";
           }
           leaf sonet-alarm-pmis {
             type empty;
             description
               "Path payload level mismatch alarm";
           }
           leaf sonet-alarm-loc {
             type empty;
             description
               "Loss of cell delineation alarm";
           }
           leaf sonet-alarm-vais {
             type empty;
             description
               "VT AIS alarm";
           }
           leaf sonet-alarm-vlop {
             type empty;
             description
               "VT loss of pointer alarm";
           }
           leaf sonet-alarm-vrdi {
             type empty;
             description
               "VT remote defect indicator alarm";
           }
           leaf sonet-alarm-vuneq {
             type empty;
             description
               "VT unequipped alarm";
           }
           leaf sonet-alarm-vmis {
             type empty;
             description
               "VT label mismatch alarm";
           }
           leaf sonet-alarm-vloc {
             type empty;
             description
               "VT loss of cell delineation alarm";
           }
           leaf sdh-alarm-lol {
             type empty;
             description
               "Loss of light alarm";
           }
           leaf sdh-alarm-pll {
             type empty;
             description
               "PLL lock alarm";
           }
           leaf sdh-alarm-lof {
             type empty;
             description
               "Loss of frame alarm";
           }
           leaf sdh-alarm-los {
             type empty;
             description
               "Loss of signal alarm";
           }
           leaf sdh-alarm-oof {
             type empty;
             description
               "Out of frame alarm";
           }
           leaf sdh-alarm-msais {
             type empty;
             description
               "Multiplex section AIS alarm";
           }
           leaf sdh-alarm-hpais {
             type empty;
             description
               "High order path AIS alarm";
           }
           leaf sdh-alarm-lop {
             type empty;
             description
               "Loss of pointer alarm";
           }
           leaf sdh-alarm-berr-sd {
             type empty;
             description
               "Bit error rate alarm, defect";
           }
           leaf sdh-alarm-berr-sf {
             type empty;
             description
               "Bit error rate alarm, fault";
           }
           leaf sdh-alarm-msferf {
             type empty;
             description
               "Multiplex section far-end remote failure alarm";
           }
           leaf sdh-alarm-hpferf {
             type empty;
             description
               "High order path far-end remote failure alarm";
           }
           leaf sdh-alarm-hpfebe {
             type empty;
             description
               "High order path far-end block error alarm";
           }
           leaf sdh-alarm-hpuneq {
             type empty;
             description
               "High order path unequipped alarm";
           }
           leaf sdh-alarm-hpplm {
             type empty;
             description
               "High order path payload level mismatch alarm";
           }
           leaf sdh-alarm-loc {
             type empty;
             description
               "Loss of cell delineation alarm";
           }
           leaf sdh-alarm-tuais {
             type empty;
             description
               "TU AIS alarm";
           }
           leaf sdh-alarm-tulop {
             type empty;
             description
               "TU loss of pointer alarm";
           }
           leaf sdh-alarm-turdi {
             type empty;
             description
               "TU remote defect indicator alarm";
           }
           leaf sdh-alarm-tuuneq {
             type empty;
             description
               "TU unequipped alarm";
           }
           leaf sdh-alarm-tumis {
             type empty;
             description
               "TU label mismatch error";
           }
           leaf sdh-alarm-tuloc {
             type empty;
             description
               "TU loss of cell delineation alarm";
           }
           leaf ds3-alarm-pll {
             type empty;
             description
               "PLL lock alarm";
           }
           leaf ds3-alarm-ais {
             type empty;
             description
               "AIS alarm";
           }
           leaf ds3-alarm-lof {
             type empty;
             description
               "Loss of frame alarm";
           }
           leaf ds3-alarm-los {
             type empty;
             description
               "Loss of signal alarm";
           }
           leaf ds3-alarm-lcv {
             type empty;
             description
               "Line code violation alarm";
           }
           leaf ds3-alarm-exz {
             type empty;
             description
               "Excessive zeros alarm";
           }
           leaf ds3-alarm-ferf {
             type empty;
             description
               "Far-end receive failure alarm";
           }
           leaf ds3-alarm-ylw {
             type empty;
             description
               "Yellow alarm";
           }
           leaf ds3-alarm-idle {
             type empty;
             description
               "Idle alarm";
           }
           leaf ds1-alarm-ais {
             type empty;
             description
               "AIS alarm";
           }
           leaf ds1-alarm-lof {
             type empty;
             description
               "Loss of frame alarm";
           }
           leaf ds1-alarm-los {
             type empty;
             description
               "Loss of signal alarm";
           }
           leaf ds1-alarm-ylw {
             type empty;
             description
               "Yellow alarm";
           }
           leaf ds1-alarm-crc-major {
             type empty;
             description
               "CRC errors crossed major threshold";
           }
           leaf ds1-alarm-crc-minor {
             type empty;
             description
               "CRC errors crossed minor threshold";
           }
           leaf dsl-alarm-lof {
             type empty;
             description
               "Loss of frame alarm";
           }
           leaf dsl-alarm-los {
             type empty;
             description
               "Loss of signal alarm";
           }
           leaf dsl-alarm-lom {
             type empty;
             description
               "Loss of multiframe alarm";
           }
           leaf dsl-alarm-locdi {
             type empty;
             description
               "Loss of cell delineation alarm for interleaved channel";
           }
           leaf dsl-alarm-locdni {
             type empty;
             description
               "Loss of cell delineation alarm for non-interleaved channel";
           }
           leaf dsl-alarm-lop {
             type empty;
             description
               "Loss of power alarm";
           }
           leaf dsl-alarm-far-lof {
             type empty;
             description
               "Far-end loss-of-frame alarm";
           }
           leaf dsl-alarm-far-los {
             type empty;
             description
               "Far-end loss-of-signal alarm";
           }
           leaf dsl-alarm-far-locdi {
             type empty;
             description
               "Far-end loss-of-cell-delineation alarm for interleaved 
               channel";
           }
           leaf dsl-alarm-far-locdni {
             type empty;
             description
               "Far-end loss-of-cell-delineation alarm for non-interleaved 
               channel";
           }
           leaf fibrechannel-alarm-link-down {
             type empty;
             description
               "Link alive failure";
           }
           leaf ethernet-alarm-link-down {
             type empty;
             description
               "Link alive failure";
           }
           leaf ethernet-alarm-an-not-supported {
             type empty;
             description
               "AN not supported";
           }
           leaf ethernet-alarm-link-local-fault {
             type empty;
             description
               "Link local fault";
           }
           leaf ethernet-alarm-link-remote-fault {
             type empty;
             description
               "Link remote fault";
           }
           leaf ethernet-alarm-link-local-degrade {
             type empty;
             description
               "Link local degrade";
           }
           leaf ethernet-alarm-link-remote-degrade {
             type empty;
             description
               "Link remote degrade";
           }
           leaf ethernet-alarm-lcdp {
             type empty;
             description
               "Loss of code-group delineation";
           }
           leaf isdn-alarm-los {
             type empty;
             description
               "Loss of signal alarm";
           }
           leaf isdn-alarm-lof {
             type empty;
             description
               "Loss of frame alarm";
           }
           leaf shdsl-alarm-losd {
             type empty;
             description
               "Loss of signal alarm";
           }
           leaf shdsl-alarm-losw {
             type empty;
             description
               "Loss of sync word alarm";
           }
           leaf shdsl-alarm-line1-losd {
             type empty;
             description
               "Loss of signal (line 1) alarm";
           }
           leaf shdsl-alarm-line1-losw {
             type empty;
             description
               "Loss of sync word (line 1) alarm";
           }
           leaf shdsl-alarm-line2-losd {
             type empty;
             description
               "Loss of signal (line 2) alarm";
           }
           leaf shdsl-alarm-line2-losw {
             type empty;
             description
               "Loss of sync word (line 2) alarm";
           }
           leaf shdsl-efm-alarm-losd {
             type empty;
             description
               "Loss of signal alarm";
           }
           leaf shdsl-efm-alarm-losw {
             type empty;
             description
               "Loss of sync word alarm";
           }
           leaf otn-alarm-los {
             type empty;
             description
               "Loss of signal alarm";
           }
           leaf otn-alarm-lof {
             type empty;
             description
               "Loss of frame alarm";
           }
           leaf otn-alarm-lom {
             type empty;
             description
               "Loss of multiframe alarm";
           }
           leaf otn-alarm-wavelength-lock {
             type empty;
             description
               "Loss of Wavelength Lock alarm";
           }
           leaf otn-alarm-otu-ais {
             type empty;
             description
               "OTU Alarm Indication Signal alarm";
           }
           leaf otn-alarm-otu-bdi {
             type empty;
             description
               "OTU Background Block Error alarm";
           }
           leaf otn-alarm-otu-ttim {
             type empty;
             description
               "OTU Trail Trace Identifier Mismatch alarm";
           }
           leaf otn-alarm-otu-iae {
             type empty;
             description
               "OTU Incoming Alignment alarm";
           }
           leaf otn-alarm-otu-sd {
             type empty;
             description
               "OTU Signal Degrade alarm";
           }
           leaf otn-alarm-otu-sf {
             type empty;
             description
               "OTU Signal Fail alarm";
           }
           leaf otn-alarm-otu-biae {
             type empty;
             description
               "OTU Backward Incoming Alignment alarm";
           }
           leaf otn-alarm-otu-tsf {
             type empty;
             description
               "OTU Trail Signal Fail alarm";
           }
           leaf otn-alarm-otu-ssf {
             type empty;
             description
               "OTU Server Signal Fail alarm";
           }
           leaf otn-alarm-otu-fec-excessive {
             type empty;
             description
               "OTU FEC Excessive alarm";
           }
           leaf otn-alarm-otu-fec-degraded {
             type empty;
             description
               "OTU FEC Degraded alarm";
           }
           leaf otn-alarm-otu-fe-fec-degraded {
             type empty;
             description
               "OTU FE FEC Degraded/Excessive alarm";
           }
           leaf otn-alarm-otu-threshold-bbe {
             type empty;
             description
               "OTU Background Block Error threshold alarm";
           }
           leaf otn-alarm-otu-threshold-es {
             type empty;
             description
               "OTU Errored Seconds threshold alarm";
           }
           leaf otn-alarm-otu-threshold-ses {
             type empty;
             description
               "OTU Severely Errored Seconds threshold alarm";
           }
           leaf otn-alarm-otu-threshold-uas {
             type empty;
             description
               "OTU Unavailable Seconds threshold alarm";
           }
           leaf otn-alarm-odu-ais {
             type empty;
             description
               "ODU  Alarm Indiaction Signal alarm";
           }
           leaf otn-alarm-odu-oci {
             type empty;
             description
               "ODU Open Connection Indication alarm";
           }
           leaf otn-alarm-odu-lck {
             type empty;
             description
               "ODU Locked alarm";
           }
           leaf otn-alarm-odu-bdi {
             type empty;
             description
               "ODU Backward Defect Indication alarm";
           }
           leaf otn-alarm-odu-ttim {
             type empty;
             description
               "ODU Trail Trace Identifier Mismatch alarm";
           }
           leaf otn-alarm-odu-sd {
             type empty;
             description
               "ODU Signal Degrade alarm";
           }
           leaf otn-alarm-odu-sf {
             type empty;
             description
               "ODU Signal Fail alarm";
           }
           leaf otn-alarm-odu-iae {
             type empty;
             description
               "ODU Incoming Alignment alarm";
           }
           leaf otn-alarm-odu-ltc {
             type empty;
             description
               "ODU Loss of Tandem Connection alarm";
           }
           leaf otn-alarm-odu-csf {
             type empty;
             description
               "ODU Client Signal Fail alarm";
           }
           leaf otn-alarm-odu-tsf {
             type empty;
             description
               "ODU Trail Signal Fail alarm";
           }
           leaf otn-alarm-odu-ssf {
             type empty;
             description
               "ODU Server Signal Fail alarm";
           }
           leaf otn-alarm-odu-rx-aps-change {
             type empty;
             description
               "ODU Rx Aps Change alarm";
           }
           leaf otn-alarm-odu-threshold-bbe {
             type empty;
             description
               "ODU Background Block Error threshold alarm";
           }
           leaf otn-alarm-odu-threshold-es {
             type empty;
             description
               "ODU Errored Seconds threshold alarm";
           }
           leaf otn-alarm-odu-threshold-ses {
             type empty;
             description
               "ODU Severely Errored Seconds threshold alarm";
           }
           leaf otn-alarm-odu-threshold-uas {
             type empty;
             description
               "ODU Unavailable Seconds threshold alarm";
           }
           leaf otn-alarm-opu-pmi {
             type empty;
             description
               "OPU Payload Mismatch alarm";
           }
           leaf otn-alarm-pre-fec-sd {
             type empty;
             description
               "Pre-FEC SD alarm";
           }
           leaf otn-alarm-fe-pre-fec-sd {
             type empty;
             description
               "Far end pre-FEC SD alarm";
           }
           leaf optics-alarms-mod-fault {
             type empty;
             description
               "Module Fault alarm";
           }
           leaf optics-alarms-lol {
             type empty;
             description
               "Loss of Lock alarm";
           }
           leaf optics-alarms-los {
             type empty;
             description
               "Loss of Signal alarms";
           }
           leaf optics-alarms-lof {
             type empty;
             description
               "Loss of frame alarm";
           }
           leaf optics-alarms-lom {
             type empty;
             description
               "Loss of multi-frame alarm";
           }
           leaf optics-alarms-otu-bdi {
             type empty;
             description
               "Backward defect indiacation alarm";
           }
           leaf optics-alarms-rmsf {
             type empty;
             description
               "Rx Modem sysnc fault alarm";
           }
           leaf optics-alarms-rmlol {
             type empty;
             description
               "Rx Modem loss of lock alarm";
           }
           leaf optics-alarms-rloa {
             type empty;
             description
               "Rx loss of alignment alarm";
           }
           leaf optics-alarms-mbclf {
             type empty;
             description
               "Modulator Bias control loop fail alarm";
           }
           leaf optics-alarms-itlaf {
             type empty;
             description
               "ITLA Fault alarm";
           }
           leaf optics-alarms-daccf {
             type empty;
             description
               "DAC Calibration Fault alarm";
           }
           leaf optics-alarms-adccf {
             type empty;
             description
               "ADC Calibration Fault alarm";
           }
           leaf optics-alarms-fec-degrade {
             type empty;
             description
               "FEC Degrade alarm";
           }
           leaf optics-alarms-fec-excessive {
             type empty;
             description
               "FEC Excessive alarm";
           }
           leaf optics-alarms-fe-fec-degrade {
             type empty;
             description
               "Far-end FEC Degrade alarm";
           }
           leaf optics-alarms-fe-fec-excessive {
             type empty;
             description
               "Far-end FEC Excessive alarm";
           }
           leaf ima-alarm-startup-fe {
             type empty;
             description
               "IMA group startup far-end alarm";
           }
           leaf ima-alarm-config-abort {
             type empty;
             description
               "IMA group config abort alarm";
           }
           leaf ima-alarm-config-abort-fe {
             type empty;
             description
               "IMA group config abort far-end alarm";
           }
           leaf ima-alarm-insufficient-links {
             type empty;
             description
               "IMA group insufficient links alarm";
           }
           leaf ima-alarm-insufficient-links-fe {
             type empty;
             description
               "IMA group insufficient links far-end alarm";
           }
           leaf ima-alarm-blocked {
             type empty;
             description
               "IMA group blocked alarm";
           }
           leaf ima-alarm-blocked-fe {
             type empty;
             description
               "IMA group blocked far-end alarm";
           }
           leaf ima-alarm-timing-mismatch {
             type empty;
             description
               "IMA group timing mismatch alarm";
           }
           leaf ima-alarm-version-mismatch {
             type empty;
             description
               "IMA group version mismatch alarm";
           }
           leaf ima-alarm-lif {
             type empty;
             description
               "IMA link loss of IMA frame alarm";
           }
           leaf ima-alarm-lods {
             type empty;
             description
               "IMA link out of delay synchronization alarm";
           }
           leaf ima-alarm-rdi {
             type empty;
             description
               "IMA link remote defect indicator alarm";
           }
           leaf ima-alarm-tx-misconnected {
             type empty;
             description
               "IMA link tx misconnected alarm";
           }
           leaf ima-alarm-rx-misconnected {
             type empty;
             description
               "IMA link rx misconnected alarm";
           }
           leaf ima-alarm-fault {
             type empty;
             description
               "IMA link fault alarm";
           }
           leaf ima-alarm-tx-unusable-fe {
             type empty;
             description
               "IMA link Tx unusable far-end alarm";
           }
           leaf ima-alarm-rx-unusable-fe {
             type empty;
             description
               "IMA link Tx unusable far-end alarm";
           }
           leaf generic-value {
             type int32;
             description
               "Hexadecimal value of unknown flag bits";
           }
         }
       }
       container active-defects {
         leaf type {
           type string;
           description
             "Media type for associated interface alarms";
         }
         container interface-alarms {
           description
             "Container tag for interface alarms";
           leaf alarm-not-present {
             type empty;
             description
               "No alarm indicated";
           }
           leaf sonet-alarm-lol {
             type empty;
             description
               "Loss of light alarm";
           }
           leaf sonet-alarm-pll {
             type empty;
             description
               "PLL lock alarm";
           }
           leaf sonet-alarm-lof {
             type empty;
             description
               "Loss of frame alarm";
           }
           leaf sonet-alarm-los {
             type empty;
             description
               "Loss of signal alarm";
           }
           leaf sonet-alarm-sef {
             type empty;
             description
               "Severely errored frame alarm";
           }
           leaf sonet-alarm-lais {
             type empty;
             description
               "Line AIS alarm";
           }
           leaf sonet-alarm-pais {
             type empty;
             description
               "Path AIS alarm";
           }
           leaf sonet-alarm-lop {
             type empty;
             description
               "Loss of pointer alarm";
           }
           leaf sonet-alarm-berr-sd {
             type empty;
             description
               "Bit error rate alarm, defect";
           }
           leaf sonet-alarm-berr-sf {
             type empty;
             description
               "Bit error rate alarm, fault";
           }
           leaf sonet-alarm-lrdi {
             type empty;
             description
               "Line remote defect indicator alarm";
           }
           leaf sonet-alarm-prdi {
             type empty;
             description
               "Path remote defect indicator alarm";
           }
           leaf sonet-alarm-rei {
             type empty;
             description
               "Path remote error indicator alarm";
           }
           leaf sonet-alarm-uneq {
             type empty;
             description
               "Unequipped alarm";
           }
           leaf sonet-alarm-pmis {
             type empty;
             description
               "Path payload level mismatch alarm";
           }
           leaf sonet-alarm-loc {
             type empty;
             description
               "Loss of cell delineation alarm";
           }
           leaf sonet-alarm-vais {
             type empty;
             description
               "VT AIS alarm";
           }
           leaf sonet-alarm-vlop {
             type empty;
             description
               "VT loss of pointer alarm";
           }
           leaf sonet-alarm-vrdi {
             type empty;
             description
               "VT remote defect indicator alarm";
           }
           leaf sonet-alarm-vuneq {
             type empty;
             description
               "VT unequipped alarm";
           }
           leaf sonet-alarm-vmis {
             type empty;
             description
               "VT label mismatch alarm";
           }
           leaf sonet-alarm-vloc {
             type empty;
             description
               "VT loss of cell delineation alarm";
           }
           leaf sdh-alarm-lol {
             type empty;
             description
               "Loss of light alarm";
           }
           leaf sdh-alarm-pll {
             type empty;
             description
               "PLL lock alarm";
           }
           leaf sdh-alarm-lof {
             type empty;
             description
               "Loss of frame alarm";
           }
           leaf sdh-alarm-los {
             type empty;
             description
               "Loss of signal alarm";
           }
           leaf sdh-alarm-oof {
             type empty;
             description
               "Out of frame alarm";
           }
           leaf sdh-alarm-msais {
             type empty;
             description
               "Multiplex section AIS alarm";
           }
           leaf sdh-alarm-hpais {
             type empty;
             description
               "High order path AIS alarm";
           }
           leaf sdh-alarm-lop {
             type empty;
             description
               "Loss of pointer alarm";
           }
           leaf sdh-alarm-berr-sd {
             type empty;
             description
               "Bit error rate alarm, defect";
           }
           leaf sdh-alarm-berr-sf {
             type empty;
             description
               "Bit error rate alarm, fault";
           }
           leaf sdh-alarm-msferf {
             type empty;
             description
               "Multiplex section far-end remote failure alarm";
           }
           leaf sdh-alarm-hpferf {
             type empty;
             description
               "High order path far-end remote failure alarm";
           }
           leaf sdh-alarm-hpfebe {
             type empty;
             description
               "High order path far-end block error alarm";
           }
           leaf sdh-alarm-hpuneq {
             type empty;
             description
               "High order path unequipped alarm";
           }
           leaf sdh-alarm-hpplm {
             type empty;
             description
               "High order path payload level mismatch alarm";
           }
           leaf sdh-alarm-loc {
             type empty;
             description
               "Loss of cell delineation alarm";
           }
           leaf sdh-alarm-tuais {
             type empty;
             description
               "TU AIS alarm";
           }
           leaf sdh-alarm-tulop {
             type empty;
             description
               "TU loss of pointer alarm";
           }
           leaf sdh-alarm-turdi {
             type empty;
             description
               "TU remote defect indicator alarm";
           }
           leaf sdh-alarm-tuuneq {
             type empty;
             description
               "TU unequipped alarm";
           }
           leaf sdh-alarm-tumis {
             type empty;
             description
               "TU label mismatch error";
           }
           leaf sdh-alarm-tuloc {
             type empty;
             description
               "TU loss of cell delineation alarm";
           }
           leaf ds3-alarm-pll {
             type empty;
             description
               "PLL lock alarm";
           }
           leaf ds3-alarm-ais {
             type empty;
             description
               "AIS alarm";
           }
           leaf ds3-alarm-lof {
             type empty;
             description
               "Loss of frame alarm";
           }
           leaf ds3-alarm-los {
             type empty;
             description
               "Loss of signal alarm";
           }
           leaf ds3-alarm-lcv {
             type empty;
             description
               "Line code violation alarm";
           }
           leaf ds3-alarm-exz {
             type empty;
             description
               "Excessive zeros alarm";
           }
           leaf ds3-alarm-ferf {
             type empty;
             description
               "Far-end receive failure alarm";
           }
           leaf ds3-alarm-ylw {
             type empty;
             description
               "Yellow alarm";
           }
           leaf ds3-alarm-idle {
             type empty;
             description
               "Idle alarm";
           }
           leaf ds1-alarm-ais {
             type empty;
             description
               "AIS alarm";
           }
           leaf ds1-alarm-lof {
             type empty;
             description
               "Loss of frame alarm";
           }
           leaf ds1-alarm-los {
             type empty;
             description
               "Loss of signal alarm";
           }
           leaf ds1-alarm-ylw {
             type empty;
             description
               "Yellow alarm";
           }
           leaf ds1-alarm-crc-major {
             type empty;
             description
               "CRC errors crossed major threshold";
           }
           leaf ds1-alarm-crc-minor {
             type empty;
             description
               "CRC errors crossed minor threshold";
           }
           leaf dsl-alarm-lof {
             type empty;
             description
               "Loss of frame alarm";
           }
           leaf dsl-alarm-los {
             type empty;
             description
               "Loss of signal alarm";
           }
           leaf dsl-alarm-lom {
             type empty;
             description
               "Loss of multiframe alarm";
           }
           leaf dsl-alarm-locdi {
             type empty;
             description
               "Loss of cell delineation alarm for interleaved channel";
           }
           leaf dsl-alarm-locdni {
             type empty;
             description
               "Loss of cell delineation alarm for non-interleaved channel";
           }
           leaf dsl-alarm-lop {
             type empty;
             description
               "Loss of power alarm";
           }
           leaf dsl-alarm-far-lof {
             type empty;
             description
               "Far-end loss-of-frame alarm";
           }
           leaf dsl-alarm-far-los {
             type empty;
             description
               "Far-end loss-of-signal alarm";
           }
           leaf dsl-alarm-far-locdi {
             type empty;
             description
               "Far-end loss-of-cell-delineation alarm for interleaved 
               channel";
           }
           leaf dsl-alarm-far-locdni {
             type empty;
             description
               "Far-end loss-of-cell-delineation alarm for non-interleaved 
               channel";
           }
           leaf fibrechannel-alarm-link-down {
             type empty;
             description
               "Link alive failure";
           }
           leaf ethernet-alarm-link-down {
             type empty;
             description
               "Link alive failure";
           }
           leaf ethernet-alarm-an-not-supported {
             type empty;
             description
               "AN not supported";
           }
           leaf ethernet-alarm-link-local-fault {
             type empty;
             description
               "Link local fault";
           }
           leaf ethernet-alarm-link-remote-fault {
             type empty;
             description
               "Link remote fault";
           }
           leaf ethernet-alarm-link-local-degrade {
             type empty;
             description
               "Link local degrade";
           }
           leaf ethernet-alarm-link-remote-degrade {
             type empty;
             description
               "Link remote degrade";
           }
           leaf ethernet-alarm-lcdp {
             type empty;
             description
               "Loss of code-group delineation";
           }
           leaf isdn-alarm-los {
             type empty;
             description
               "Loss of signal alarm";
           }
           leaf isdn-alarm-lof {
             type empty;
             description
               "Loss of frame alarm";
           }
           leaf shdsl-alarm-losd {
             type empty;
             description
               "Loss of signal alarm";
           }
           leaf shdsl-alarm-losw {
             type empty;
             description
               "Loss of sync word alarm";
           }
           leaf shdsl-alarm-line1-losd {
             type empty;
             description
               "Loss of signal (line 1) alarm";
           }
           leaf shdsl-alarm-line1-losw {
             type empty;
             description
               "Loss of sync word (line 1) alarm";
           }
           leaf shdsl-alarm-line2-losd {
             type empty;
             description
               "Loss of signal (line 2) alarm";
           }
           leaf shdsl-alarm-line2-losw {
             type empty;
             description
               "Loss of sync word (line 2) alarm";
           }
           leaf shdsl-efm-alarm-losd {
             type empty;
             description
               "Loss of signal alarm";
           }
           leaf shdsl-efm-alarm-losw {
             type empty;
             description
               "Loss of sync word alarm";
           }
           leaf otn-alarm-los {
             type empty;
             description
               "Loss of signal alarm";
           }
           leaf otn-alarm-lof {
             type empty;
             description
               "Loss of frame alarm";
           }
           leaf otn-alarm-lom {
             type empty;
             description
               "Loss of multiframe alarm";
           }
           leaf otn-alarm-wavelength-lock {
             type empty;
             description
               "Loss of Wavelength Lock alarm";
           }
           leaf otn-alarm-otu-ais {
             type empty;
             description
               "OTU Alarm Indication Signal alarm";
           }
           leaf otn-alarm-otu-bdi {
             type empty;
             description
               "OTU Background Block Error alarm";
           }
           leaf otn-alarm-otu-ttim {
             type empty;
             description
               "OTU Trail Trace Identifier Mismatch alarm";
           }
           leaf otn-alarm-otu-iae {
             type empty;
             description
               "OTU Incoming Alignment alarm";
           }
           leaf otn-alarm-otu-sd {
             type empty;
             description
               "OTU Signal Degrade alarm";
           }
           leaf otn-alarm-otu-sf {
             type empty;
             description
               "OTU Signal Fail alarm";
           }
           leaf otn-alarm-otu-biae {
             type empty;
             description
               "OTU Backward Incoming Alignment alarm";
           }
           leaf otn-alarm-otu-tsf {
             type empty;
             description
               "OTU Trail Signal Fail alarm";
           }
           leaf otn-alarm-otu-ssf {
             type empty;
             description
               "OTU Server Signal Fail alarm";
           }
           leaf otn-alarm-otu-fec-excessive {
             type empty;
             description
               "OTU FEC Excessive alarm";
           }
           leaf otn-alarm-otu-fec-degraded {
             type empty;
             description
               "OTU FEC Degraded alarm";
           }
           leaf otn-alarm-otu-fe-fec-degraded {
             type empty;
             description
               "OTU FE FEC Degraded/Excessive alarm";
           }
           leaf otn-alarm-otu-threshold-bbe {
             type empty;
             description
               "OTU Background Block Error threshold alarm";
           }
           leaf otn-alarm-otu-threshold-es {
             type empty;
             description
               "OTU Errored Seconds threshold alarm";
           }
           leaf otn-alarm-otu-threshold-ses {
             type empty;
             description
               "OTU Severely Errored Seconds threshold alarm";
           }
           leaf otn-alarm-otu-threshold-uas {
             type empty;
             description
               "OTU Unavailable Seconds threshold alarm";
           }
           leaf otn-alarm-odu-ais {
             type empty;
             description
               "ODU  Alarm Indiaction Signal alarm";
           }
           leaf otn-alarm-odu-oci {
             type empty;
             description
               "ODU Open Connection Indication alarm";
           }
           leaf otn-alarm-odu-lck {
             type empty;
             description
               "ODU Locked alarm";
           }
           leaf otn-alarm-odu-bdi {
             type empty;
             description
               "ODU Backward Defect Indication alarm";
           }
           leaf otn-alarm-odu-ttim {
             type empty;
             description
               "ODU Trail Trace Identifier Mismatch alarm";
           }
           leaf otn-alarm-odu-sd {
             type empty;
             description
               "ODU Signal Degrade alarm";
           }
           leaf otn-alarm-odu-sf {
             type empty;
             description
               "ODU Signal Fail alarm";
           }
           leaf otn-alarm-odu-iae {
             type empty;
             description
               "ODU Incoming Alignment alarm";
           }
           leaf otn-alarm-odu-ltc {
             type empty;
             description
               "ODU Loss of Tandem Connection alarm";
           }
           leaf otn-alarm-odu-csf {
             type empty;
             description
               "ODU Client Signal Fail alarm";
           }
           leaf otn-alarm-odu-tsf {
             type empty;
             description
               "ODU Trail Signal Fail alarm";
           }
           leaf otn-alarm-odu-ssf {
             type empty;
             description
               "ODU Server Signal Fail alarm";
           }
           leaf otn-alarm-odu-rx-aps-change {
             type empty;
             description
               "ODU Rx Aps Change alarm";
           }
           leaf otn-alarm-odu-threshold-bbe {
             type empty;
             description
               "ODU Background Block Error threshold alarm";
           }
           leaf otn-alarm-odu-threshold-es {
             type empty;
             description
               "ODU Errored Seconds threshold alarm";
           }
           leaf otn-alarm-odu-threshold-ses {
             type empty;
             description
               "ODU Severely Errored Seconds threshold alarm";
           }
           leaf otn-alarm-odu-threshold-uas {
             type empty;
             description
               "ODU Unavailable Seconds threshold alarm";
           }
           leaf otn-alarm-opu-pmi {
             type empty;
             description
               "OPU Payload Mismatch alarm";
           }
           leaf otn-alarm-pre-fec-sd {
             type empty;
             description
               "Pre-FEC SD alarm";
           }
           leaf otn-alarm-fe-pre-fec-sd {
             type empty;
             description
               "Far end pre-FEC SD alarm";
           }
           leaf optics-alarms-mod-fault {
             type empty;
             description
               "Module Fault alarm";
           }
           leaf optics-alarms-lol {
             type empty;
             description
               "Loss of Lock alarm";
           }
           leaf optics-alarms-los {
             type empty;
             description
               "Loss of Signal alarms";
           }
           leaf optics-alarms-lof {
             type empty;
             description
               "Loss of frame alarm";
           }
           leaf optics-alarms-lom {
             type empty;
             description
               "Loss of multi-frame alarm";
           }
           leaf optics-alarms-otu-bdi {
             type empty;
             description
               "Backward defect indiacation alarm";
           }
           leaf optics-alarms-rmsf {
             type empty;
             description
               "Rx Modem sysnc fault alarm";
           }
           leaf optics-alarms-rmlol {
             type empty;
             description
               "Rx Modem loss of lock alarm";
           }
           leaf optics-alarms-rloa {
             type empty;
             description
               "Rx loss of alignment alarm";
           }
           leaf optics-alarms-mbclf {
             type empty;
             description
               "Modulator Bias control loop fail alarm";
           }
           leaf optics-alarms-itlaf {
             type empty;
             description
               "ITLA Fault alarm";
           }
           leaf optics-alarms-daccf {
             type empty;
             description
               "DAC Calibration Fault alarm";
           }
           leaf optics-alarms-adccf {
             type empty;
             description
               "ADC Calibration Fault alarm";
           }
           leaf optics-alarms-fec-degrade {
             type empty;
             description
               "FEC Degrade alarm";
           }
           leaf optics-alarms-fec-excessive {
             type empty;
             description
               "FEC Excessive alarm";
           }
           leaf optics-alarms-fe-fec-degrade {
             type empty;
             description
               "Far-end FEC Degrade alarm";
           }
           leaf optics-alarms-fe-fec-excessive {
             type empty;
             description
               "Far-end FEC Excessive alarm";
           }
           leaf ima-alarm-startup-fe {
             type empty;
             description
               "IMA group startup far-end alarm";
           }
           leaf ima-alarm-config-abort {
             type empty;
             description
               "IMA group config abort alarm";
           }
           leaf ima-alarm-config-abort-fe {
             type empty;
             description
               "IMA group config abort far-end alarm";
           }
           leaf ima-alarm-insufficient-links {
             type empty;
             description
               "IMA group insufficient links alarm";
           }
           leaf ima-alarm-insufficient-links-fe {
             type empty;
             description
               "IMA group insufficient links far-end alarm";
           }
           leaf ima-alarm-blocked {
             type empty;
             description
               "IMA group blocked alarm";
           }
           leaf ima-alarm-blocked-fe {
             type empty;
             description
               "IMA group blocked far-end alarm";
           }
           leaf ima-alarm-timing-mismatch {
             type empty;
             description
               "IMA group timing mismatch alarm";
           }
           leaf ima-alarm-version-mismatch {
             type empty;
             description
               "IMA group version mismatch alarm";
           }
           leaf ima-alarm-lif {
             type empty;
             description
               "IMA link loss of IMA frame alarm";
           }
           leaf ima-alarm-lods {
             type empty;
             description
               "IMA link out of delay synchronization alarm";
           }
           leaf ima-alarm-rdi {
             type empty;
             description
               "IMA link remote defect indicator alarm";
           }
           leaf ima-alarm-tx-misconnected {
             type empty;
             description
               "IMA link tx misconnected alarm";
           }
           leaf ima-alarm-rx-misconnected {
             type empty;
             description
               "IMA link rx misconnected alarm";
           }
           leaf ima-alarm-fault {
             type empty;
             description
               "IMA link fault alarm";
           }
           leaf ima-alarm-tx-unusable-fe {
             type empty;
             description
               "IMA link Tx unusable far-end alarm";
           }
           leaf ima-alarm-rx-unusable-fe {
             type empty;
             description
               "IMA link Tx unusable far-end alarm";
           }
           leaf generic-value {
             type int32;
             description
               "Hexadecimal value of unknown flag bits";
           }
         }
       }
       container media-state-information {
         leaf media-type {
           type string;
           description
             "Type of media this information is for";
         }
         list media-state {
           leaf media-state-name {
             type string;
             description
               "Media state category";
           }
           leaf media-state-state {
             type string;
             description
               "Current state for this category";
           }
         }
       }
       container sonet-errors {
         list media-alarm {
           leaf media-alarm-name {
             type string;
           }
           leaf media-alarm-count {
             type int32;
           }
         }
       }
       container sonet-physical-information {
         list media-alarm {
           leaf media-alarm-name {
             type string;
           }
           leaf media-alarm-seconds {
             type int32;
           }
           leaf media-alarm-count {
             type int32;
           }
           leaf media-alarm-state {
             type string;
           }
         }
       }
       container sonet-section-information {
         list media-alarm {
           leaf media-alarm-name {
             type string;
           }
           leaf media-alarm-seconds {
             type int32;
           }
           leaf media-alarm-count {
             type int32;
           }
           leaf media-alarm-state {
             type string;
           }
         }
       }
       container sonet-line-information {
         list media-alarm {
           leaf media-alarm-name {
             type string;
           }
           leaf media-alarm-seconds {
             type int32;
           }
           leaf media-alarm-count {
             type int32;
           }
           leaf media-alarm-state {
             type string;
           }
         }
       }
       container sonet-path-information {
         list media-alarm {
           leaf media-alarm-name {
             type string;
           }
           leaf media-alarm-seconds {
             type int32;
           }
           leaf media-alarm-count {
             type int32;
           }
           leaf media-alarm-state {
             type string;
           }
         }
       }
       container sonet-payload-pointer-information {
         leaf sonet-payload-pointer-curptr {
           type string;
           description
             "Value of the SONET/SDH payload pointer, derived from the H1 
             and H2 overhead bytes";
         }
         leaf sonet-payload-pointer-ptrinc-count {
           type string;
           description
             "Number of times the value of the SONET/SDH payload pointer had
             positive justification";
         }
         leaf sonet-payload-pointer-ptrdec-count {
           type string;
           description
             "Number of times the value of the SONET/SDH payload pointer had
             negative justification";
         }
         leaf sonet-payload-pointer-newptr-ndf-count {
           type string;
           description
             "Number of times a new payload pointer was created with the New
             Data Found flag set";
         }
       }
       container sonet-vt-information {
         list media-alarm {
           leaf media-alarm-name {
             type string;
           }
           leaf media-alarm-seconds {
             type int32;
           }
           leaf media-alarm-count {
             type int32;
           }
           leaf media-alarm-state {
             type string;
           }
         }
       }
       container otn-errors {
         list media-alarm {
           leaf media-alarm-name {
             type string;
           }
           leaf media-alarm-count {
             type int32;
           }
         }
       }
       container otn-fec-statistics {
         leaf fec-corrected-errors {
           type int32;
         }
         leaf fec-valid-time {
           type int32;
         }
         leaf fec-corrected-error-ratio {
           type int32;
         }
         leaf fec-uncorrected-words {
           type int32;
         }
       }
       container otn-fec-alarms {
         description
           "OTN degraded and excessive FEC error rates";
         list media-alarm {
           leaf media-alarm-name {
             type string;
           }
           leaf media-alarm-seconds {
             type int32;
           }
           leaf media-alarm-count {
             type int32;
           }
           leaf media-alarm-state {
             type string;
           }
         }
       }
       container otn-fec-mode {
         leaf fec-mode {
           type string;
           description
             "Optics FEC mode";
         }
       }
       container otn-otn-mode {
         leaf otn-mode {
           type string;
         }
       }
       container otn-otn-rate {
         leaf otn-rate {
           type string;
         }
       }
       container otn-otn-loopback {
         leaf otn-loopback {
           type string;
         }
       }
       container otn-local-loopback {
         leaf local-loopback {
           type string;
         }
       }
       container otn-payload-prbs {
         leaf payload-prbs {
           type string;
         }
       }
       container otn-laser-enable {
         leaf laser-enable {
           type string;
           description
             "Optics laser status";
         }
       }
       container media-information {
         description
           "Information about media alarms";
         leaf media-type {
           type string;
           description
             "Type of media this information is for";
         }
         list media-alarm {
           leaf media-alarm-name {
             type string;
           }
           leaf media-alarm-count {
             type int32;
           }
           leaf media-alarm-seconds {
             type int32;
           }
           leaf media-alarm-state {
             type string;
           }
           leaf ce-counter-name {
             type string;
             description
               "Circuit Emulation counter information";
           }
           leaf ce-counter-packets {
             type int32;
             description
               "Circuit Emulation number of packets";
           }
           leaf ce-counter-bytes {
             type int32;
             description
               "Circuit Emulation number of bytes";
           }
           leaf ce-counter-count {
             type int32;
             description
               "Circuit Emulation number of event occurrences";
           }
         }
         leaf ds1-timeslots {
           type string;
         }
         leaf ds1-line-encoding {
           type string;
         }
         leaf ds1-byte-encoding {
           type string;
         }
         leaf ds1-data-inversion {
           type string;
         }
         leaf idle-cycle-flag {
           type string;
         }
         leaf start-end-flag {
           type string;
         }
         leaf ds0-byte-encoding {
           type string;
         }
         leaf ds0-data-inversion {
           type string;
         }
         leaf e3-data-inversion {
           type string;
         }
         leaf ds1-buildout {
           type string;
           description
             "Number of feet";
         }
       }
       container ethernet-pcs-statistics {
         description
           "Ethernet PCS statistics";
         leaf bit-error-seconds {
           type int32;
           description
             "Bit error duration";
         }
         leaf errored-blocks-seconds {
           type int32;
           description
             "Errored blocks duration";
         }
       }
       container link-degrade-information {
         leaf lnk-degrd-mon {
           type string;
           description
             "Link degrade feature is enable/disable for this interface";
         }
         leaf lnk-degrd-set-thr {
           type uint32;
           description
             "BER At Which Link Considered Improved";
         }
         leaf lnk-degrd-clr-thr {
           type uint32;
           description
             "BER At Which Link Considered Degraded";
         }
         leaf lnk-degrd-war-set-thr {
           type uint32;
           description
             "BER At Which Warning Will Be Trigged";
         }
         leaf lnk-degrd-war-clr-thr {
           type uint32;
           description
             "BER At Which Warning Will Be Cleared";
         }
         leaf lnk-degrd-est-ber {
           type uint32;
           description
             "Link Degrade Estimated BER";
         }
         leaf lnk-degrd-seconds {
           type uint64;
           description
             "Link Degrade ";
         }
         leaf lnk-degrd-count {
           type uint64;
           description
             "Link Degrade ";
         }
         leaf lnk-degrd-state {
           type string;
           description
             "Link Degrade ";
         }
       }
       container ethernet-fec-mode {
         description
           "Ethernet FEC Mode";
         leaf enabled_fec_mode {
           type string;
           description
             "Enabled FEC mode: <NONE/FEC74/FEC91/FEC108/FEC161>";
         }
         leaf fec_codeword_size {
           type uint32;
           description
             "FEC Codeword size";
         }
         leaf fec_codeword_rate {
           type jt:unsigned-float;
           description
             "FEC Codeword rate";
         }
       }
       container ethernet-fec-statistics {
         description
           "Ethernet FEC statistics";
         leaf fec_ccw_count {
           type int32;
           description
             "FEC Corrected Error Count";
         }
         leaf fec_nccw_count {
           type int32;
           description
             "FEC Uncorrected Error Count";
         }
         leaf fec_ccw_error_rate {
           type int32;
           description
             "FEC Corrected Error Rate (errors/sec)";
         }
         leaf fec_nccw_error_rate {
           type int32;
           description
             "FEC Uncorrected Error Rate (errors/sec)";
         }
         leaf pre-fec-ber {
           type jt:unsigned-float;
           description
             "PRE_FEC BER";
         }
       }
       container ethernet-fechistogram-statistics {
         description
           "Ethernet Fec Histogram stats";
         leaf bin-num {
           type int32;
           description
             "Bin number";
         }
         leaf sym-live-err {
           type int32;
           description
             "Sym Live Err";
         }
         leaf sym-harvest-err {
           type int32;
           description
             "Sym harvested Err";
         }
         leaf sym-harvest-last-update {
           type string;
           description
             "Sym harvested last update";
         }
       }
       container ctle {
         description
           "Ctle ";
         leaf ctle_value {
           type int32;
           description
             "Ctle value";
         }
       }
       container pre-emphasis {
         description
           "Pre-emphasis ";
         leaf pre_emphasis_value {
           type int32;
           description
             "Pre-emphasis value";
         }
       }
       container differential-amplitude {
         description
           "Differential-amplitude ";
         leaf differential_amplitude_value {
           type int32;
           description
             "Differential-amplitude value";
         }
       }
       container ethernet-mac-statistics {
         description
           "Ethernet MAC statistics";
         leaf input-bytes {
           type int32;
         }
         leaf input-packets {
           type uint64;
         }
         leaf output-bytes {
           type int32;
         }
         leaf output-packets {
           type uint64;
         }
         leaf input-unicasts {
           type int32;
         }
         leaf output-unicasts {
           type int32;
         }
         leaf input-broadcasts {
           type int32;
         }
         leaf output-broadcasts {
           type int32;
         }
         leaf input-multicasts {
           type int32;
         }
         leaf output-multicasts {
           type int32;
         }
         leaf input-crc-errors {
           type int32;
         }
         leaf output-crc-errors {
           type int32;
         }
         leaf input-fifo-errors {
           type int32;
         }
         leaf output-fifo-errors {
           type int32;
         }
         leaf input-dma-errors {
           type int32;
         }
         leaf output-dma-errors {
           type int32;
         }
         leaf input-mac-control-frames {
           type int32;
         }
         leaf output-mac-control-frames {
           type int32;
         }
         leaf input-mac-pause-frames {
           type int32;
         }
         leaf output-mac-pause-frames {
           type int32;
         }
         leaf input-oversized-frames {
           type int32;
         }
         leaf input-jabber-frames {
           type int32;
         }
         leaf input-fragment-frames {
           type int32;
         }
         leaf input-vlan-tagged-frames {
           type int32;
         }
         leaf input-code-violations {
           type int32;
         }
         leaf input-total-errors {
           type int32;
         }
         leaf output-total-errors {
           type int32;
         }
         leaf input-policer-frame-drops {
           type int32;
         }
         leaf input-policer-byte-drops {
           type int32;
         }
       }
       container sriov-vf-statistics {
         description
           "SRIOV VF statistics";
         leaf vf-number {
           type uint32;
         }
         leaf pci-address {
           type string;
         }
         leaf mapped-to {
           type string;
         }
         leaf input-bytes {
           type int32;
         }
         leaf input-packets {
           type uint64;
         }
         leaf output-bytes {
           type int32;
         }
         leaf output-packets {
           type uint64;
         }
         leaf mc-packets {
           type int32;
         }
       }
       container ethernet-prbs-mode {
         description
           "PRBS Mode";
         leaf prbs-mode {
           type string;
           description
             "PRBS Mode: <Enabled/Disabled>";
         }
       }
       container ethernet-prbs-pattern {
         description
           "PRBS Pattern";
         leaf prbs-pattern {
           type int32;
           description
             "PRBS Pattern";
         }
       }
       container ethernet-prbs-statistics {
         description
           "Ethernet PRBS statistics";
         leaf prbs-lane {
           type int32;
           description
             "PRBS Lane";
         }
         leaf prbs-error-count {
           type int32;
           description
             "PRBS Error Count";
         }
         leaf prbs-loop-count {
           type int32;
           description
             "PRBS Loop Count";
         }
         leaf prbs-ber-sec {
           type int32;
           description
             "PRBS BER seconds";
         }
         leaf prbs-bits {
           type int32;
           description
             "PRBS Bits";
         }
         leaf prbs-run-sec {
           type int32;
           description
             "PRBS Run seconds";
         }
         leaf prbs-state {
           type string;
           description
             "PRBS State";
         }
         leaf prbs-ber-rate {
           type string;
           description
             "PRBS BER rate";
         }
       }
       container smart-sfp-configurable-type {
         leaf smart-sfp-tdm-management {
           type string;
         }
         leaf smart-sfp-mac {
           type jt:mac-addr;
         }
       }
       container smart-sfp-type {
         leaf smart-sfp-module-type {
           type string;
         }
         leaf smart-sfp-present {
           type string;
         }
       }
       container smart-sfp-config {
         leaf tdm-loopback {
           type string;
         }
         leaf dmac-check-enable {
           type string;
         }
         leaf encap-ecid {
           type int32;
         }
         leaf decap-ecid {
           type int32;
         }
         leaf vlan-id-1 {
           type int32;
         }
         leaf vlan-id-2 {
           type int32;
         }
         leaf mode {
           type string;
         }
         leaf chan-dmac {
           type jt:mac-addr;
         }
         leaf ces-psn-port-channel-id-state {
           type string;
         }
         leaf tdm-intf-signal {
           type string;
         }
       }
       list smart-sfp-channel-config {
         key "channel-num";
         description
           "Smart SFP channel config";
         leaf channel-num {
           type uint32;
           description
             "Channel number";
         }
         leaf channel-klm {
           type string;
           description
             "K (TUG3), L (TUG2), M (TU-12/VC-12/E1) Mapping";
         }
         leaf encap-ecid {
           type int32;
         }
         leaf encap-rtp-freq {
           type string;
         }
         leaf decap-ecid {
           type int32;
         }
         leaf decap-timing {
           type string;
         }
         leaf decap-rtp-freq {
           type string;
         }
         leaf ces-psn-mode {
           type string;
         }
         leaf ces-psn-dmac {
           type jt:mac-addr;
         }
         leaf ces-psn-vlan-1 {
           type int32;
         }
         leaf ces-psn-vlan-2 {
           type int32;
         }
         leaf encap-rtphdr-insert {
           type string;
         }
         leaf decap-rtphdr {
           type string;
         }
       }
       container smart-sfp-oc3-statistics {
         leaf fcs-error-count {
           type uint32;
         }
         leaf sec-sefs {
           type uint32;
         }
         leaf sec-es {
           type uint32;
         }
         leaf sec-es-min15 {
           type uint32;
         }
         leaf sec-ses {
           type uint32;
         }
         leaf sec-ses-min15 {
           type uint32;
         }
         leaf sec-cv {
           type uint32;
         }
         leaf sec-cv-min15 {
           type uint32;
         }
         leaf line-es {
           type uint32;
         }
         leaf line-es-min15 {
           type uint32;
         }
         leaf line-ses {
           type uint32;
         }
         leaf line-ses-min15 {
           type uint32;
         }
         leaf line-cv {
           type uint32;
         }
         leaf line-cv-min15 {
           type uint32;
         }
         leaf line-uas {
           type uint32;
         }
         leaf line-uas-min15 {
           type uint32;
         }
         leaf path-es {
           type uint32;
         }
         leaf path-es-min15 {
           type uint32;
         }
         leaf path-ses {
           type uint32;
         }
         leaf path-ses-min15 {
           type uint32;
         }
         leaf path-cv {
           type uint32;
         }
         leaf path-cv-min15 {
           type uint32;
         }
         leaf path-uas {
           type uint32;
         }
         leaf path-uas-min15 {
           type uint32;
         }
       }
       container smart-sfp-e1t1-statistics {
         leaf e1t1-es {
           type uint32;
         }
         leaf e1t1-es-min15 {
           type uint32;
         }
         leaf e1t1-ses {
           type uint32;
         }
         leaf e1t1-ses-min15 {
           type uint32;
         }
         leaf e1t1-uas {
           type uint32;
         }
         leaf e1t1-uas-min15 {
           type uint32;
         }
         leaf e1t1-bes {
           type uint32;
         }
         leaf e1t1-bes-min15 {
           type uint32;
         }
         leaf e1t1-les {
           type uint32;
         }
         leaf e1t1-les-min15 {
           type uint32;
         }
         leaf e1t1-pes {
           type uint32;
         }
         leaf e1t1-pes-min15 {
           type uint32;
         }
         leaf e1t1-psess {
           type uint32;
         }
         leaf e1t1-psess-min15 {
           type uint32;
         }
         leaf e1t1-ces {
           type uint32;
         }
         leaf e1t1-ces-min15 {
           type uint32;
         }
         leaf e1t1-cses {
           type uint32;
         }
         leaf e1t1-cses-min15 {
           type uint32;
         }
         leaf e1t1-sefs {
           type uint32;
         }
         leaf e1t1-sefs-min15 {
           type uint32;
         }
       }
       container smart-sfp-e3t3-statistics {
         leaf e3t3-les {
           type uint32;
         }
         leaf e3t3-les-min15 {
           type uint32;
         }
         leaf e3t3-pes {
           type uint32;
         }
         leaf e3t3-pes-min15 {
           type uint32;
         }
         leaf e3t3-psess {
           type uint32;
         }
         leaf e3t3-psess-min15 {
           type uint32;
         }
         leaf e3t3-ces {
           type uint32;
         }
         leaf e3t3-ces-min15 {
           type uint32;
         }
         leaf e3t3-cses {
           type uint32;
         }
         leaf e3t3-cses-min15 {
           type uint32;
         }
         leaf e3t3-sefs {
           type uint32;
         }
         leaf e3t3-sefs-min15 {
           type uint32;
         }
         leaf e3t3-uas {
           type uint32;
         }
         leaf e3t3-uas-min15 {
           type uint32;
         }
       }
       container fibrechannel-port-flow-control {
         description
           "Fibre Channel interface flow control";
         leaf fibrechannel-port-flow-control-mode {
           type string;
         }
         list fibrechannel-port-flow-control-credits {
           description
             "Generic flow control credits";
           leaf fibrechannel-port-flow-control-credits-subject {
             type string;
           }
           leaf fibrechannel-port-flow-control-credits-assigned {
             type uint64;
           }
           leaf fibrechannel-port-flow-control-credits-available {
             type uint64;
           }
         }
       }
       container fibrechannel-mac-statistics {
         description
           "Fibre Channel MAC statistics";
         container fibrechannel-mac-statistics-generic {
           leaf link-failures {
             type uint64;
           }
           leaf loss-of-sync {
             type uint64;
           }
           leaf loss-of-signal {
             type uint64;
           }
           leaf sw-link-resets {
             type uint64;
           }
           leaf buffer-to-buffer-credit-recovery-lost-frames {
             type uint64;
           }
           leaf buffer-to-buffer-credit-recovery-lost-rrdys {
             type uint64;
           }
         }
         container fibrechannel-mac-statistics-received {
           leaf rx-class-2-frames {
             type uint64;
           }
           leaf rx-class-2-octets {
             type uint64;
           }
           leaf rx-class-3-frames {
             type uint64;
           }
           leaf rx-class-3-octets {
             type uint64;
           }
           leaf rx-class-f-frames {
             type uint64;
           }
           leaf rx-class-f-octets {
             type uint64;
           }
           leaf class-2-discards {
             type uint64;
           }
           leaf class-3-discards {
             type uint64;
           }
           leaf class-f-discards {
             type uint64;
           }
           leaf rx-frames-too-long {
             type uint64;
           }
           leaf rx-frames-too-short {
             type uint64;
           }
           leaf rx-missing-eof {
             type uint64;
           }
           leaf rx-invalid-crcs {
             type uint64;
           }
           leaf rx-link-resets {
             type uint64;
           }
           leaf rx-link-reset-responses {
             type uint64;
           }
           leaf rx-offlines {
             type uint64;
           }
           leaf rx-not-operationals {
             type uint64;
           }
           leaf rx-invalid-tx-words {
             type uint64;
           }
           leaf rx-encoding-disparity-errors {
             type uint64;
           }
           leaf rx-delimiter-errors {
             type uint64;
           }
           leaf rx-input-buffers-full {
             type uint64;
           }
           leaf rx-invalid-ordered-sets {
             type uint64;
           }
           leaf rx-prim-seq-protocol-errors {
             type uint64;
           }
           leaf rx-other-errors {
             type uint64;
           }
         }
         container fibrechannel-mac-statistics-transmitted {
           leaf tx-class-2-frames {
             type uint64;
           }
           leaf tx-class-2-octets {
             type uint64;
           }
           leaf tx-class-3-frames {
             type uint64;
           }
           leaf tx-class-3-octets {
             type uint64;
           }
           leaf tx-class-f-frames {
             type uint64;
           }
           leaf tx-class-f-octets {
             type uint64;
           }
           leaf tx-link-resets {
             type uint64;
           }
           leaf tx-link-reset-responses {
             type uint64;
           }
           leaf tx-offlines {
             type uint64;
           }
           leaf tx-not-operationals {
             type uint64;
           }
           leaf tx-bb-credit-zeroes {
             type uint64;
           }
           leaf tx-other-errors {
             type uint64;
           }
         }
       }
       container ethernet-filter-statistics {
         description
           "Ethernet filter statistics";
         leaf input-reject-count {
           type int32;
         }
         leaf output-packet-pad-count {
           type int32;
         }
         leaf output-packet-error-count {
           type int32;
         }
         leaf input-packets {
           type uint64;
         }
         leaf input-reject-destination-address-count {
           type int32;
         }
         leaf input-reject-source-address-count {
           type int32;
         }
         leaf output-packets {
           type uint64;
         }
         leaf cam-destination-filter-count {
           type int32;
         }
         leaf cam-source-filter-count {
           type int32;
         }
       }
       container ethernet-autonegotiation {
         description
           "Ethernet autonegotiation information";
         leaf autonegotiation-status {
           type string;
         }
         leaf link-partner-duplexity {
           type string;
         }
         leaf flow-control {
           type string;
         }
         leaf link-partner-status {
           type string;
           description
             "Auto-negotiation status of link partner";
         }
         leaf link-partner-speed {
           type string;
           description
             "Link partner speed";
         }
         leaf link-partner-reason {
           type string;
           description
             "Reason link partner is down";
         }
         container local-info {
           description
             "Auto-negotiation status of local partner";
           leaf local-flow-control {
             type string;
             description
               "Local interface flow control type";
           }
           leaf local-flow-control-tx {
             type string;
             description
               "Local interface flow control tx type";
           }
           leaf local-flow-control-rx {
             type string;
             description
               "Local interface flow control rx type";
           }
           leaf local-remote-fault {
             type string;
             description
               "Local interface remote fault type";
           }
           leaf local-link-speed {
             type string;
             description
               "Local link speed";
           }
           leaf local-link-duplexity {
             type string;
           }
         }
       }
       container mac-database {
         leaf number-of-mac-record {
           type int32;
         }
         list mac-record {
           leaf mac-address {
             type jt:mac-addr;
           }
           leaf receive-frames {
             type int32;
           }
           leaf receive-bytes {
             type int32;
           }
           leaf transmit-frames {
             type int32;
           }
           leaf transmit-bytes {
             type int32;
           }
         }
       }
       container dsl-information {
         description
           "Operational information and statistics for ADSL interfaces";
         leaf dsl-line-status {
           type string;
           description
             "Status of modem";
         }
         leaf dsl-line-operating-mode {
           type string;
           description
             "Line type of digital subscriber line";
         }
         leaf dsl-line-type {
           type string;
           description
             "Line type of digital subscriber line";
         }
         leaf adsl-annex-type {
           type string;
           description
             "Type of ADSL annex";
         }
         leaf adsl-last-fail-code {
           type string;
           description
             "Reason for the last line-open failure";
         }
         leaf adsl-subfunction {
           type int32;
           description
             "Specified analog front-end chip and discrete front end";
         }
         leaf adsl-seconds-in-showtime {
           type int32;
           description
             "Number of seconds the ADSL connection is in showtime state";
         }
         container dsl-chipset-information {
           leaf atu-r-country-code {
             type int32;
             description
               "Country code for ATU-R chipset vendor";
           }
           leaf atu-c-country-code {
             type int32;
             description
               "Country code for ATU-C chipset vendor";
           }
           leaf atu-r-vendor-id {
             type string;
             description
               "ATU-R ITU chipset vendor ID";
           }
           leaf atu-c-vendor-id {
             type string;
             description
               "ATU-C ITU chipset vendor ID";
           }
           leaf atu-r-vendor-specific {
             type int32;
             description
               "ATU-R vendor-specific data";
           }
           leaf atu-c-vendor-specific {
             type int32;
             description
               "ATU-C vendor-specific data";
           }
         }
         container dsl-statistics {
           leaf near-end-attainable-bitrate {
             type int32;
             description
               "Near-end attainable bit rate";
           }
           leaf far-end-attainable-bitrate {
             type int32;
             description
               "Far-end attainable bit rate";
           }
           leaf near-end-attenuation {
             type string;
             description
               "Near-end attenuation";
           }
           leaf far-end-attenuation {
             type string;
             description
               "Far-end attenuation";
           }
           leaf near-end-capacity-used {
             type int32;
             description
               "Near-end capacity used";
           }
           leaf far-end-capacity-used {
             type int32;
             description
               "Far-end capacity used";
           }
           leaf near-end-noise-margin {
             type string;
             description
               "Near-end noise margin";
           }
           leaf far-end-noise-margin {
             type string;
             description
               "Far-end noise margin";
           }
           leaf near-end-output-power {
             type string;
             description
               "Near-end output power";
           }
           leaf far-end-output-power {
             type string;
             description
               "Far-end output power";
           }
           leaf near-end-interleaved-bitrate {
             type int32;
             description
               "Near-end interleaved bit rate";
           }
           leaf near-end-fast-bitrate {
             type int32;
             description
               "Near-end fast bit rate";
           }
           leaf far-end-interleaved-bitrate {
             type int32;
             description
               "Far-end interleaved bit rate";
           }
           leaf far-end-fast-bitrate {
             type int32;
             description
               "Far-end fast bit rate";
           }
           leaf near-end-interleaved-crc {
             type int32;
             description
               "Near-end interleaved cyclic redundancy check correction";
           }
           leaf near-end-fast-crc {
             type int32;
             description
               "Near-end fast cyclic redundancy check correction";
           }
           leaf far-end-interleaved-crc {
             type int32;
             description
               "Far-end interleaved cyclic redundancy check correction";
           }
           leaf far-end-fast-crc {
             type int32;
             description
               "Far-end fast cyclic redundancy check";
           }
           leaf near-end-interleaved-fec {
             type int32;
             description
               "Near-end interleaved footer error correction";
           }
           leaf near-end-fast-fec {
             type int32;
             description
               "Near-end fast footer error correction";
           }
           leaf far-end-interleaved-fec {
             type int32;
             description
               "Far-end interleaved footer error correction";
           }
           leaf far-end-fast-fec {
             type int32;
             description
               "Far-end fast footer error correction";
           }
           leaf near-end-interleaved-hec {
             type int32;
             description
               "Near-end interleaved header error correction";
           }
           leaf near-end-fast-hec {
             type int32;
             description
               "Near-end fast header error correction";
           }
           leaf far-end-interleaved-hec {
             type int32;
             description
               "Far-end interleaved header error correction";
           }
           leaf far-end-fast-hec {
             type int32;
             description
               "Far-end fast header error correction";
           }
           leaf near-end-interleaved-rx-cells {
             type int32;
             description
               "Near-end interleaved receiver cells";
           }
           leaf near-end-fast-rx-cells {
             type int32;
             description
               "Near-end fast receiver cells";
           }
           leaf near-end-interleaved-tx-cells {
             type int32;
             description
               "Near-end interleaved transmitter cells";
           }
           leaf near-end-fast-tx-cells {
             type int32;
             description
               "Near-end fast transmitter cells";
           }
           leaf interleaved-rx-cells {
             type int32;
             description
               "Interleaved receiver cells";
           }
           leaf fast-rx-cells {
             type int32;
             description
               "Fast receiver cells";
           }
           leaf interleaved-tx-cells {
             type int32;
             description
               "Interleaved transmitter cells";
           }
           leaf fast-tx-cells {
             type int32;
             description
               "Fast transmitter cells";
           }
         }
       }
       container vdsl-information {
         description
           "Operational information and statistics for VDSL interfaces";
         leaf vdsl-line-status {
           type string;
           description
             "Status of modem";
         }
         leaf vdsl-line-profile-type {
           type string;
           description
             "Line type of digital subscriber line";
         }
         leaf vdsl-line-type {
           type string;
           description
             "Line type of digital subscriber line";
         }
         leaf vdsl-annex-type {
           type string;
           description
             "Type of VDSL annex";
         }
         leaf vdsl-last-fail-code {
           type string;
           description
             "Reason for the last line-open failure";
         }
         leaf vdsl-subfunction {
           type int32;
           description
             "Specified analog front-end chip and discrete front end";
         }
         leaf vdsl-seconds-in-showtime {
           type int32;
           description
             "Number of seconds the VDSL connection is in showtime state";
         }
         container vdsl-chipset-information {
           leaf vtu-r-country-code {
             type int32;
             description
               "Country code for VTU-R chipset vendor";
           }
           leaf vtu-c-country-code {
             type int32;
             description
               "Country code for VTU-C chipset vendor";
           }
           leaf vtu-r-vendor-id {
             type string;
             description
               "VTU-R ITU chipset vendor ID";
           }
           leaf vtu-c-vendor-id {
             type string;
             description
               "VTU-C ITU chipset vendor ID";
           }
           leaf vtu-r-vendor-specific {
             type int32;
             description
               "VTU-R vendor-specific data";
           }
           leaf vtu-c-vendor-specific {
             type int32;
             description
               "VTU-C vendor-specific data";
           }
         }
         container vdsl-statistics {
           leaf vdsl-near-end-attainable-bitrate {
             type int32;
             description
               "Near end attainable bit rate ";
           }
           leaf vdsl-far-end-attainable-bitrate {
             type int32;
             description
               "Far-end attainable bit rate";
           }
           leaf vdsl-near-end-attenuation {
             type string;
             description
               "Near-end attenuation";
           }
           leaf vdsl-far-end-attenuation {
             type string;
             description
               "Far-end attenuation";
           }
           leaf vdsl-near-end-capacity-used {
             type int32;
             description
               "Near-end capacity used";
           }
           leaf vdsl-far-end-capacity-used {
             type int32;
             description
               "Far-end capacity used";
           }
           leaf vdsl-near-end-noise-margin {
             type string;
             description
               "Near-end noise margin";
           }
           leaf vdsl-far-end-noise-margin {
             type string;
             description
               "Far-end noise margin";
           }
           leaf vdsl-near-end-output-power {
             type string;
             description
               "Near-end output power";
           }
           leaf vdsl-far-end-output-power {
             type string;
             description
               "Far-end output power";
           }
           leaf vdsl-near-end-interleaved-bitrate {
             type int32;
             description
               "Near-end interleaved bit rate";
           }
           leaf vdsl-near-end-fast-bitrate {
             type int32;
             description
               "Near-end fast bit rate";
           }
           leaf vdsl-far-end-interleaved-bitrate {
             type int32;
             description
               "Far-end interleaved bit rate";
           }
           leaf vdsl-far-end-fast-bitrate {
             type int32;
             description
               "Far-end fast bit rate";
           }
           leaf vdsl-near-end-interleaved-crc {
             type int32;
             description
               "Near-end interleaved cyclic redundancy check correction";
           }
           leaf vdsl-near-end-fast-crc {
             type int32;
             description
               "Near-end fast cyclic redundancy check correction";
           }
           leaf vdsl-far-end-interleaved-crc {
             type int32;
             description
               "Far-end interleaved cyclic redundancy check correction";
           }
           leaf vdsl-far-end-fast-crc {
             type int32;
             description
               "Far-end fast cyclic redundancy check";
           }
           leaf vdsl-near-end-interleaved-fec {
             type int32;
             description
               "Near-end interleaved footer error correction";
           }
           leaf vdsl-near-end-fast-fec {
             type int32;
             description
               "Near-end fast footer error correction";
           }
           leaf vdsl-far-end-interleaved-fec {
             type int32;
             description
               "Far-end interleaved footer error correction";
           }
           leaf vdsl-far-end-fast-fec {
             type int32;
             description
               "Far-end fast footer error correction";
           }
           leaf vdsl-near-end-interleaved-hec {
             type int32;
             description
               "Near-end interleaved header error correction";
           }
           leaf vdsl-near-end-fast-hec {
             type int32;
             description
               "Near-end fast header error correction";
           }
           leaf vdsl-far-end-interleaved-hec {
             type int32;
             description
               "Far-end interleaved header error correction";
           }
           leaf vdsl-far-end-fast-hec {
             type int32;
             description
               "Far-end fast header error correction";
           }
           leaf vdsl-near-end-interleaved-rx-cells {
             type int32;
             description
               "Near-end interleaved receiver cells";
           }
           leaf vdsl-near-end-fast-rx-cells {
             type int32;
             description
               "Near-end fast receiver cells";
           }
           leaf vdsl-near-end-interleaved-tx-cells {
             type int32;
             description
               "Near-end interleaved transmitter cells";
           }
           leaf vdsl-near-end-fast-tx-cells {
             type int32;
             description
               "Near-end fast transmitter cells";
           }
         }
       }
       container dsl-sfp-information {
         description
           "Operational information and statistics for DSL SFP interfaces";
         leaf dsl-sfp-chip-type {
           type string;
           description
             "Type of dsl sfp";
         }
         leaf dsl-sfp-firmware-version {
           type string;
           description
             "DSL SFP firmware release number";
         }
         leaf dsl-sfp-training-status {
           type string;
           description
             "Status of dsl sfp";
         }
         leaf dsl-sfp-training-mode {
           type string;
           description
             "Mode of dsl sfp";
         }
         leaf dsl-sfp-annex-type {
           type string;
           description
             "Type of dsl sfp ADSL VDSL annex";
         }
         leaf dsl-sfp-profile-type {
           type string;
           description
             "Line type of dsl sfp";
         }
         leaf dsl-sfp-carrier-set {
           type string;
           description
             "Type of dsl sfp VDSL GFAST carrier set";
         }
         leaf dsl-sfp-line-status {
           type string;
           description
             "Line status of dsl sfp";
         }
         container dsl-sfp-statistics {
           leaf dsl-sfp-ds-pkt-count {
             type int32;
             description
               "DS traffic pkt count";
           }
           leaf dsl-sfp-us-pkt-count {
             type int32;
             description
               "US traffic pkt count";
           }
           leaf dsl-sfp-ds-crc-error-pkt-count {
             type int32;
             description
               "DS CRC error pkt count";
           }
           leaf dsl-sfp-us-crc-error-pkt-count {
             type int32;
             description
               "US CRC error pkt count";
           }
           leaf dsl-sfp-ds-electrical-length {
             type int32;
             description
               "DS Electrical Length(dB)";
           }
           leaf dsl-sfp-us-electrical-length {
             type int32;
             description
               "US Electrical Length(dB)";
           }
           leaf dsl-sfp-ds-net-data-rate {
             type int32;
             description
               "DS Net Data Rate(Kbps)";
           }
           leaf dsl-sfp-us-net-data-rate {
             type int32;
             description
               "US Net Data Rate(Kbps)";
           }
           leaf dsl-sfp-ds-snr-margin {
             type int32;
             description
               "DS SNR Margin(dB)";
           }
           leaf dsl-sfp-us-snr-margin {
             type int32;
             description
               "US SNR Margin(dB)";
           }
           leaf dsl-sfp-ds-cv {
             type int32;
             description
               "DS CV";
           }
           leaf dsl-sfp-us-cv {
             type int32;
             description
               "US CV";
           }
           leaf dsl-sfp-ds-es {
             type int32;
             description
               "DS Es";
           }
           leaf dsl-sfp-us-es {
             type int32;
             description
               "US Es";
           }
           leaf dsl-sfp-ds-ses {
             type int32;
             description
               "DS Ses";
           }
           leaf dsl-sfp-us-ses {
             type int32;
             description
               "US Ses";
           }
           leaf dsl-sfp-ds-uas {
             type int32;
             description
               "DS Uas";
           }
           leaf dsl-sfp-us-uas {
             type int32;
             description
               "US Uas";
           }
         }
       }
       container shdsl-information {
         description
           "Operational information and statistics for SHDSL interfaces";
         leaf shdsl-line-termination {
           type string;
           description
             "Line termination remote or central";
         }
         leaf shdsl-annex {
           type string;
           description
             "Type of SHDSL annex";
         }
         leaf shdsl-line-mode {
           type string;
           description
             "Two or four wire mode";
         }
         leaf shdsl-modem-status {
           type string;
           description
             "Status of the SHDSL modem";
         }
         leaf shdsl-bit-rate {
           type int32;
           description
             "Actual line rate";
         }
         leaf shdsl-last-fail-reason {
           type string;
           description
             "Reason for last line-open failure";
         }
         leaf shdsl-last-fail-code {
           type int32;
           description
             "Last line-open failure code";
         }
         leaf shdsl-framer-mode {
           type string;
           description
             "Framer mode used";
         }
         leaf shdsl-dying-gasp {
           type string;
           description
             "Dying gasp is enabled or disabled";
         }
         leaf shdsl-framer-sync-status {
           type string;
           description
             "Framer synchronization status";
         }
         leaf shdsl-chipset-version {
           type int32;
           description
             "Version number for the DSP/framer chip";
         }
         leaf shdsl-firmware-version {
           type string;
           description
             "Transreceiver firmware release number";
         }
         container shdsl-statistics {
           leaf shdsl-loop-attenuation {
             type int32;
             description
               "An estimate of the loop attenuation";
           }
           leaf shdsl-transmit-power {
             type int32;
             description
               "Nominal transmit power";
           }
           leaf shdsl-receiver-gain {
             type int32;
             description
               "Total receiver gain";
           }
           leaf shdsl-snr-sampling {
             type int32;
             description
               "Received signal to noise ratio";
           }
           leaf shdsl-rx-cells {
             type int32;
             description
               "Total ATM cells received";
           }
           leaf shdsl-tx-cells {
             type int32;
             description
               "Total ATM cells transmitted";
           }
           leaf shdsl-crc {
             type int32;
             description
               "Number of CRC errors";
           }
           leaf shdsl-sega {
             type int32;
             description
               "Number of SEGA errors";
           }
           leaf shdsl-losw {
             type int32;
             description
               "Number of LOSW  errors";
           }
           leaf shdsl-hec {
             type int32;
             description
               "Header error check errors";
           }
           leaf shdsl-cell-drop {
             type int32;
             description
               "Cells dropped because of errors";
           }
         }
       }
       container efm-information {
         description
           "Operational information and statistics for EFM interfaces";
         container efm-group-statistics {
           leaf efm-type {
             type string;
             description
               "EFM type Single pair or EFM bond";
           }
           leaf efm-active-pairs {
             type int32;
             description
               "Number of EFM Active Pairs";
           }
           leaf efm-group-bit-rate {
             type int32;
             description
               "Bit rate (in Kbps) for EFM Group";
           }
         }
         container efm-line-statistics {
           leaf line-pair {
             type int32;
             description
               "Line Pair Number";
           }
           leaf line-status {
             type string;
           }
           container active-alarms-efm {
             leaf type-efm {
               type string;
               description
                 "Media type for associated interface alarms";
             }
             container interface-alarms {
               description
                 "Container tag for interface alarms";
               leaf alarm-not-present {
                 type empty;
                 description
                   "No alarm indicated";
               }
               leaf sonet-alarm-lol {
                 type empty;
                 description
                   "Loss of light alarm";
               }
               leaf sonet-alarm-pll {
                 type empty;
                 description
                   "PLL lock alarm";
               }
               leaf sonet-alarm-lof {
                 type empty;
                 description
                   "Loss of frame alarm";
               }
               leaf sonet-alarm-los {
                 type empty;
                 description
                   "Loss of signal alarm";
               }
               leaf sonet-alarm-sef {
                 type empty;
                 description
                   "Severely errored frame alarm";
               }
               leaf sonet-alarm-lais {
                 type empty;
                 description
                   "Line AIS alarm";
               }
               leaf sonet-alarm-pais {
                 type empty;
                 description
                   "Path AIS alarm";
               }
               leaf sonet-alarm-lop {
                 type empty;
                 description
                   "Loss of pointer alarm";
               }
               leaf sonet-alarm-berr-sd {
                 type empty;
                 description
                   "Bit error rate alarm, defect";
               }
               leaf sonet-alarm-berr-sf {
                 type empty;
                 description
                   "Bit error rate alarm, fault";
               }
               leaf sonet-alarm-lrdi {
                 type empty;
                 description
                   "Line remote defect indicator alarm";
               }
               leaf sonet-alarm-prdi {
                 type empty;
                 description
                   "Path remote defect indicator alarm";
               }
               leaf sonet-alarm-rei {
                 type empty;
                 description
                   "Path remote error indicator alarm";
               }
               leaf sonet-alarm-uneq {
                 type empty;
                 description
                   "Unequipped alarm";
               }
               leaf sonet-alarm-pmis {
                 type empty;
                 description
                   "Path payload level mismatch alarm";
               }
               leaf sonet-alarm-loc {
                 type empty;
                 description
                   "Loss of cell delineation alarm";
               }
               leaf sonet-alarm-vais {
                 type empty;
                 description
                   "VT AIS alarm";
               }
               leaf sonet-alarm-vlop {
                 type empty;
                 description
                   "VT loss of pointer alarm";
               }
               leaf sonet-alarm-vrdi {
                 type empty;
                 description
                   "VT remote defect indicator alarm";
               }
               leaf sonet-alarm-vuneq {
                 type empty;
                 description
                   "VT unequipped alarm";
               }
               leaf sonet-alarm-vmis {
                 type empty;
                 description
                   "VT label mismatch alarm";
               }
               leaf sonet-alarm-vloc {
                 type empty;
                 description
                   "VT loss of cell delineation alarm";
               }
               leaf sdh-alarm-lol {
                 type empty;
                 description
                   "Loss of light alarm";
               }
               leaf sdh-alarm-pll {
                 type empty;
                 description
                   "PLL lock alarm";
               }
               leaf sdh-alarm-lof {
                 type empty;
                 description
                   "Loss of frame alarm";
               }
               leaf sdh-alarm-los {
                 type empty;
                 description
                   "Loss of signal alarm";
               }
               leaf sdh-alarm-oof {
                 type empty;
                 description
                   "Out of frame alarm";
               }
               leaf sdh-alarm-msais {
                 type empty;
                 description
                   "Multiplex section AIS alarm";
               }
               leaf sdh-alarm-hpais {
                 type empty;
                 description
                   "High order path AIS alarm";
               }
               leaf sdh-alarm-lop {
                 type empty;
                 description
                   "Loss of pointer alarm";
               }
               leaf sdh-alarm-berr-sd {
                 type empty;
                 description
                   "Bit error rate alarm, defect";
               }
               leaf sdh-alarm-berr-sf {
                 type empty;
                 description
                   "Bit error rate alarm, fault";
               }
               leaf sdh-alarm-msferf {
                 type empty;
                 description
                   "Multiplex section far-end remote failure alarm";
               }
               leaf sdh-alarm-hpferf {
                 type empty;
                 description
                   "High order path far-end remote failure alarm";
               }
               leaf sdh-alarm-hpfebe {
                 type empty;
                 description
                   "High order path far-end block error alarm";
               }
               leaf sdh-alarm-hpuneq {
                 type empty;
                 description
                   "High order path unequipped alarm";
               }
               leaf sdh-alarm-hpplm {
                 type empty;
                 description
                   "High order path payload level mismatch alarm";
               }
               leaf sdh-alarm-loc {
                 type empty;
                 description
                   "Loss of cell delineation alarm";
               }
               leaf sdh-alarm-tuais {
                 type empty;
                 description
                   "TU AIS alarm";
               }
               leaf sdh-alarm-tulop {
                 type empty;
                 description
                   "TU loss of pointer alarm";
               }
               leaf sdh-alarm-turdi {
                 type empty;
                 description
                   "TU remote defect indicator alarm";
               }
               leaf sdh-alarm-tuuneq {
                 type empty;
                 description
                   "TU unequipped alarm";
               }
               leaf sdh-alarm-tumis {
                 type empty;
                 description
                   "TU label mismatch error";
               }
               leaf sdh-alarm-tuloc {
                 type empty;
                 description
                   "TU loss of cell delineation alarm";
               }
               leaf ds3-alarm-pll {
                 type empty;
                 description
                   "PLL lock alarm";
               }
               leaf ds3-alarm-ais {
                 type empty;
                 description
                   "AIS alarm";
               }
               leaf ds3-alarm-lof {
                 type empty;
                 description
                   "Loss of frame alarm";
               }
               leaf ds3-alarm-los {
                 type empty;
                 description
                   "Loss of signal alarm";
               }
               leaf ds3-alarm-lcv {
                 type empty;
                 description
                   "Line code violation alarm";
               }
               leaf ds3-alarm-exz {
                 type empty;
                 description
                   "Excessive zeros alarm";
               }
               leaf ds3-alarm-ferf {
                 type empty;
                 description
                   "Far-end receive failure alarm";
               }
               leaf ds3-alarm-ylw {
                 type empty;
                 description
                   "Yellow alarm";
               }
               leaf ds3-alarm-idle {
                 type empty;
                 description
                   "Idle alarm";
               }
               leaf ds1-alarm-ais {
                 type empty;
                 description
                   "AIS alarm";
               }
               leaf ds1-alarm-lof {
                 type empty;
                 description
                   "Loss of frame alarm";
               }
               leaf ds1-alarm-los {
                 type empty;
                 description
                   "Loss of signal alarm";
               }
               leaf ds1-alarm-ylw {
                 type empty;
                 description
                   "Yellow alarm";
               }
               leaf ds1-alarm-crc-major {
                 type empty;
                 description
                   "CRC errors crossed major threshold";
               }
               leaf ds1-alarm-crc-minor {
                 type empty;
                 description
                   "CRC errors crossed minor threshold";
               }
               leaf dsl-alarm-lof {
                 type empty;
                 description
                   "Loss of frame alarm";
               }
               leaf dsl-alarm-los {
                 type empty;
                 description
                   "Loss of signal alarm";
               }
               leaf dsl-alarm-lom {
                 type empty;
                 description
                   "Loss of multiframe alarm";
               }
               leaf dsl-alarm-locdi {
                 type empty;
                 description
                   "Loss of cell delineation alarm for interleaved channel";
               }
               leaf dsl-alarm-locdni {
                 type empty;
                 description
                   "Loss of cell delineation alarm for non-interleaved 
                   channel";
               }
               leaf dsl-alarm-lop {
                 type empty;
                 description
                   "Loss of power alarm";
               }
               leaf dsl-alarm-far-lof {
                 type empty;
                 description
                   "Far-end loss-of-frame alarm";
               }
               leaf dsl-alarm-far-los {
                 type empty;
                 description
                   "Far-end loss-of-signal alarm";
               }
               leaf dsl-alarm-far-locdi {
                 type empty;
                 description
                   "Far-end loss-of-cell-delineation alarm for interleaved 
                   channel";
               }
               leaf dsl-alarm-far-locdni {
                 type empty;
                 description
                   "Far-end loss-of-cell-delineation alarm for 
                   non-interleaved channel";
               }
               leaf fibrechannel-alarm-link-down {
                 type empty;
                 description
                   "Link alive failure";
               }
               leaf ethernet-alarm-link-down {
                 type empty;
                 description
                   "Link alive failure";
               }
               leaf ethernet-alarm-an-not-supported {
                 type empty;
                 description
                   "AN not supported";
               }
               leaf ethernet-alarm-link-local-fault {
                 type empty;
                 description
                   "Link local fault";
               }
               leaf ethernet-alarm-link-remote-fault {
                 type empty;
                 description
                   "Link remote fault";
               }
               leaf ethernet-alarm-link-local-degrade {
                 type empty;
                 description
                   "Link local degrade";
               }
               leaf ethernet-alarm-link-remote-degrade {
                 type empty;
                 description
                   "Link remote degrade";
               }
               leaf ethernet-alarm-lcdp {
                 type empty;
                 description
                   "Loss of code-group delineation";
               }
               leaf isdn-alarm-los {
                 type empty;
                 description
                   "Loss of signal alarm";
               }
               leaf isdn-alarm-lof {
                 type empty;
                 description
                   "Loss of frame alarm";
               }
               leaf shdsl-alarm-losd {
                 type empty;
                 description
                   "Loss of signal alarm";
               }
               leaf shdsl-alarm-losw {
                 type empty;
                 description
                   "Loss of sync word alarm";
               }
               leaf shdsl-alarm-line1-losd {
                 type empty;
                 description
                   "Loss of signal (line 1) alarm";
               }
               leaf shdsl-alarm-line1-losw {
                 type empty;
                 description
                   "Loss of sync word (line 1) alarm";
               }
               leaf shdsl-alarm-line2-losd {
                 type empty;
                 description
                   "Loss of signal (line 2) alarm";
               }
               leaf shdsl-alarm-line2-losw {
                 type empty;
                 description
                   "Loss of sync word (line 2) alarm";
               }
               leaf shdsl-efm-alarm-losd {
                 type empty;
                 description
                   "Loss of signal alarm";
               }
               leaf shdsl-efm-alarm-losw {
                 type empty;
                 description
                   "Loss of sync word alarm";
               }
               leaf otn-alarm-los {
                 type empty;
                 description
                   "Loss of signal alarm";
               }
               leaf otn-alarm-lof {
                 type empty;
                 description
                   "Loss of frame alarm";
               }
               leaf otn-alarm-lom {
                 type empty;
                 description
                   "Loss of multiframe alarm";
               }
               leaf otn-alarm-wavelength-lock {
                 type empty;
                 description
                   "Loss of Wavelength Lock alarm";
               }
               leaf otn-alarm-otu-ais {
                 type empty;
                 description
                   "OTU Alarm Indication Signal alarm";
               }
               leaf otn-alarm-otu-bdi {
                 type empty;
                 description
                   "OTU Background Block Error alarm";
               }
               leaf otn-alarm-otu-ttim {
                 type empty;
                 description
                   "OTU Trail Trace Identifier Mismatch alarm";
               }
               leaf otn-alarm-otu-iae {
                 type empty;
                 description
                   "OTU Incoming Alignment alarm";
               }
               leaf otn-alarm-otu-sd {
                 type empty;
                 description
                   "OTU Signal Degrade alarm";
               }
               leaf otn-alarm-otu-sf {
                 type empty;
                 description
                   "OTU Signal Fail alarm";
               }
               leaf otn-alarm-otu-biae {
                 type empty;
                 description
                   "OTU Backward Incoming Alignment alarm";
               }
               leaf otn-alarm-otu-tsf {
                 type empty;
                 description
                   "OTU Trail Signal Fail alarm";
               }
               leaf otn-alarm-otu-ssf {
                 type empty;
                 description
                   "OTU Server Signal Fail alarm";
               }
               leaf otn-alarm-otu-fec-excessive {
                 type empty;
                 description
                   "OTU FEC Excessive alarm";
               }
               leaf otn-alarm-otu-fec-degraded {
                 type empty;
                 description
                   "OTU FEC Degraded alarm";
               }
               leaf otn-alarm-otu-fe-fec-degraded {
                 type empty;
                 description
                   "OTU FE FEC Degraded/Excessive alarm";
               }
               leaf otn-alarm-otu-threshold-bbe {
                 type empty;
                 description
                   "OTU Background Block Error threshold alarm";
               }
               leaf otn-alarm-otu-threshold-es {
                 type empty;
                 description
                   "OTU Errored Seconds threshold alarm";
               }
               leaf otn-alarm-otu-threshold-ses {
                 type empty;
                 description
                   "OTU Severely Errored Seconds threshold alarm";
               }
               leaf otn-alarm-otu-threshold-uas {
                 type empty;
                 description
                   "OTU Unavailable Seconds threshold alarm";
               }
               leaf otn-alarm-odu-ais {
                 type empty;
                 description
                   "ODU  Alarm Indiaction Signal alarm";
               }
               leaf otn-alarm-odu-oci {
                 type empty;
                 description
                   "ODU Open Connection Indication alarm";
               }
               leaf otn-alarm-odu-lck {
                 type empty;
                 description
                   "ODU Locked alarm";
               }
               leaf otn-alarm-odu-bdi {
                 type empty;
                 description
                   "ODU Backward Defect Indication alarm";
               }
               leaf otn-alarm-odu-ttim {
                 type empty;
                 description
                   "ODU Trail Trace Identifier Mismatch alarm";
               }
               leaf otn-alarm-odu-sd {
                 type empty;
                 description
                   "ODU Signal Degrade alarm";
               }
               leaf otn-alarm-odu-sf {
                 type empty;
                 description
                   "ODU Signal Fail alarm";
               }
               leaf otn-alarm-odu-iae {
                 type empty;
                 description
                   "ODU Incoming Alignment alarm";
               }
               leaf otn-alarm-odu-ltc {
                 type empty;
                 description
                   "ODU Loss of Tandem Connection alarm";
               }
               leaf otn-alarm-odu-csf {
                 type empty;
                 description
                   "ODU Client Signal Fail alarm";
               }
               leaf otn-alarm-odu-tsf {
                 type empty;
                 description
                   "ODU Trail Signal Fail alarm";
               }
               leaf otn-alarm-odu-ssf {
                 type empty;
                 description
                   "ODU Server Signal Fail alarm";
               }
               leaf otn-alarm-odu-rx-aps-change {
                 type empty;
                 description
                   "ODU Rx Aps Change alarm";
               }
               leaf otn-alarm-odu-threshold-bbe {
                 type empty;
                 description
                   "ODU Background Block Error threshold alarm";
               }
               leaf otn-alarm-odu-threshold-es {
                 type empty;
                 description
                   "ODU Errored Seconds threshold alarm";
               }
               leaf otn-alarm-odu-threshold-ses {
                 type empty;
                 description
                   "ODU Severely Errored Seconds threshold alarm";
               }
               leaf otn-alarm-odu-threshold-uas {
                 type empty;
                 description
                   "ODU Unavailable Seconds threshold alarm";
               }
               leaf otn-alarm-opu-pmi {
                 type empty;
                 description
                   "OPU Payload Mismatch alarm";
               }
               leaf otn-alarm-pre-fec-sd {
                 type empty;
                 description
                   "Pre-FEC SD alarm";
               }
               leaf otn-alarm-fe-pre-fec-sd {
                 type empty;
                 description
                   "Far end pre-FEC SD alarm";
               }
               leaf optics-alarms-mod-fault {
                 type empty;
                 description
                   "Module Fault alarm";
               }
               leaf optics-alarms-lol {
                 type empty;
                 description
                   "Loss of Lock alarm";
               }
               leaf optics-alarms-los {
                 type empty;
                 description
                   "Loss of Signal alarms";
               }
               leaf optics-alarms-lof {
                 type empty;
                 description
                   "Loss of frame alarm";
               }
               leaf optics-alarms-lom {
                 type empty;
                 description
                   "Loss of multi-frame alarm";
               }
               leaf optics-alarms-otu-bdi {
                 type empty;
                 description
                   "Backward defect indiacation alarm";
               }
               leaf optics-alarms-rmsf {
                 type empty;
                 description
                   "Rx Modem sysnc fault alarm";
               }
               leaf optics-alarms-rmlol {
                 type empty;
                 description
                   "Rx Modem loss of lock alarm";
               }
               leaf optics-alarms-rloa {
                 type empty;
                 description
                   "Rx loss of alignment alarm";
               }
               leaf optics-alarms-mbclf {
                 type empty;
                 description
                   "Modulator Bias control loop fail alarm";
               }
               leaf optics-alarms-itlaf {
                 type empty;
                 description
                   "ITLA Fault alarm";
               }
               leaf optics-alarms-daccf {
                 type empty;
                 description
                   "DAC Calibration Fault alarm";
               }
               leaf optics-alarms-adccf {
                 type empty;
                 description
                   "ADC Calibration Fault alarm";
               }
               leaf optics-alarms-fec-degrade {
                 type empty;
                 description
                   "FEC Degrade alarm";
               }
               leaf optics-alarms-fec-excessive {
                 type empty;
                 description
                   "FEC Excessive alarm";
               }
               leaf optics-alarms-fe-fec-degrade {
                 type empty;
                 description
                   "Far-end FEC Degrade alarm";
               }
               leaf optics-alarms-fe-fec-excessive {
                 type empty;
                 description
                   "Far-end FEC Excessive alarm";
               }
               leaf ima-alarm-startup-fe {
                 type empty;
                 description
                   "IMA group startup far-end alarm";
               }
               leaf ima-alarm-config-abort {
                 type empty;
                 description
                   "IMA group config abort alarm";
               }
               leaf ima-alarm-config-abort-fe {
                 type empty;
                 description
                   "IMA group config abort far-end alarm";
               }
               leaf ima-alarm-insufficient-links {
                 type empty;
                 description
                   "IMA group insufficient links alarm";
               }
               leaf ima-alarm-insufficient-links-fe {
                 type empty;
                 description
                   "IMA group insufficient links far-end alarm";
               }
               leaf ima-alarm-blocked {
                 type empty;
                 description
                   "IMA group blocked alarm";
               }
               leaf ima-alarm-blocked-fe {
                 type empty;
                 description
                   "IMA group blocked far-end alarm";
               }
               leaf ima-alarm-timing-mismatch {
                 type empty;
                 description
                   "IMA group timing mismatch alarm";
               }
               leaf ima-alarm-version-mismatch {
                 type empty;
                 description
                   "IMA group version mismatch alarm";
               }
               leaf ima-alarm-lif {
                 type empty;
                 description
                   "IMA link loss of IMA frame alarm";
               }
               leaf ima-alarm-lods {
                 type empty;
                 description
                   "IMA link out of delay synchronization alarm";
               }
               leaf ima-alarm-rdi {
                 type empty;
                 description
                   "IMA link remote defect indicator alarm";
               }
               leaf ima-alarm-tx-misconnected {
                 type empty;
                 description
                   "IMA link tx misconnected alarm";
               }
               leaf ima-alarm-rx-misconnected {
                 type empty;
                 description
                   "IMA link rx misconnected alarm";
               }
               leaf ima-alarm-fault {
                 type empty;
                 description
                   "IMA link fault alarm";
               }
               leaf ima-alarm-tx-unusable-fe {
                 type empty;
                 description
                   "IMA link Tx unusable far-end alarm";
               }
               leaf ima-alarm-rx-unusable-fe {
                 type empty;
                 description
                   "IMA link Tx unusable far-end alarm";
               }
               leaf generic-value {
                 type int32;
                 description
                   "Hexadecimal value of unknown flag bits";
               }
             }
           }
           container active-defects-efm {
             leaf type-efm {
               type string;
               description
                 "Media type for associated interface alarms";
             }
             container interface-alarms {
               description
                 "Container tag for interface alarms";
               leaf alarm-not-present {
                 type empty;
                 description
                   "No alarm indicated";
               }
               leaf sonet-alarm-lol {
                 type empty;
                 description
                   "Loss of light alarm";
               }
               leaf sonet-alarm-pll {
                 type empty;
                 description
                   "PLL lock alarm";
               }
               leaf sonet-alarm-lof {
                 type empty;
                 description
                   "Loss of frame alarm";
               }
               leaf sonet-alarm-los {
                 type empty;
                 description
                   "Loss of signal alarm";
               }
               leaf sonet-alarm-sef {
                 type empty;
                 description
                   "Severely errored frame alarm";
               }
               leaf sonet-alarm-lais {
                 type empty;
                 description
                   "Line AIS alarm";
               }
               leaf sonet-alarm-pais {
                 type empty;
                 description
                   "Path AIS alarm";
               }
               leaf sonet-alarm-lop {
                 type empty;
                 description
                   "Loss of pointer alarm";
               }
               leaf sonet-alarm-berr-sd {
                 type empty;
                 description
                   "Bit error rate alarm, defect";
               }
               leaf sonet-alarm-berr-sf {
                 type empty;
                 description
                   "Bit error rate alarm, fault";
               }
               leaf sonet-alarm-lrdi {
                 type empty;
                 description
                   "Line remote defect indicator alarm";
               }
               leaf sonet-alarm-prdi {
                 type empty;
                 description
                   "Path remote defect indicator alarm";
               }
               leaf sonet-alarm-rei {
                 type empty;
                 description
                   "Path remote error indicator alarm";
               }
               leaf sonet-alarm-uneq {
                 type empty;
                 description
                   "Unequipped alarm";
               }
               leaf sonet-alarm-pmis {
                 type empty;
                 description
                   "Path payload level mismatch alarm";
               }
               leaf sonet-alarm-loc {
                 type empty;
                 description
                   "Loss of cell delineation alarm";
               }
               leaf sonet-alarm-vais {
                 type empty;
                 description
                   "VT AIS alarm";
               }
               leaf sonet-alarm-vlop {
                 type empty;
                 description
                   "VT loss of pointer alarm";
               }
               leaf sonet-alarm-vrdi {
                 type empty;
                 description
                   "VT remote defect indicator alarm";
               }
               leaf sonet-alarm-vuneq {
                 type empty;
                 description
                   "VT unequipped alarm";
               }
               leaf sonet-alarm-vmis {
                 type empty;
                 description
                   "VT label mismatch alarm";
               }
               leaf sonet-alarm-vloc {
                 type empty;
                 description
                   "VT loss of cell delineation alarm";
               }
               leaf sdh-alarm-lol {
                 type empty;
                 description
                   "Loss of light alarm";
               }
               leaf sdh-alarm-pll {
                 type empty;
                 description
                   "PLL lock alarm";
               }
               leaf sdh-alarm-lof {
                 type empty;
                 description
                   "Loss of frame alarm";
               }
               leaf sdh-alarm-los {
                 type empty;
                 description
                   "Loss of signal alarm";
               }
               leaf sdh-alarm-oof {
                 type empty;
                 description
                   "Out of frame alarm";
               }
               leaf sdh-alarm-msais {
                 type empty;
                 description
                   "Multiplex section AIS alarm";
               }
               leaf sdh-alarm-hpais {
                 type empty;
                 description
                   "High order path AIS alarm";
               }
               leaf sdh-alarm-lop {
                 type empty;
                 description
                   "Loss of pointer alarm";
               }
               leaf sdh-alarm-berr-sd {
                 type empty;
                 description
                   "Bit error rate alarm, defect";
               }
               leaf sdh-alarm-berr-sf {
                 type empty;
                 description
                   "Bit error rate alarm, fault";
               }
               leaf sdh-alarm-msferf {
                 type empty;
                 description
                   "Multiplex section far-end remote failure alarm";
               }
               leaf sdh-alarm-hpferf {
                 type empty;
                 description
                   "High order path far-end remote failure alarm";
               }
               leaf sdh-alarm-hpfebe {
                 type empty;
                 description
                   "High order path far-end block error alarm";
               }
               leaf sdh-alarm-hpuneq {
                 type empty;
                 description
                   "High order path unequipped alarm";
               }
               leaf sdh-alarm-hpplm {
                 type empty;
                 description
                   "High order path payload level mismatch alarm";
               }
               leaf sdh-alarm-loc {
                 type empty;
                 description
                   "Loss of cell delineation alarm";
               }
               leaf sdh-alarm-tuais {
                 type empty;
                 description
                   "TU AIS alarm";
               }
               leaf sdh-alarm-tulop {
                 type empty;
                 description
                   "TU loss of pointer alarm";
               }
               leaf sdh-alarm-turdi {
                 type empty;
                 description
                   "TU remote defect indicator alarm";
               }
               leaf sdh-alarm-tuuneq {
                 type empty;
                 description
                   "TU unequipped alarm";
               }
               leaf sdh-alarm-tumis {
                 type empty;
                 description
                   "TU label mismatch error";
               }
               leaf sdh-alarm-tuloc {
                 type empty;
                 description
                   "TU loss of cell delineation alarm";
               }
               leaf ds3-alarm-pll {
                 type empty;
                 description
                   "PLL lock alarm";
               }
               leaf ds3-alarm-ais {
                 type empty;
                 description
                   "AIS alarm";
               }
               leaf ds3-alarm-lof {
                 type empty;
                 description
                   "Loss of frame alarm";
               }
               leaf ds3-alarm-los {
                 type empty;
                 description
                   "Loss of signal alarm";
               }
               leaf ds3-alarm-lcv {
                 type empty;
                 description
                   "Line code violation alarm";
               }
               leaf ds3-alarm-exz {
                 type empty;
                 description
                   "Excessive zeros alarm";
               }
               leaf ds3-alarm-ferf {
                 type empty;
                 description
                   "Far-end receive failure alarm";
               }
               leaf ds3-alarm-ylw {
                 type empty;
                 description
                   "Yellow alarm";
               }
               leaf ds3-alarm-idle {
                 type empty;
                 description
                   "Idle alarm";
               }
               leaf ds1-alarm-ais {
                 type empty;
                 description
                   "AIS alarm";
               }
               leaf ds1-alarm-lof {
                 type empty;
                 description
                   "Loss of frame alarm";
               }
               leaf ds1-alarm-los {
                 type empty;
                 description
                   "Loss of signal alarm";
               }
               leaf ds1-alarm-ylw {
                 type empty;
                 description
                   "Yellow alarm";
               }
               leaf ds1-alarm-crc-major {
                 type empty;
                 description
                   "CRC errors crossed major threshold";
               }
               leaf ds1-alarm-crc-minor {
                 type empty;
                 description
                   "CRC errors crossed minor threshold";
               }
               leaf dsl-alarm-lof {
                 type empty;
                 description
                   "Loss of frame alarm";
               }
               leaf dsl-alarm-los {
                 type empty;
                 description
                   "Loss of signal alarm";
               }
               leaf dsl-alarm-lom {
                 type empty;
                 description
                   "Loss of multiframe alarm";
               }
               leaf dsl-alarm-locdi {
                 type empty;
                 description
                   "Loss of cell delineation alarm for interleaved channel";
               }
               leaf dsl-alarm-locdni {
                 type empty;
                 description
                   "Loss of cell delineation alarm for non-interleaved 
                   channel";
               }
               leaf dsl-alarm-lop {
                 type empty;
                 description
                   "Loss of power alarm";
               }
               leaf dsl-alarm-far-lof {
                 type empty;
                 description
                   "Far-end loss-of-frame alarm";
               }
               leaf dsl-alarm-far-los {
                 type empty;
                 description
                   "Far-end loss-of-signal alarm";
               }
               leaf dsl-alarm-far-locdi {
                 type empty;
                 description
                   "Far-end loss-of-cell-delineation alarm for interleaved 
                   channel";
               }
               leaf dsl-alarm-far-locdni {
                 type empty;
                 description
                   "Far-end loss-of-cell-delineation alarm for 
                   non-interleaved channel";
               }
               leaf fibrechannel-alarm-link-down {
                 type empty;
                 description
                   "Link alive failure";
               }
               leaf ethernet-alarm-link-down {
                 type empty;
                 description
                   "Link alive failure";
               }
               leaf ethernet-alarm-an-not-supported {
                 type empty;
                 description
                   "AN not supported";
               }
               leaf ethernet-alarm-link-local-fault {
                 type empty;
                 description
                   "Link local fault";
               }
               leaf ethernet-alarm-link-remote-fault {
                 type empty;
                 description
                   "Link remote fault";
               }
               leaf ethernet-alarm-link-local-degrade {
                 type empty;
                 description
                   "Link local degrade";
               }
               leaf ethernet-alarm-link-remote-degrade {
                 type empty;
                 description
                   "Link remote degrade";
               }
               leaf ethernet-alarm-lcdp {
                 type empty;
                 description
                   "Loss of code-group delineation";
               }
               leaf isdn-alarm-los {
                 type empty;
                 description
                   "Loss of signal alarm";
               }
               leaf isdn-alarm-lof {
                 type empty;
                 description
                   "Loss of frame alarm";
               }
               leaf shdsl-alarm-losd {
                 type empty;
                 description
                   "Loss of signal alarm";
               }
               leaf shdsl-alarm-losw {
                 type empty;
                 description
                   "Loss of sync word alarm";
               }
               leaf shdsl-alarm-line1-losd {
                 type empty;
                 description
                   "Loss of signal (line 1) alarm";
               }
               leaf shdsl-alarm-line1-losw {
                 type empty;
                 description
                   "Loss of sync word (line 1) alarm";
               }
               leaf shdsl-alarm-line2-losd {
                 type empty;
                 description
                   "Loss of signal (line 2) alarm";
               }
               leaf shdsl-alarm-line2-losw {
                 type empty;
                 description
                   "Loss of sync word (line 2) alarm";
               }
               leaf shdsl-efm-alarm-losd {
                 type empty;
                 description
                   "Loss of signal alarm";
               }
               leaf shdsl-efm-alarm-losw {
                 type empty;
                 description
                   "Loss of sync word alarm";
               }
               leaf otn-alarm-los {
                 type empty;
                 description
                   "Loss of signal alarm";
               }
               leaf otn-alarm-lof {
                 type empty;
                 description
                   "Loss of frame alarm";
               }
               leaf otn-alarm-lom {
                 type empty;
                 description
                   "Loss of multiframe alarm";
               }
               leaf otn-alarm-wavelength-lock {
                 type empty;
                 description
                   "Loss of Wavelength Lock alarm";
               }
               leaf otn-alarm-otu-ais {
                 type empty;
                 description
                   "OTU Alarm Indication Signal alarm";
               }
               leaf otn-alarm-otu-bdi {
                 type empty;
                 description
                   "OTU Background Block Error alarm";
               }
               leaf otn-alarm-otu-ttim {
                 type empty;
                 description
                   "OTU Trail Trace Identifier Mismatch alarm";
               }
               leaf otn-alarm-otu-iae {
                 type empty;
                 description
                   "OTU Incoming Alignment alarm";
               }
               leaf otn-alarm-otu-sd {
                 type empty;
                 description
                   "OTU Signal Degrade alarm";
               }
               leaf otn-alarm-otu-sf {
                 type empty;
                 description
                   "OTU Signal Fail alarm";
               }
               leaf otn-alarm-otu-biae {
                 type empty;
                 description
                   "OTU Backward Incoming Alignment alarm";
               }
               leaf otn-alarm-otu-tsf {
                 type empty;
                 description
                   "OTU Trail Signal Fail alarm";
               }
               leaf otn-alarm-otu-ssf {
                 type empty;
                 description
                   "OTU Server Signal Fail alarm";
               }
               leaf otn-alarm-otu-fec-excessive {
                 type empty;
                 description
                   "OTU FEC Excessive alarm";
               }
               leaf otn-alarm-otu-fec-degraded {
                 type empty;
                 description
                   "OTU FEC Degraded alarm";
               }
               leaf otn-alarm-otu-fe-fec-degraded {
                 type empty;
                 description
                   "OTU FE FEC Degraded/Excessive alarm";
               }
               leaf otn-alarm-otu-threshold-bbe {
                 type empty;
                 description
                   "OTU Background Block Error threshold alarm";
               }
               leaf otn-alarm-otu-threshold-es {
                 type empty;
                 description
                   "OTU Errored Seconds threshold alarm";
               }
               leaf otn-alarm-otu-threshold-ses {
                 type empty;
                 description
                   "OTU Severely Errored Seconds threshold alarm";
               }
               leaf otn-alarm-otu-threshold-uas {
                 type empty;
                 description
                   "OTU Unavailable Seconds threshold alarm";
               }
               leaf otn-alarm-odu-ais {
                 type empty;
                 description
                   "ODU  Alarm Indiaction Signal alarm";
               }
               leaf otn-alarm-odu-oci {
                 type empty;
                 description
                   "ODU Open Connection Indication alarm";
               }
               leaf otn-alarm-odu-lck {
                 type empty;
                 description
                   "ODU Locked alarm";
               }
               leaf otn-alarm-odu-bdi {
                 type empty;
                 description
                   "ODU Backward Defect Indication alarm";
               }
               leaf otn-alarm-odu-ttim {
                 type empty;
                 description
                   "ODU Trail Trace Identifier Mismatch alarm";
               }
               leaf otn-alarm-odu-sd {
                 type empty;
                 description
                   "ODU Signal Degrade alarm";
               }
               leaf otn-alarm-odu-sf {
                 type empty;
                 description
                   "ODU Signal Fail alarm";
               }
               leaf otn-alarm-odu-iae {
                 type empty;
                 description
                   "ODU Incoming Alignment alarm";
               }
               leaf otn-alarm-odu-ltc {
                 type empty;
                 description
                   "ODU Loss of Tandem Connection alarm";
               }
               leaf otn-alarm-odu-csf {
                 type empty;
                 description
                   "ODU Client Signal Fail alarm";
               }
               leaf otn-alarm-odu-tsf {
                 type empty;
                 description
                   "ODU Trail Signal Fail alarm";
               }
               leaf otn-alarm-odu-ssf {
                 type empty;
                 description
                   "ODU Server Signal Fail alarm";
               }
               leaf otn-alarm-odu-rx-aps-change {
                 type empty;
                 description
                   "ODU Rx Aps Change alarm";
               }
               leaf otn-alarm-odu-threshold-bbe {
                 type empty;
                 description
                   "ODU Background Block Error threshold alarm";
               }
               leaf otn-alarm-odu-threshold-es {
                 type empty;
                 description
                   "ODU Errored Seconds threshold alarm";
               }
               leaf otn-alarm-odu-threshold-ses {
                 type empty;
                 description
                   "ODU Severely Errored Seconds threshold alarm";
               }
               leaf otn-alarm-odu-threshold-uas {
                 type empty;
                 description
                   "ODU Unavailable Seconds threshold alarm";
               }
               leaf otn-alarm-opu-pmi {
                 type empty;
                 description
                   "OPU Payload Mismatch alarm";
               }
               leaf otn-alarm-pre-fec-sd {
                 type empty;
                 description
                   "Pre-FEC SD alarm";
               }
               leaf otn-alarm-fe-pre-fec-sd {
                 type empty;
                 description
                   "Far end pre-FEC SD alarm";
               }
               leaf optics-alarms-mod-fault {
                 type empty;
                 description
                   "Module Fault alarm";
               }
               leaf optics-alarms-lol {
                 type empty;
                 description
                   "Loss of Lock alarm";
               }
               leaf optics-alarms-los {
                 type empty;
                 description
                   "Loss of Signal alarms";
               }
               leaf optics-alarms-lof {
                 type empty;
                 description
                   "Loss of frame alarm";
               }
               leaf optics-alarms-lom {
                 type empty;
                 description
                   "Loss of multi-frame alarm";
               }
               leaf optics-alarms-otu-bdi {
                 type empty;
                 description
                   "Backward defect indiacation alarm";
               }
               leaf optics-alarms-rmsf {
                 type empty;
                 description
                   "Rx Modem sysnc fault alarm";
               }
               leaf optics-alarms-rmlol {
                 type empty;
                 description
                   "Rx Modem loss of lock alarm";
               }
               leaf optics-alarms-rloa {
                 type empty;
                 description
                   "Rx loss of alignment alarm";
               }
               leaf optics-alarms-mbclf {
                 type empty;
                 description
                   "Modulator Bias control loop fail alarm";
               }
               leaf optics-alarms-itlaf {
                 type empty;
                 description
                   "ITLA Fault alarm";
               }
               leaf optics-alarms-daccf {
                 type empty;
                 description
                   "DAC Calibration Fault alarm";
               }
               leaf optics-alarms-adccf {
                 type empty;
                 description
                   "ADC Calibration Fault alarm";
               }
               leaf optics-alarms-fec-degrade {
                 type empty;
                 description
                   "FEC Degrade alarm";
               }
               leaf optics-alarms-fec-excessive {
                 type empty;
                 description
                   "FEC Excessive alarm";
               }
               leaf optics-alarms-fe-fec-degrade {
                 type empty;
                 description
                   "Far-end FEC Degrade alarm";
               }
               leaf optics-alarms-fe-fec-excessive {
                 type empty;
                 description
                   "Far-end FEC Excessive alarm";
               }
               leaf ima-alarm-startup-fe {
                 type empty;
                 description
                   "IMA group startup far-end alarm";
               }
               leaf ima-alarm-config-abort {
                 type empty;
                 description
                   "IMA group config abort alarm";
               }
               leaf ima-alarm-config-abort-fe {
                 type empty;
                 description
                   "IMA group config abort far-end alarm";
               }
               leaf ima-alarm-insufficient-links {
                 type empty;
                 description
                   "IMA group insufficient links alarm";
               }
               leaf ima-alarm-insufficient-links-fe {
                 type empty;
                 description
                   "IMA group insufficient links far-end alarm";
               }
               leaf ima-alarm-blocked {
                 type empty;
                 description
                   "IMA group blocked alarm";
               }
               leaf ima-alarm-blocked-fe {
                 type empty;
                 description
                   "IMA group blocked far-end alarm";
               }
               leaf ima-alarm-timing-mismatch {
                 type empty;
                 description
                   "IMA group timing mismatch alarm";
               }
               leaf ima-alarm-version-mismatch {
                 type empty;
                 description
                   "IMA group version mismatch alarm";
               }
               leaf ima-alarm-lif {
                 type empty;
                 description
                   "IMA link loss of IMA frame alarm";
               }
               leaf ima-alarm-lods {
                 type empty;
                 description
                   "IMA link out of delay synchronization alarm";
               }
               leaf ima-alarm-rdi {
                 type empty;
                 description
                   "IMA link remote defect indicator alarm";
               }
               leaf ima-alarm-tx-misconnected {
                 type empty;
                 description
                   "IMA link tx misconnected alarm";
               }
               leaf ima-alarm-rx-misconnected {
                 type empty;
                 description
                   "IMA link rx misconnected alarm";
               }
               leaf ima-alarm-fault {
                 type empty;
                 description
                   "IMA link fault alarm";
               }
               leaf ima-alarm-tx-unusable-fe {
                 type empty;
                 description
                   "IMA link Tx unusable far-end alarm";
               }
               leaf ima-alarm-rx-unusable-fe {
                 type empty;
                 description
                   "IMA link Tx unusable far-end alarm";
               }
               leaf generic-value {
                 type int32;
                 description
                   "Hexadecimal value of unknown flag bits";
               }
             }
           }
           container media-information {
             description
               "Information about media alarms";
             leaf media-type {
               type string;
               description
                 "Type of media this information is for";
             }
             list media-alarm {
               leaf media-alarm-name {
                 type string;
               }
               leaf media-alarm-count {
                 type int32;
               }
               leaf media-alarm-seconds {
                 type int32;
               }
               leaf media-alarm-state {
                 type string;
               }
               leaf ce-counter-name {
                 type string;
                 description
                   "Circuit Emulation counter information";
               }
               leaf ce-counter-packets {
                 type int32;
                 description
                   "Circuit Emulation number of packets";
               }
               leaf ce-counter-bytes {
                 type int32;
                 description
                   "Circuit Emulation number of bytes";
               }
               leaf ce-counter-count {
                 type int32;
                 description
                   "Circuit Emulation number of event occurrences";
               }
             }
             leaf ds1-timeslots {
               type string;
             }
             leaf ds1-line-encoding {
               type string;
             }
             leaf ds1-byte-encoding {
               type string;
             }
             leaf ds1-data-inversion {
               type string;
             }
             leaf idle-cycle-flag {
               type string;
             }
             leaf start-end-flag {
               type string;
             }
             leaf ds0-byte-encoding {
               type string;
             }
             leaf ds0-data-inversion {
               type string;
             }
             leaf e3-data-inversion {
               type string;
             }
             leaf ds1-buildout {
               type string;
               description
                 "Number of feet";
             }
           }
           container shdsl-information {
             description
               "Operational information and statistics for SHDSL interfaces";
             leaf shdsl-line-termination {
               type string;
               description
                 "Line termination remote or central";
             }
             leaf shdsl-annex {
               type string;
               description
                 "Type of SHDSL annex";
             }
             leaf shdsl-line-mode {
               type string;
               description
                 "Two or four wire mode";
             }
             leaf shdsl-modem-status {
               type string;
               description
                 "Status of the SHDSL modem";
             }
             leaf shdsl-bit-rate {
               type int32;
               description
                 "Actual line rate";
             }
             leaf shdsl-last-fail-reason {
               type string;
               description
                 "Reason for last line-open failure";
             }
             leaf shdsl-last-fail-code {
               type int32;
               description
                 "Last line-open failure code";
             }
             leaf shdsl-framer-mode {
               type string;
               description
                 "Framer mode used";
             }
             leaf shdsl-paf-status {
               type string;
               description
                 "EFM PAF Status";
             }
             leaf shdsl-dying-gasp {
               type string;
               description
                 "Dying gasp is enabled or disabled";
             }
             leaf shdsl-framer-sync-status {
               type string;
               description
                 "Framer synchronization status";
             }
             leaf shdsl-chipset-version {
               type int32;
               description
                 "Version number for the DSP/framer chip";
             }
             leaf shdsl-firmware-version {
               type string;
               description
                 "Transreceiver firmware release number";
             }
             container shdsl-statistics {
               leaf shdsl-loop-attenuation {
                 type int32;
                 description
                   "An estimate of the loop attenuation";
               }
               leaf shdsl-transmit-power {
                 type int32;
                 description
                   "Nominal transmit power";
               }
               leaf shdsl-receiver-gain {
                 type int32;
                 description
                   "Total receiver gain";
               }
               leaf shdsl-snr-sampling {
                 type int32;
                 description
                   "Received signal to noise ratio";
               }
               leaf shdsl-rx-cells {
                 type int32;
                 description
                   "Total ATM cells received";
               }
               leaf shdsl-tx-cells {
                 type int32;
                 description
                   "Total ATM cells transmitted";
               }
               leaf shdsl-crc {
                 type int32;
                 description
                   "Number of CRC errors";
               }
               leaf shdsl-sega {
                 type int32;
                 description
                   "Number of SEGA errors";
               }
               leaf shdsl-losw {
                 type int32;
                 description
                   "Number of LOSW  errors";
               }
               leaf shdsl-hec {
                 type int32;
                 description
                   "Header error check errors";
               }
               leaf shdsl-cell-drop {
                 type int32;
                 description
                   "Cells dropped because of errors";
               }
             }
           }
         }
       }
       container atm-information {
         description
           "Operational information and statistics for ATM interfaces";
         leaf atm-hcs-state {
           type string;
         }
         leaf atm-loss-of-cell {
           type string;
         }
         container plcp-defects {
           list media-alarm {
             leaf media-alarm-name {
               type string;
             }
             leaf media-alarm-seconds {
               type int32;
             }
             leaf media-alarm-count {
               type int32;
             }
             leaf media-alarm-state {
               type string;
             }
           }
         }
         container atm-defects {
           list media-alarm {
             leaf media-alarm-name {
               type string;
             }
             leaf media-alarm-seconds {
               type int32;
             }
             leaf media-alarm-count {
               type int32;
             }
             leaf media-alarm-state {
               type string;
             }
           }
         }
         container plcp-statistics {
           leaf ferr-count {
             type int32;
           }
           leaf ferr-seconds {
             type int32;
           }
           leaf bipe-count {
             type int32;
           }
           leaf bipe-seconds {
             type int32;
           }
           leaf febe-count {
             type int32;
           }
           leaf febe-seconds {
             type int32;
           }
         }
         container atm-statistics {
           leaf uncorrectable-hcs-errors {
             type int32;
           }
           leaf correctable-hcs-errors {
             type int32;
           }
           leaf tx-cell-fifo-overruns {
             type int32;
           }
           leaf rx-cell-fifo-overruns {
             type int32;
           }
           leaf rx-cell-fifo-underruns {
             type int32;
           }
           leaf rx-cell-count {
             type int32;
           }
           leaf tx-cell-count {
             type int32;
           }
           leaf tx-idle-cell-count {
             type int32;
           }
           leaf vc-queue-drops {
             type int32;
           }
           leaf no-buffers {
             type int32;
           }
           leaf length-errors {
             type int32;
           }
           leaf timeouts {
             type int32;
           }
           leaf bundle-timeouts {
             type int32;
           }
           leaf rx-invalid-vcs {
             type int32;
           }
           leaf bad-crcs {
             type int32;
           }
           leaf oam-cell-no-buffers {
             type int32;
           }
         }
       }
       container modem-information {
         description
           "Operational information for MODEM interfaces";
         leaf modem-type {
           type string;
           description
             "Modem type information";
         }
         leaf init-command-str {
           type string;
           description
             "Modem initialization command string";
         }
         leaf init-status {
           type string;
           description
             "Modem initialization status";
         }
         leaf call-status {
           type string;
           description
             "Current status of call";
         }
         leaf call-duration {
           type int32;
           description
             "Duration for which call has been on";
         }
         leaf call-direction {
           type string;
           description
             "Direction of call (incoming or outgoing)";
         }
         leaf baud-rate {
           type int32;
           description
             "Modem baud rate";
         }
         leaf error-code {
           type string;
           description
             "Error string as returned by modem";
         }
       }
       container serial-information {
         description
           "Serial interfaces information and statistics";
         leaf serial-information.heading {
           type string;
           description
             "Serial interfaces information and statistics";
         }
         leaf dce-loopback-override {
           type string;
         }
         container line-protocol {
           leaf line-protocol-mode {
             type string;
           }
         }
         container resync-history {
           leaf resync-counter {
             type int32;
           }
           leaf resync-timestamp {
             type string;
           }
         }
         container clocking-mode {
           leaf clock-mode {
             type string;
           }
         }
         container clocking-rate {
           leaf clock-rate {
             type string;
             description
               "Interface clock rate";
           }
         }
         container serial-encoding {
           leaf serial-encoding-conf {
             type string;
           }
         }
         container dtr-circuit {
           leaf dtr-circuit-mode {
             type string;
           }
         }
         container eia530-signal-polarity {
           leaf dtr-polarity {
             type string;
           }
           leaf rts-polarity {
             type string;
           }
           leaf dcd-polarity {
             type string;
           }
           leaf dsr-polarity {
             type string;
           }
           leaf cts-polarity {
             type string;
           }
           leaf tm-polarity {
             type string;
           }
         }
         container x21-signal-polarity {
           leaf rts-polarity {
             type string;
           }
           leaf cts-polarity {
             type string;
           }
         }
         container serial-loopback {
           leaf serial-loopback-mode {
             type string;
           }
         }
         container tx-clock {
           leaf tx-clock-mode {
             type string;
           }
         }
         container data-signal {
           leaf rx-clock {
             type string;
           }
         }
         container eia530-control-signal {
           leaf mode {
             type string;
           }
           container to-dce {
             leaf dtr {
               type string;
             }
             leaf rts {
               type string;
             }
             leaf cts {
               type string;
             }
             leaf dcd {
               type string;
             }
             leaf dsr {
               type string;
             }
           }
           container from-dce {
             leaf dtr {
               type string;
             }
             leaf rts {
               type string;
             }
             leaf cts {
               type string;
             }
             leaf dcd {
               type string;
             }
             leaf dsr {
               type string;
             }
             leaf tm {
               type string;
             }
           }
           container to-dte {
             leaf dtr {
               type string;
             }
             leaf rts {
               type string;
             }
             leaf cts {
               type string;
             }
             leaf dcd {
               type string;
             }
             leaf dsr {
               type string;
             }
           }
           container from-dte {
             leaf dtr {
               type string;
             }
             leaf rts {
               type string;
             }
             leaf cts {
               type string;
             }
             leaf dcd {
               type string;
             }
             leaf dsr {
               type string;
             }
             leaf tm {
               type string;
             }
           }
         }
         container x21-control-signal {
           leaf rts {
             type string;
           }
           leaf cts {
             type string;
           }
         }
       }
       container virtual-path-information {
         description
           "Operational information and statistics for a virtual path";
         leaf vpi {
           type int32;
           description
             "Virtual path identifier";
         }
         leaf atm-tm-cbr {
           type empty;
           description
             "Constant bit rate";
         }
         leaf atm-tm-vbr {
           type empty;
           description
             "Variable bit rate";
         }
         leaf atm-tm-rtvbr {
           type empty;
           description
             "Real-time variable bit rate";
         }
         leaf peak {
           type int32;
         }
         leaf sustained {
           type int32;
         }
         leaf burst {
           type int32;
         }
         leaf queue-limit {
           type int32;
         }
         leaf down-time {
           type int32;
           description
             "Total down time for this circuit";
         }
         leaf last-down-time {
           type int32;
           description
             "Time elapsed since circuit last went down";
         }
         leaf cdvt {
           type int32;
         }
         container ifvp-flags {
           leaf ifvp-down {
             type empty;
           }
           leaf ifvp-none {
             type empty;
           }
           leaf ifvp-active {
             type empty;
           }
           leaf ifvp-closed {
             type empty;
           }
           leaf ifvp-oam {
             type empty;
           }
           leaf ifvp-shaping {
             type empty;
           }
           leaf ifvp-passiveoam {
             type empty;
           }
           leaf ifvp-tunnel {
             type empty;
           }
           leaf generic-value {
             type int32;
             description
               "Hexadecimal value of unknown flag bits";
           }
         }
         container oam-parameters {
           leaf period {
             type int32;
           }
           leaf up-count {
             type int32;
           }
           leaf down-count {
             type int32;
           }
         }
         container oam-statistics {
           description
             "Container tag for OAM statistics";
           leaf oam-total-received-count {
             type int32;
           }
           leaf oam-total-transmitted-count {
             type int32;
           }
           leaf oam-loopback-received-count {
             type int32;
           }
           leaf oam-loopback-transmitted-count {
             type int32;
           }
           leaf oam-loopback-received-last {
             type string;
           }
           leaf oam-loopback-transmitted-last {
             type string;
           }
           leaf oam-rdi-received-count {
             type int32;
           }
           leaf oam-rdi-transmitted-count {
             type int32;
           }
           leaf oam-rdi-received-last {
             type string;
           }
           leaf oam-rdi-transmitted-last {
             type string;
           }
           leaf oam-ais-received-count {
             type int32;
           }
           leaf oam-ais-transmitted-count {
             type int32;
           }
           leaf oam-ais-received-last {
             type string;
           }
           leaf oam-ais-transmitted-last {
             type string;
           }
         }
         container traffic-statistics {
           leaf input-bps {
             type int32;
           }
           leaf input-pps {
             type int32;
           }
           leaf output-bps {
             type int32;
           }
           leaf output-pps {
             type int32;
           }
           leaf input-packets {
             type uint64;
           }
           leaf output-packets {
             type uint64;
           }
           container ipv4-traffic-statistics {
             leaf input-bps {
               type int32;
             }
             leaf output-bps {
               type int32;
             }
             leaf input-pps {
               type int32;
             }
             leaf output-pps {
               type int32;
             }
             leaf input-bytes {
               type int32;
             }
             leaf output-bytes {
               type int32;
             }
             leaf input-packets {
               type uint64;
             }
             leaf output-packets {
               type uint64;
             }
           }
           leaf input-bytes {
             type int32;
           }
           leaf output-bytes {
             type int32;
           }
           container ipv6-transit-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-traffic-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-total-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
         }
       }
       container ct3-information {
         list interface-tx-queue {
           key "name";
           leaf name {
             type string;
             description
               "Name of this item";
           }
           leaf bandwidth {
             type string;
           }
           leaf wrr {
             type string;
           }
           leaf output-packets {
             type uint64;
           }
           leaf output-bytes {
             type int32;
           }
           leaf output-drops {
             type int32;
           }
           leaf output-errors {
             type int32;
           }
           leaf output-drops-bytes {
             type int32;
           }
         }
       }
       container cds1-information {
         list interface-tx-queue {
           key "name";
           leaf name {
             type string;
             description
               "Name of this item";
           }
           leaf bandwidth {
             type string;
           }
           leaf wrr {
             type string;
           }
           leaf output-packets {
             type uint64;
           }
           leaf output-bytes {
             type int32;
           }
           leaf output-drops {
             type int32;
           }
           leaf output-errors {
             type int32;
           }
           leaf output-drops-bytes {
             type int32;
           }
         }
       }
       container nxds0-information {
         list interface-tx-queue {
           key "name";
           leaf name {
             type string;
             description
               "Name of this item";
           }
           leaf bandwidth {
             type string;
           }
           leaf wrr {
             type string;
           }
           leaf output-packets {
             type uint64;
           }
           leaf output-bytes {
             type int32;
           }
           leaf output-drops {
             type int32;
           }
           leaf output-errors {
             type int32;
           }
           leaf output-drops-bytes {
             type int32;
           }
         }
       }
       container dsu-information {
         description
           "DSU configuration and statistics";
         leaf dsu-compatibility-mode {
           type string;
         }
         leaf dsu-scrambler {
           type string;
         }
         leaf dsu-subrate {
           type string;
         }
         leaf feac-loopback {
           type string;
         }
         leaf feac-response {
           type string;
         }
         leaf feac-count {
           type int32;
         }
       }
       container ds3-bert-information {
         description
           "DS3 BERT configuration and statistics";
         leaf ds3-bert-period {
           type int32;
         }
         leaf ds3-bert-elapsed {
           type int32;
         }
         leaf ds3-bert-status {
           type string;
         }
         leaf ds3-bert-algorithm {
           type string;
         }
         leaf ds3-bert-induced-error-rate {
           type int32;
         }
         leaf ds3-bert-bit-count {
           type int32;
         }
         leaf ds3-bert-bit-count-overflow {
           type int32;
         }
         leaf ds3-bert-error-bit-count {
           type int32;
         }
         leaf ds3-bert-error-bit-count-overflow {
           type int32;
         }
         leaf ds3-bert-error-rate {
           type string;
         }
         leaf ds3-bert-los-status {
           type string;
         }
         leaf ds3-bert-los-count {
           type int32;
         }
         leaf ds3-bert-los-seconds {
           type int32;
         }
       }
       container e3-bert-information {
         description
           "E3 BERT configuration and statistics";
         leaf e3-bert-period {
           type int32;
         }
         leaf e3-bert-elapsed {
           type int32;
         }
         leaf e3-bert-status {
           type string;
         }
         leaf e3-bert-algorithm {
           type string;
         }
         leaf e3-bert-induced-error-rate {
           type int32;
         }
         leaf e3-bert-bit-count {
           type int32;
         }
         leaf e3-bert-bit-count-overflow {
           type int32;
         }
         leaf e3-bert-error-bit-count {
           type int32;
         }
         leaf e3-bert-error-bit-count-overflow {
           type int32;
         }
         leaf e3-bert-error-rate {
           type string;
         }
         leaf e3-bert-los-status {
           type string;
         }
         leaf e3-bert-los-count {
           type string;
         }
         leaf e3-bert-los-seconds {
           type string;
         }
       }
       container ds1-bert-information {
         description
           "DS1 BERT configuration and statistics";
         leaf ds1-bert-period {
           type int32;
         }
         leaf ds1-bert-elapsed {
           type int32;
         }
         leaf ds1-bert-status {
           type string;
         }
         leaf ds1-bert-induced-error-rate {
           type int32;
         }
         leaf ds1-bert-algorithm {
           type string;
         }
         leaf ds1-bert-bit-count {
           type int32;
         }
         leaf ds1-bert-error-bit-count {
           type int32;
         }
         leaf ds1-bert-error-rate {
           type string;
         }
         leaf ds1-bert-los-status {
           type string;
         }
         leaf ds1-bert-los-count {
           type int32;
         }
         leaf ds1-bert-los-seconds {
           type int32;
         }
       }
       container ds0-bert-information {
         description
           "DS0 BERT configuration and statistics";
         leaf ds0-bert-period {
           type int32;
         }
         leaf ds0-bert-elapsed {
           type int32;
         }
         leaf ds0-bert-status {
           type string;
         }
         leaf ds0-bert-induced-error-rate {
           type int32;
         }
         leaf ds0-bert-algorithm {
           type string;
         }
         leaf ds0-bert-bit-count {
           type int32;
         }
         leaf ds0-bert-error-bit-count {
           type int32;
         }
         leaf ds0-bert-error-rate {
           type string;
         }
         leaf ds0-bert-los-status {
           type string;
         }
         leaf ds0-bert-los-count {
           type int32;
         }
         leaf ds0-bert-los-seconds {
           type int32;
         }
       }
       container hdlc-information {
         leaf hdlc-rx-bucket-state {
           type string;
         }
         leaf hdlc-rx-bit-rate {
           type int32;
         }
         leaf hdlc-rx-threshold {
           type int32;
         }
         leaf hdlc-tx-bucket-state {
           type string;
         }
         leaf hdlc-tx-bit-rate {
           type int32;
         }
         leaf hdlc-tx-threshold {
           type int32;
         }
         leaf hdlc-giant-threshold {
           type int32;
         }
         leaf hdlc-runt-threshold {
           type int32;
         }
       }
       container pfe-information {
         description
           "Information about Packet Forwarding Engine configuration";
         leaf destination-slot {
           type int32;
         }
         leaf destination-mask {
           type int32;
         }
         leaf stream-number {
           type int32;
         }
         leaf stream-mask {
           type int32;
         }
         leaf plp-byte-count {
           type int32;
         }
         leaf plp-byte {
           type string;
         }
         leaf pop-all-label {
           type string;
         }
       }
       list logical-interface {
         key "name";
         description
           "Information about a single logical interface";
         leaf lcp-state {
           type string;
           description
             "State of the Line Control Protocol";
         }
         leaf chap-state {
           type string;
           description
             "State of the Challenge Handshake Authentication Protocol";
         }
         leaf pap-state {
           type string;
           description
             "State of the Password Authentication Protocol";
         }
         leaf name {
           type string;
           description
             "Name of this item";
         }
         leaf local-index {
           type int32;
           description
             "Local kernel index for this interface";
         }
         leaf snmp-index {
           type int32;
           description
             "SNMP ifIndex for this interface";
         }
         leaf hardware-token {
           type int32;
           description
             "Hardware token for layer 3 ifl";
         }
         leaf generation {
           type string;
           description
             "Generation number used to distinguish between successive 
             instances of this interface";
         }
         leaf description {
           type string;
           description
             "Description of this interface";
         }
         leaf multilink-flapped {
           type string;
           description
             "Time when the interface last flapped";
         }
         leaf logical-interface-bandwidth {
           type string;
           description
             "Bandwidth of this logical interface";
         }
         leaf link-address {
           type string;
           description
             "Link address on this logical interface";
         }
         leaf unmatched-ifl {
           type string;
         }
         leaf encapsulation {
           type string;
           description
             "Encapsulation on the logical interface";
         }
         leaf dont-fragment {
           type string;
           description
             "Dont fragment on the logical interface";
         }
         leaf dont-decrement-ttl {
           type string;
           description
             "Dont decrement TTL";
         }
         leaf propagate-dscp {
           type string;
           description
             "Propagate DSCP field";
         }
         leaf propagate-ecn {
           type string;
           description
             "Propagate ECN field";
         }
         leaf esi-value {
           type string;
           description
             "Ethernet segment identifier for this interface";
         }
         leaf esi-mode {
           type string;
           description
             "Ethernet segment mode for this interface";
         }
         leaf evpn-multihomed-status {
           type string;
         }
         leaf virtual-gateway-esi-value {
           type string;
           description
             "Ethernet segment identifier for this interface";
         }
         leaf virtual-gateway-esi-mode {
           type string;
           description
             "Ethernet segment mode for this interface";
         }
         leaf interface-set-name {
           type string;
           description
             "Interface set on the logical interface";
         }
         leaf tenant-name {
           type string;
           description
             "Tenant name assigned to logical interface";
         }
         leaf demux-table-type {
           type string;
           description
             "Demux table enabled on the logical interface";
         }
         leaf gre-keepalive-configured {
           type string;
           description
             "Gre Keepalives enabled on the logical interface";
         }
         leaf gre-keepalive-adj-state {
           type string;
           description
             "Gre Keepalives enabled on the logical interface";
         }
         leaf copy-tos-to-outer-ip-header {
           type string;
           description
             "Flag that enables copying of the value in the ToS field of the
             IP packet's payload header to the delivery header in the 
             generic routingencapsulation packet";
         }
         leaf copy-tos-to-outer-ip-header-transit {
           type string;
           description
             "Flag that enables copying of the value in the ToS field of the
             IP packet's payload header to the delivery header in the 
             generic routing encapsulation transit packet";
         }
         leaf force-control-packets-on-transit-path {
           type string;
           description
             "Flag that enables forcing control traffic to follow transit 
             path encapsulation packet";
         }
         leaf redundant-logical-interface-name {
           type string;
           description
             "Name of the redundant logical interface";
         }
         leaf logical-interface-mac {
           type string;
           description
             "MAC on the logical interface";
         }
         leaf logical-interface-vgw-v4-mac {
           type string;
           description
             "MAC on the logical interface";
         }
         leaf logical-interface-vgw-v6-mac {
           type string;
           description
             "MAC on the logical interface";
         }
         leaf logical-interface-zone-name {
           type string;
           description
             "Zone name for this interface";
         }
         leaf subunit {
           type int32;
           description
             "Subunit for this interface";
         }
         leaf dialer-time-to-disconnect {
           type string;
           description
             "Time for dialer to disconnect due to idle timeout";
         }
         container if-config-flags {
           leaf iff-none {
             type empty;
           }
           leaf iff-hardware-down {
             type empty;
           }
           leaf iff-down {
             type empty;
           }
           leaf iff-up {
             type empty;
           }
           leaf iff-admin-down {
             type empty;
           }
           leaf iff-admin-up {
             type empty;
           }
           leaf iff-link-down {
             type empty;
           }
           leaf iff-device-down {
             type empty;
           }
           leaf iff-point-to-point {
             type empty;
           }
           leaf iff-point-to-multipoint {
             type empty;
           }
           leaf plp-to-clp {
             type empty;
           }
           leaf iff-multiaccess {
             type empty;
           }
           leaf iff-change {
             type empty;
           }
           leaf iff-inverse-arp {
             type empty;
           }
           leaf iff-no-multicast {
             type empty;
           }
           leaf iff-multicast {
             type empty;
           }
           leaf iff-promiscuous {
             type empty;
           }
           leaf iff-all-multicast {
             type empty;
           }
           leaf iff-snmp-traps {
             type empty;
           }
           leaf iff-no-forwarding-viable {
             type empty;
           }
           leaf iff-macsec {
             type empty;
           }
           leaf iff-secure {
             type empty;
           }
           leaf iff-rx-passive {
             type empty;
           }
           leaf iff-tx-passive {
             type empty;
           }
           leaf iff-ccc-down {
             type empty;
           }
           leaf iff-clear-df {
             type empty;
           }
           leaf iff-tunnel-reassembly {
             type empty;
           }
           leaf iff-acfc {
             type empty;
           }
           leaf iff-pfc {
             type empty;
           }
           leaf iff-rdd {
             type empty;
           }
           leaf iff-looped {
             type empty;
           }
           leaf iff-framing-conflict {
             type empty;
           }
           leaf internal-flags {
             type string;
             description
               "Hexadecimal value of internal flag bits";
           }
         }
         container layer2-input-policer-information {
           description
             "Information about Layer 2 input policer for interface";
           leaf layer2-input-policer {
             type string;
             description
               "Name of the Layer 2 input policer";
           }
         }
         container layer2-output-policer-information {
           description
             "Information about Layer 2 output policer for interface";
           leaf layer2-output-policer {
             type string;
             description
               "Name of the Layer 2 output policer";
           }
         }
         container atm-input-policer-information {
           description
             "Information about atm input policer for interface";
           leaf atm-input-policer {
             type string;
             description
               "Name of the atm input policer";
           }
         }
         container pppoe-information {
           description
             "PPPoE information";
           list pppoe-interface {
             leaf state {
               type string;
               description
                 "State";
             }
             leaf session-id {
               type string;
               description
                 "Session ID";
             }
             leaf ac-name-session {
               type string;
               description
                 "Session AC name";
             }
             leaf remote-mac {
               type string;
               description
                 "Remote MAC address";
             }
             leaf ac-name-config {
               type string;
               description
                 "Configured AC name";
             }
             leaf service-name {
               type string;
               description
                 "Service name";
             }
             leaf auto-reconnect {
               type string;
               description
                 "Autoreconnect timeout";
             }
             leaf idle-timeout {
               type string;
               description
                 "Idle timeout";
             }
             leaf underlying-interface-name {
               type string;
               description
                 "Underlying interface name";
             }
             leaf underlying-interface-index {
               type string;
               description
                 "Underlying interface index";
             }
             leaf padg-credits {
               type int32;
               description
                 "PADG transmit credits";
             }
             leaf pppoe-credit-scale-factor {
               type string;
               description
                 "Scaling factor";
             }
             leaf ignore-eol-tag {
               type string;
               description
                 "Ignore End-of-List TAG";
             }
             leaf ppp-max-payload-tag {
               type int32;
               description
                 "PPP-Max-Payload TAG";
             }
             leaf interface-name {
               type string;
               description
                 "Interface name";
             }
             leaf interface-index {
               type string;
               description
                 "Index";
             }
             leaf aci-iflset-name {
               type string;
               description
                 "ACI Interface Set name";
             }
             leaf aci-iflset-index {
               type string;
               description
                 "ACI Interface Set index";
             }
             leaf ifl-type {
               type string;
               description
                 "Type";
             }
             leaf session-uptime {
               type string;
               description
                 "Duration for which the session has been up";
             }
             leaf dynamic-profile {
               type string;
               description
                 "Dynamic Profile name";
             }
             leaf pppoe-credits {
               type string;
               description
                 "Forwarding credit balances";
             }
             leaf dynamic-interface-bandwidth {
               type string;
               description
                 "Dynamic interface bandwidth";
             }
             leaf agent-circuit-id {
               type string;
               description
                 "Agent Circuit ID";
             }
             leaf agent-remote-id {
               type string;
               description
                 "Agent Remote ID";
             }
             leaf padm-motm {
               type string;
               description
                 "PADM Message of the Moment tag";
             }
             leaf padm-hurl {
               type string;
               description
                 "PADM HTTP URL tag";
             }
             leaf pppoe-relay-session-id {
               type string;
               description
                 "PPPoE Relay Session ID";
             }
           }
         }
         container pppoe-underlying-information {
           description
             "PPPoE Underlying information";
           list pppoe-underlying-interface {
             leaf dynamic-profile {
               type string;
               description
                 "Dynamic Profile name";
             }
             leaf service-name-table {
               type string;
               description
                 "Name of Service Name Table";
             }
             leaf max-sessions {
               type int32;
               description
                 "Maximum number of PPPoE sessions";
             }
             leaf max-sessions-vsa-ignore {
               type string;
               description
                 "Ignore max-sessions VSA";
             }
             leaf duplicate-protection {
               type string;
               description
                 "Duplicate protection mode";
             }
             leaf short-cycle-protection {
               type string;
               description
                 "Short cycle protection mode";
             }
             leaf direct-connect {
               type string;
               description
                 "Direct connect mode";
             }
             leaf ac-name {
               type string;
               description
                 "Access Concentrator name";
             }
             leaf underlying-interface-name {
               type string;
               description
                 "Underlying interface name";
             }
             leaf underlying-interface-index {
               type string;
               description
                 "Underlying interface index";
             }
             leaf encapsulation-type-identifier {
               type string;
               description
                 "Encapsulation type identifier";
             }
             leaf state {
               type string;
               description
                 "State";
             }
             leaf active-sessions {
               type int32;
               description
                 "Number of active PPPoE sessions";
             }
             leaf aci-autosensing {
               type string;
               description
                 "ACI VLAN Autosensing mode";
             }
             leaf line-identity-autosensing {
               type string;
               description
                 "Line Identity Autosensing mode";
             }
           }
         }
         container aci-vlan-information {
           leaf dynamic-profile {
             type string;
             description
               "Dynamic Profile name";
           }
         }
         container line-identity-information {
           leaf dynamic-profile {
             type string;
             description
               "Dynamic Profile name";
           }
           leaf circuit-id {
             type string;
             description
               "Aci vlan attribute";
           }
           leaf remote-id {
             type string;
             description
               "Aci vlan attribute";
           }
           leaf accept-no-ids {
             type string;
             description
               "Aci vlan attribute";
           }
         }
         container demux-information {
           description
             "Demux information";
           container demux-interface {
             leaf demux-underlying-interface-name {
               type string;
               description
                 "Underlying interface name";
             }
             leaf demux-underlying-interface-index {
               type string;
               description
                 "Underlying interface index";
             }
             leaf demux-inet-prefix-type {
               type string;
               description
                 "Prefix type";
             }
             leaf demux-inet-prefix-count {
               type string;
               description
                 "IPv4 Prefix count";
             }
             leaf demux-inet-prefix {
               type string;
               description
                 "IPv4 Prefix";
             }
             leaf demux-inet6-prefix-type {
               type string;
               description
                 "Prefix type";
             }
             leaf demux-inet6-prefix-count {
               type string;
               description
                 "IPv6 Prefix count";
             }
             leaf demux-inet6-prefix {
               type string;
               description
                 "IPv6 Prefix";
             }
           }
         }
         container dual-ad-icl-color-information {
           container dual-ad-icl-color-info {
             description
               "Dual-AD ICL Color Information";
             leaf dual-ad-icl-color-type {
               type uint32;
               description
                 "Dual-AD ICL Color Type";
             }
             leaf dual-ad-icl-color {
               type uint32;
               description
                 "Dual-AD ICL Color";
             }
           }
         }
         container dialer-information {
           description
             "Dialer information";
           leaf dialer-time-to-disconnect {
             type string;
             description
               "Time for dialer to disconnect due to idle timeout";
           }
           container dialer-interface {
             list dial-string-list {
               leaf dial-string {
                 type string;
                 description
                   "Dial string";
               }
             }
             list sub-interface-list {
               leaf sub-interface-name {
                 type string;
                 description
                   "Subordinate interface name";
               }
             }
             list watch-list {
               leaf watch-route {
                 type string;
                 description
                   "Watch route";
               }
             }
           }
         }
         container shared-interface-information {
           description
             "Shared interface information";
           container shared-interface-logical-interface {
             description
               "Shared interface logical interface";
             leaf peer-interface-name {
               type string;
               description
                 "Peer interface name";
             }
             leaf interface-shared-with {
               type string;
               description
                 "Logical interface owner";
             }
             leaf rx-fe {
               type string;
               description
                 "Rx tunnel token forwarding element";
             }
             leaf rx-nhid {
               type string;
               description
                 "Rx tunnel token next hop index";
             }
             leaf tx-fe {
               type string;
               description
                 "Tx tunnel token forwarding element";
             }
             leaf tx-nhid {
               type string;
               description
                 "Tx tunnel token next hop index";
             }
           }
         }
         container mac-database {
           leaf number-of-mac-record {
             type int32;
           }
           list mac-record {
             leaf mac-address {
               type jt:mac-addr;
             }
             leaf receive-frames {
               type int32;
             }
             leaf receive-bytes {
               type int32;
             }
             leaf transmit-frames {
               type int32;
             }
             leaf transmit-bytes {
               type int32;
             }
           }
         }
         container policer-overhead {
           description
             "Policer overhead information";
           leaf ingress-policer-overhead {
             type int32;
             description
               "Ingress policer overhead information";
           }
           leaf egress-policer-overhead {
             type int32;
             description
               "Egress policer overhead information";
           }
         }
         container queue-counters {
           description
             "Queue counter statistics";
           leaf queue-counters-error-message {
             type string;
             description
               "Queue statistics not available for this interface";
           }
           list queue {
             key "queue-number";
             description
               "Counters for a single queue";
             leaf queue-number {
               type uint32;
               description
                 "Queue number";
             }
             leaf queue-counters-queued-packets {
               type int32;
               description
                 "Queued packet count";
             }
             leaf queue-counters-trans-packets {
               type int32;
               description
                 "Total number of transmitted packets";
             }
             leaf queue-counters-total-drop-packets {
               type int32;
               description
                 "Number of total packets dropped at the queue";
             }
             leaf forwarding-class-name {
               type string;
               description
                 "Forwarding class name associated with queue";
             }
             leaf queue-counters-queued-packets-rate {
               type int32;
               description
                 "Rate at which packets are queued";
             }
             leaf queue-counters-queued-bytes {
               type int32;
               description
                 "Queued bytes count";
             }
             leaf queue-counters-queued-bytes-rate {
               type int32;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets-rate {
               type int32;
               description
                 "Rate at which packets are transmitted";
             }
             leaf queue-counters-trans-bytes {
               type int32;
               description
                 "Total number of transmitted bytes";
             }
             leaf queue-counters-trans-bytes-rate {
               type int32;
               description
                 "Rate at which bytes are transmitted";
             }
             leaf queue-counters-tail-drop-packets-na {
               type string;
               description
                 "Number of packets dropped due to tail drop not available";
             }
             leaf queue-counters-tail-drop-packets {
               type int32;
               description
                 "Number of packets dropped at the tail of the queue";
             }
             leaf queue-counters-tail-drop-packets-rate {
               type int32;
               description
                 "Rate at which packets are dropped at tail of queue";
             }
             leaf queue-counters-tail-drop-bytes {
               type int32;
               description
                 "Number of packets dropped at tail drop of the queue";
             }
             leaf queue-counters-tail-drop-bytes-rate {
               type int32;
               description
                 "Number of packets dropped at tail drop of the queue";
             }
             leaf queue-counters-ecn-ce-packets {
               type int32;
               description
                 "Total number of ECN CE packets";
             }
             leaf queue-counters-ecn-ce-packets-rate {
               type int32;
               description
                 "Rate at which ECN CE packets are transmitted";
             }
             leaf queue-counters-ecn-ce-bytes {
               type int32;
               description
                 "Total number of ECN CE bytes";
             }
             leaf queue-counters-ecn-ce-bytes-rate {
               type int32;
               description
                 "Rate at which ECN CE bytes are transmitted";
             }
             leaf queue-counters-rate-limit-drop-packets-na {
               type string;
               description
                 "Number of packets dropped due to rate-limit drop not 
                 available";
             }
             leaf queue-counters-rate-limit-drop-packets {
               type int32;
               description
                 "Number of packets dropped by rate-limit for the queue";
             }
             leaf queue-counters-rate-limit-drop-packets-rate {
               type int32;
               description
                 "Rate at which packets are dropped by rate-limit for the 
                 queue";
             }
             leaf queue-counters-rate-limit-drop-bytes-na {
               type string;
               description
                 "Number of bytes dropped due to tail drop not available";
             }
             leaf queue-counters-rate-limit-drop-bytes {
               type int32;
               description
                 "Number of bytes dropped at the tail of the queue";
             }
             leaf queue-counters-rate-limit-drop-bytes-rate {
               type int32;
               description
                 "Rate at which bytes are dropped at the tail of the queue";
             }
             leaf queue-counters-red-packets-na {
               type string;
               description
                 "Number of packets dropped due to RED not available";
             }
             leaf queue-counters-red-packets {
               type int32;
               description
                 "Number of packets dropped due to RED";
             }
             leaf queue-counters-red-packets-rate {
               type int32;
               description
                 "Rate at which packets are dropped due to RED";
             }
             leaf queue-counters-red-packets-ln {
               type int32;
               description
                 "Number of RED dropped low-loss, non-TCP packets";
             }
             leaf queue-counters-red-packets-rate-ln {
               type int32;
               description
                 "RED drop rate for low-loss, non-TCP packets";
             }
             leaf queue-counters-red-packets-lt {
               type int32;
               description
                 "Number of RED dropped of low-loss, TCP packets";
             }
             leaf queue-counters-red-packets-rate-lt {
               type int32;
               description
                 "RED drop rate for low-loss, TCP packets";
             }
             leaf queue-counters-red-packets-hn {
               type int32;
               description
                 "Number of RED dropped high-loss, non-TCP packets";
             }
             leaf queue-counters-red-packets-rate-hn {
               type int32;
               description
                 "RED drop rate for high-loss, non-TCP packets";
             }
             leaf queue-counters-red-packets-ht {
               type int32;
               description
                 "Number of RED dropped high-loss, TCP packets";
             }
             leaf queue-counters-red-packets-rate-ht {
               type int32;
               description
                 "RED drop rate for high-loss, TCP packets";
             }
             leaf queue-counters-red-packets-low {
               type int32;
               description
                 "Number of RED dropped low-loss packets";
             }
             leaf queue-counters-red-packets-rate-low {
               type int32;
               description
                 "RED drop rate for low-loss packets";
             }
             leaf queue-counters-red-packets-medium-low {
               type int32;
               description
                 "Number of RED dropped medium-low-loss packets";
             }
             leaf queue-counters-red-packets-rate-medium-low {
               type int32;
               description
                 "RED drop rate for medium-low-loss packets";
             }
             leaf queue-counters-red-packets-medium-high {
               type int32;
               description
                 "Number of RED dropped medium-high-loss packets";
             }
             leaf queue-counters-red-packets-rate-medium-high {
               type int32;
               description
                 "RED drop rate for medium-high-loss packets";
             }
             leaf queue-counters-red-packets-medium {
               type int32;
               description
                 "Number of RED dropped medium-loss packets";
             }
             leaf queue-counters-red-packets-rate-medium {
               type int32;
               description
                 "RED drop rate for medium-loss packets";
             }
             leaf queue-counters-red-packets-high {
               type int32;
               description
                 "Number of RED dropped high-loss packets";
             }
             leaf queue-counters-red-packets-rate-high {
               type int32;
               description
                 "RED drop rate for high-loss packets";
             }
             leaf queue-counters-red-bytes-na {
               type string;
               description
                 "Number of bytes dropped due to RED not available";
             }
             leaf queue-counters-red-bytes {
               type int32;
               description
                 "Number of bytes dropped due to RED";
             }
             leaf queue-counters-red-bytes-rate {
               type int32;
               description
                 "Rate at which bytes are dropped due to RED";
             }
             leaf queue-counters-red-bytes-ln {
               type int32;
               description
                 "Number of RED dropped low-loss, non-TCP bytes";
             }
             leaf queue-counters-red-bytes-rate-ln {
               type int32;
               description
                 "RED drop rate for low-loss, non-TCP bytes";
             }
             leaf queue-counters-red-bytes-lt {
               type int32;
               description
                 "Number of RED dropped low-loss, TCP bytes";
             }
             leaf queue-counters-red-bytes-rate-lt {
               type int32;
               description
                 "RED drop rate for low-loss, TCP bytes";
             }
             leaf queue-counters-red-bytes-hn {
               type int32;
               description
                 "Number of RED dropped high-loss, non-TCP bytes";
             }
             leaf queue-counters-red-bytes-rate-hn {
               type int32;
               description
                 "RED drop rate for high-loss, non-TCP bytes";
             }
             leaf queue-counters-red-bytes-ht {
               type int32;
               description
                 "Number of RED dropped high-loss, TCP bytes";
             }
             leaf queue-counters-red-bytes-rate-ht {
               type int32;
               description
                 "RED drop rate for high-loss, TCP bytes";
             }
             leaf queue-counters-red-bytes-low {
               type int32;
               description
                 "Number of RED dropped low-loss bytes";
             }
             leaf queue-counters-red-bytes-rate-low {
               type int32;
               description
                 "RED drop rate for low-loss bytes";
             }
             leaf queue-counters-red-bytes-medium-low {
               type int32;
               description
                 "Number of RED dropped medium-low-loss bytes";
             }
             leaf queue-counters-red-bytes-rate-medium-low {
               type int32;
               description
                 "RED drop rate for medium-low-loss bytes";
             }
             leaf queue-counters-red-bytes-medium-high {
               type int32;
               description
                 "Number of RED dropped medium-high-loss bytes";
             }
             leaf queue-counters-red-bytes-rate-medium-high {
               type int32;
               description
                 "RED drop rate for medium-high-loss bytes";
             }
             leaf queue-counters-red-bytes-medium {
               type int32;
               description
                 "Number of RED dropped medium-loss bytes";
             }
             leaf queue-counters-red-bytes-rate-medium {
               type int32;
               description
                 "RED drop rate for medium-loss bytes";
             }
             leaf queue-counters-red-bytes-high {
               type int32;
               description
                 "Number of RED dropped high-loss bytes";
             }
             leaf queue-counters-red-bytes-rate-high {
               type int32;
               description
                 "RED drop rate for high-loss bytes";
             }
             leaf queue-counters-timestamp {
               type int32;
               description
                 "Last packet enqueued timestamp";
             }
             leaf queue-counters-total-drop-packets-rate {
               type int32;
               description
                 "Number of total packets dropped at the queue";
             }
             leaf queue-counters-total-drop-bytes {
               type int32;
               description
                 "Number of total packets dropped at the queue";
             }
             leaf queue-counters-total-drop-bytes-rate {
               type int32;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
           container interface-cos-short-summary {
             description
               "Summary of queue information on an interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
         }
         container voq-counters {
           description
             "VOQ counter statistics";
           leaf voq-counters-error-message {
             type string;
             description
               "VOQ statistics not available for this interface";
           }
           container voq {
             description
               "Counters for a single voq";
             container fpc {
               description
                 "Counters for a single FPC";
               leaf fpc-no {
                 type int32;
                 description
                   "FPC number";
               }
               container pfe {
                 description
                   "Counters for a single PFE";
                 leaf-list pfe-no {
                   type int32;
                   description
                     "PFE number";
                 }
                 leaf voq-counters-tail-drop-packets {
                   type int32;
                   description
                     "Tail DROP packet count";
                 }
                 leaf voq-counters-tail-drop-packets-rate {
                   type int32;
                   description
                     "Rate at which tail packets are dropped";
                 }
                 leaf voq-counters-tail-drop-bytes {
                   type int32;
                   description
                     "Tail DROP bytes count";
                 }
                 leaf voq-counters-tail-drop-bytes-rate {
                   type int32;
                   description
                     "Rate at which tail bytes are dropped";
                 }
                 leaf voq-counters-drop-packets {
                   type int32;
                   description
                     "DROP packet count";
                 }
                 leaf voq-counters-drop-packets-rate {
                   type int32;
                   description
                     "Rate at which packets are dropped";
                 }
                 leaf voq-counters-drop-bytes {
                   type int32;
                   description
                     "DROP bytes count";
                 }
                 leaf voq-counters-drop-bytes-rate {
                   type int32;
                   description
                     "Rate at which bytes are dropped";
                 }
                 leaf voq-counters-queued-packets {
                   type int32;
                   description
                     "QUEUED packets count";
                 }
                 leaf voq-counters-queued-packets-rate {
                   type int32;
                   description
                     "Rate at which packets are queued";
                 }
                 leaf voq-counters-queued-bytes {
                   type int32;
                   description
                     "QUEUED bytes count";
                 }
                 leaf voq-counters-queued-bytes-rate {
                   type int32;
                   description
                     "Rate at which bytes are queued";
                 }
                 leaf voq-counters-transmitted-packets {
                   type int32;
                   description
                     "Transmitted packets count";
                 }
                 leaf voq-counters-transmitted-packets-rate {
                   type int32;
                   description
                     "Rate at which packets are transmitted";
                 }
                 leaf voq-counters-transmitted-bytes {
                   type int32;
                   description
                     "Transmitted bytes count";
                 }
                 leaf voq-counters-transmitted-bytes-rate {
                   type int32;
                   description
                     "Rate at which bytes are transmitted";
                 }
                 leaf voq-counters-queue-depth-bytes-current {
                   type int32;
                   description
                     "Current queue length";
                 }
                 leaf voq-counters-queue-depth-bytes-peak {
                   type int32;
                   description
                     "Peak queue length";
                 }
                 leaf voq-counters-queue-depth-bytes-average {
                   type int32;
                   description
                     "Average queue length";
                 }
               }
             }
             leaf queue-number {
               type uint32;
               description
                 "Queue number";
             }
             leaf forwarding-class-name {
               type string;
               description
                 "Forwarding class name associated with queue";
             }
             leaf restricted-forwarding-class-name {
               type string;
             }
           }
         }
         container ingress-queue-counters {
           description
             "Ingress queue counter statistics";
           list queue {
             key "queue-number";
             description
               "Counters for a single queue";
             leaf queue-number {
               type uint32;
               description
                 "Queue number";
             }
             leaf forwarding-class-name {
               type string;
               description
                 "Forwarding class name associated with queue";
             }
             leaf queue-counters-queued-packets {
               type int32;
               description
                 "Queued packet count";
             }
             leaf queue-counters-queued-packets-rate {
               type int32;
               description
                 "Rate at which packets are queued";
             }
             leaf queue-counters-queued-bytes {
               type int32;
               description
                 "Queued bytes count";
             }
             leaf queue-counters-queued-bytes-rate {
               type int32;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets {
               type int32;
               description
                 "Total number of transmitted packets";
             }
             leaf queue-counters-trans-packets-rate {
               type int32;
               description
                 "Rate at which packets are transmitted";
             }
             leaf queue-counters-trans-bytes {
               type int32;
               description
                 "Total number of transmitted bytes";
             }
             leaf queue-counters-trans-bytes-rate {
               type int32;
               description
                 "Rate at which bytes are transmitted";
             }
             leaf queue-counters-tail-drop-packets-na {
               type string;
               description
                 "Number of packets dropped due to tail drop not available";
             }
             leaf queue-counters-tail-drop-packets {
               type int32;
               description
                 "Number of packets dropped at the tail of the queue";
             }
             leaf queue-counters-tail-drop-packets-rate {
               type int32;
               description
                 "Rate at which packets are dropped at tail of queue";
             }
             leaf queue-counters-tail-drop-bytes {
               type int32;
               description
                 "Number of packets dropped at tail drop of the queue";
             }
             leaf queue-counters-tail-drop-bytes-rate {
               type int32;
               description
                 "Number of packets dropped at tail drop of the queue";
             }
             leaf queue-counters-ecn-ce-packets {
               type int32;
               description
                 "Total number of ECN CE packets";
             }
             leaf queue-counters-ecn-ce-packets-rate {
               type int32;
               description
                 "Rate at which ECN CE packets are transmitted";
             }
             leaf queue-counters-ecn-ce-bytes {
               type int32;
               description
                 "Total number of ECN CE bytes";
             }
             leaf queue-counters-ecn-ce-bytes-rate {
               type int32;
               description
                 "Rate at which ECN CE bytes are transmitted";
             }
             leaf queue-counters-rate-limit-drop-packets-na {
               type string;
               description
                 "Number of packets dropped due to rate-limit drop not 
                 available";
             }
             leaf queue-counters-rate-limit-drop-packets {
               type int32;
               description
                 "Number of packets dropped by rate-limit for the queue";
             }
             leaf queue-counters-rate-limit-drop-packets-rate {
               type int32;
               description
                 "Rate at which packets are dropped by rate-limit for the 
                 queue";
             }
             leaf queue-counters-rate-limit-drop-bytes-na {
               type string;
               description
                 "Number of bytes dropped due to tail drop not available";
             }
             leaf queue-counters-rate-limit-drop-bytes {
               type int32;
               description
                 "Number of bytes dropped at the tail of the queue";
             }
             leaf queue-counters-rate-limit-drop-bytes-rate {
               type int32;
               description
                 "Rate at which bytes are dropped at the tail of the queue";
             }
             leaf queue-counters-red-packets-na {
               type string;
               description
                 "Number of packets dropped due to RED not available";
             }
             leaf queue-counters-red-packets {
               type int32;
               description
                 "Number of packets dropped due to RED";
             }
             leaf queue-counters-red-packets-rate {
               type int32;
               description
                 "Rate at which packets are dropped due to RED";
             }
             leaf queue-counters-red-packets-ln {
               type int32;
               description
                 "Number of RED dropped low-loss, non-TCP packets";
             }
             leaf queue-counters-red-packets-rate-ln {
               type int32;
               description
                 "RED drop rate for low-loss, non-TCP packets";
             }
             leaf queue-counters-red-packets-lt {
               type int32;
               description
                 "Number of RED dropped of low-loss, TCP packets";
             }
             leaf queue-counters-red-packets-rate-lt {
               type int32;
               description
                 "RED drop rate for low-loss, TCP packets";
             }
             leaf queue-counters-red-packets-hn {
               type int32;
               description
                 "Number of RED dropped high-loss, non-TCP packets";
             }
             leaf queue-counters-red-packets-rate-hn {
               type int32;
               description
                 "RED drop rate for high-loss, non-TCP packets";
             }
             leaf queue-counters-red-packets-ht {
               type int32;
               description
                 "Number of RED dropped high-loss, TCP packets";
             }
             leaf queue-counters-red-packets-rate-ht {
               type int32;
               description
                 "RED drop rate for high-loss, TCP packets";
             }
             leaf queue-counters-red-packets-low {
               type int32;
               description
                 "Number of RED dropped low-loss packets";
             }
             leaf queue-counters-red-packets-rate-low {
               type int32;
               description
                 "RED drop rate for low-loss packets";
             }
             leaf queue-counters-red-packets-medium-low {
               type int32;
               description
                 "Number of RED dropped medium-low-loss packets";
             }
             leaf queue-counters-red-packets-rate-medium-low {
               type int32;
               description
                 "RED drop rate for medium-low-loss packets";
             }
             leaf queue-counters-red-packets-medium-high {
               type int32;
               description
                 "Number of RED dropped medium-high-loss packets";
             }
             leaf queue-counters-red-packets-rate-medium-high {
               type int32;
               description
                 "RED drop rate for medium-high-loss packets";
             }
             leaf queue-counters-red-packets-medium {
               type int32;
               description
                 "Number of RED dropped medium-loss packets";
             }
             leaf queue-counters-red-packets-rate-medium {
               type int32;
               description
                 "RED drop rate for medium-loss packets";
             }
             leaf queue-counters-red-packets-high {
               type int32;
               description
                 "Number of RED dropped high-loss packets";
             }
             leaf queue-counters-red-packets-rate-high {
               type int32;
               description
                 "RED drop rate for high-loss packets";
             }
             leaf queue-counters-red-bytes-na {
               type string;
               description
                 "Number of bytes dropped due to RED not available";
             }
             leaf queue-counters-red-bytes {
               type int32;
               description
                 "Number of bytes dropped due to RED";
             }
             leaf queue-counters-red-bytes-rate {
               type int32;
               description
                 "Rate at which bytes are dropped due to RED";
             }
             leaf queue-counters-red-bytes-ln {
               type int32;
               description
                 "Number of RED dropped low-loss, non-TCP bytes";
             }
             leaf queue-counters-red-bytes-rate-ln {
               type int32;
               description
                 "RED drop rate for low-loss, non-TCP bytes";
             }
             leaf queue-counters-red-bytes-lt {
               type int32;
               description
                 "Number of RED dropped low-loss, TCP bytes";
             }
             leaf queue-counters-red-bytes-rate-lt {
               type int32;
               description
                 "RED drop rate for low-loss, TCP bytes";
             }
             leaf queue-counters-red-bytes-hn {
               type int32;
               description
                 "Number of RED dropped high-loss, non-TCP bytes";
             }
             leaf queue-counters-red-bytes-rate-hn {
               type int32;
               description
                 "RED drop rate for high-loss, non-TCP bytes";
             }
             leaf queue-counters-red-bytes-ht {
               type int32;
               description
                 "Number of RED dropped high-loss, TCP bytes";
             }
             leaf queue-counters-red-bytes-rate-ht {
               type int32;
               description
                 "RED drop rate for high-loss, TCP bytes";
             }
             leaf queue-counters-red-bytes-low {
               type int32;
               description
                 "Number of RED dropped low-loss bytes";
             }
             leaf queue-counters-red-bytes-rate-low {
               type int32;
               description
                 "RED drop rate for low-loss bytes";
             }
             leaf queue-counters-red-bytes-medium-low {
               type int32;
               description
                 "Number of RED dropped medium-low-loss bytes";
             }
             leaf queue-counters-red-bytes-rate-medium-low {
               type int32;
               description
                 "RED drop rate for medium-low-loss bytes";
             }
             leaf queue-counters-red-bytes-medium-high {
               type int32;
               description
                 "Number of RED dropped medium-high-loss bytes";
             }
             leaf queue-counters-red-bytes-rate-medium-high {
               type int32;
               description
                 "RED drop rate for medium-high-loss bytes";
             }
             leaf queue-counters-red-bytes-medium {
               type int32;
               description
                 "Number of RED dropped medium-loss bytes";
             }
             leaf queue-counters-red-bytes-rate-medium {
               type int32;
               description
                 "RED drop rate for medium-loss bytes";
             }
             leaf queue-counters-red-bytes-high {
               type int32;
               description
                 "Number of RED dropped high-loss bytes";
             }
             leaf queue-counters-red-bytes-rate-high {
               type int32;
               description
                 "RED drop rate for high-loss bytes";
             }
             leaf queue-counters-timestamp {
               type int32;
               description
                 "Last packet enqueued timestamp";
             }
             leaf queue-counters-total-drop-packets {
               type int32;
               description
                 "Number of total packets dropped at the queue";
             }
             leaf queue-counters-total-drop-packets-rate {
               type int32;
               description
                 "Number of total packets dropped at the queue";
             }
             leaf queue-counters-total-drop-bytes {
               type int32;
               description
                 "Number of total packets dropped at the queue";
             }
             leaf queue-counters-total-drop-bytes-rate {
               type int32;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
           container interface-cos-short-summary {
             description
               "Summary of queue information on an interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           list queue-num-forwarding-class-name-map {
             key "queue-number";
             leaf queue-number {
               type uint32;
               description
                 "Queue number";
             }
             leaf forwarding-class-name {
               type string;
               description
                 "Forwarding class name associated with queue";
             }
           }
         }
         container forwarding-class-counters {
           description
             "Forwarding-class counter statistics";
           leaf forwarding-class-counters-error-message {
             type string;
             description
               "Forwarding-class statistics not available for this interface";
           }
           container forwarding-class-accounting-parameters {
             leaf forwarding-class-accounting-for-protocol {
               type string;
             }
             leaf forwarding-class-accounting-for-traffic-direction {
               type string;
             }
             leaf forwarding-class-accounting-for-traffic-type {
               type string;
             }
             leaf forwarding-class-accounting-overhead-bytes {
               type uint32;
             }
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
           container ipv4-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container ipv6-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container mpls-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container layer2-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container other-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container protocol-aggregate-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container forwarding-class-statistics {
             container protocol-aggregate-forwarding-class-counters {
             }
             container ipv4-forwarding-class-counters {
             }
             container ipv6-forwarding-class-counters {
             }
             container mpls-forwarding-class-counters {
             }
             container layer2-forwarding-class-counters {
             }
             container other-forwarding-class-counters {
             }
           }
         }
         container multilink-bundle-link-information {
           leaf multilink-active-bundle-links {
             type int32;
             description
               "Number of active bundle links in this multilink bundle 
               instance";
           }
           leaf multilink-removed-bundle-links {
             type int32;
             description
               "Number of bundle links that are removed from service in this
               multilink bundle instance";
           }
           leaf multilink-disabled-bundle-links {
             type int32;
             description
               "Number of bundle links that are not allowed to transmit in 
               this multilink bundle instance";
           }
         }
         container multilink-bundle-options {
           leaf mrru {
             type int32;
           }
           leaf remote-mrru {
             type int32;
             description
               "Remote max received reconstructed unit";
           }
           leaf drop-timeout {
             type int32;
           }
           leaf mlppp-inner-ppp-pfc {
             type string;
             description
               "MLPPP inner PPP protocol field compression";
           }
           leaf sequence-number-format {
             type string;
           }
           leaf fragment-threshold {
             type int32;
           }
           leaf minimum-links {
             type int32;
           }
           leaf interleave-fragments {
             type string;
           }
           leaf multilink-classes {
             type int32;
             description
               "Number of multilink classes";
           }
           leaf link-layer-overhead {
             type string;
             description
               "Link layer overhead";
           }
         }
         container multilink-bundle-errors {
           description
             "Multilink bundle errors";
           leaf packet-drops {
             type int32;
             description
               "Number of packets dropped";
           }
           leaf packet-drop-bytes {
             type int32;
             description
               "Number of bytes in dropped packets";
           }
           leaf fragment-drops {
             type int32;
             description
               "Number of fragments dropped";
           }
           leaf fragment-drop-bytes {
             type int32;
             description
               "Number of bytes in dropped fragments";
           }
           leaf mrru-exceeded {
             type int32;
             description
               "Number of assembled packets that exceeded MRRU";
           }
           leaf processing-errors {
             type int32;
             description
               "Number of errors encountered in assembling packets";
           }
         }
         container multilink-traffic-statistics {
           container bundle {
             container multilink-frames {
               description
                 "Link-pic bound frame statistics for multilink bundles and 
                 classes";
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
             container network-frames {
               description
                 "Internet/RE bound frame statistics for multilink bundles 
                 and classes";
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
             container network-v6-frames {
               description
                 "Transit IPV6 statistics for multilink bundles";
               leaf inputv6-packets {
                 type int32;
               }
               leaf inputv6-bytes {
                 type int32;
               }
               leaf outputv6-packets {
                 type int32;
               }
               leaf outputv6-bytes {
                 type int32;
               }
             }
           }
           container class {
             description
               "Multilink class traffic statistics";
             container class-info {
               description
                 "Multilink class information";
               leaf multilink-class-id {
                 type int32;
                 description
                   "Multilink class ID";
               }
             }
             container multilink-frames {
               description
                 "Link-pic bound frame statistics for multilink bundles and 
                 classes";
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
             container network-frames {
               description
                 "Internet/RE bound frame statistics for multilink bundles 
                 and classes";
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
           }
           list link {
             key "name";
             leaf name {
               type string;
               description
                 "Name of this item";
             }
             leaf down {
               type empty;
               description
                 "Link is down";
             }
             leaf link-uptime {
               type string;
               description
                 "Total uptime for the member link";
             }
             leaf input-frames {
               type int32;
             }
             leaf input-fps {
               type int32;
             }
             leaf input-bytes {
               type int32;
             }
             leaf input-bps {
               type int32;
             }
             leaf output-frames {
               type int32;
             }
             leaf output-fps {
               type int32;
             }
             leaf output-bytes {
               type int32;
             }
             leaf output-bps {
               type int32;
             }
           }
           container multilink-detail-statistics {
             container bundle-detail {
               container fragments {
                 description
                   "Fragment statistics for multilink bundles and classes";
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
               container non-fragments {
                 description
                   "Non-fragment statistics for multilink bundles and 
                   classes";
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
               container lfi {
                 description
                   "LFI frame statistics for multilink bundles and classes";
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
             }
             container class-detail {
               container class-info {
                 description
                   "Multilink class information";
                 leaf multilink-class-id {
                   type int32;
                   description
                     "Multilink class ID";
                 }
               }
               container fragments {
                 description
                   "Fragment statistics for multilink bundles and classes";
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
               container non-fragments {
                 description
                   "Non-fragment statistics for multilink bundles and 
                   classes";
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
             }
           }
           container crtp {
             container crtp-sessions {
               leaf input-frames {
                 type int32;
               }
               leaf output-frames {
                 type int32;
               }
             }
             list crtp-statistics {
               key "name";
               leaf name {
                 type string;
                 description
                   "Name of this item";
               }
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
           }
         }
         container statistics-account-overhead {
           description
             "Statistics account overhead information";
           leaf ingress-account-overhead {
             type int32;
             description
               "Ingress Statistics account overhead information";
           }
           leaf egress-account-overhead {
             type int32;
             description
               "Egress Statistics account overhead information";
           }
         }
         container traffic-statistics {
           leaf input-bps {
             type int32;
           }
           leaf input-pps {
             type int32;
           }
           leaf output-bps {
             type int32;
           }
           leaf output-pps {
             type int32;
           }
           leaf input-packets {
             type uint64;
           }
           leaf output-packets {
             type uint64;
           }
           container ipv4-traffic-statistics {
             leaf input-bps {
               type int32;
             }
             leaf output-bps {
               type int32;
             }
             leaf input-pps {
               type int32;
             }
             leaf output-pps {
               type int32;
             }
             leaf input-bytes {
               type int32;
             }
             leaf output-bytes {
               type int32;
             }
             leaf input-packets {
               type uint64;
             }
             leaf output-packets {
               type uint64;
             }
           }
           leaf input-bytes {
             type int32;
           }
           leaf output-bytes {
             type int32;
           }
           container ipv6-transit-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-traffic-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-total-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
         }
         container multicast-statistics {
           description
             "Multicast statistics for interface";
           leaf multicast-statistics-header {
             type empty;
           }
           container ipv4-multicast-statistics {
             description
               "IPV4 multicast statistics for interface";
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-multicast-statistics {
             description
               "IPV6 multicast statistics for interface";
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
         }
         container ingress-traffic-statistics {
           description
             "Traffic statistics at ingress before entering Packet 
             Forwarding Engine";
           leaf input-bps {
             type int32;
           }
           leaf input-pps {
             type int32;
           }
           leaf input-drop-bps {
             type int32;
             description
               "Drop rate at ingress in bits per second ";
           }
           leaf input-drop-pps {
             type int32;
             description
               "Drop rate at ingress in packets per second ";
           }
           leaf input-bytes {
             type int32;
           }
           leaf input-packets {
             type uint64;
           }
           leaf input-drop-bytes {
             type int32;
             description
               "Drop statistics at ingress in bytes";
           }
           leaf input-drop-packets {
             type int32;
             description
               "Drop statistics at ingress in packets";
           }
         }
         container local-traffic-statistics {
           description
             "Statistics for locally originated traffic";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
           container ipv4-local-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-local-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
         }
         container transit-traffic-statistics {
           description
             "Statistics for traffic passing through the Packet Forwarding 
             Engine";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
           container ipv4-transit-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-transit-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-total-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
         }
         container layer3-statistics {
           container l3-ipv4-unicast-statistics {
             description
               "Statistics for traffic passing through the packet forwarding
               engine";
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container l3-ipv4-multicast-statistics {
             description
               "Statistics for traffic passing through the packet forwarding
               engine";
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container l3-ipv6-unicast-statistics {
             description
               "Statistics for traffic passing through the packet forwarding
               engine";
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container l3-ipv6-multicast-statistics {
             description
               "Statistics for traffic passing through the packet forwarding
               engine";
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
         }
         container keepalive-config {
           description
             "Configured keepalive settings on this interface";
           leaf keepalive-interval {
             type int32;
           }
           leaf keepalive-up-count {
             type int32;
           }
           leaf keepalive-down-count {
             type int32;
           }
         }
         container keepalive-statistics {
           description
             "Keepalive statistics for this interface";
           leaf keepalive-lmi-descriptor {
             type string;
           }
           leaf keepalive-input-count {
             type int32;
           }
           leaf keepalive-input-time {
             type string;
           }
           leaf keepalive-output-count {
             type int32;
           }
           leaf keepalive-output-time {
             type string;
           }
         }
         container ppp-flags {
           leaf iff-ppp-flags-acfc {
             type empty;
           }
           leaf iff-ppp-flags-pfc {
             type empty;
           }
         }
         list ncp-information {
           description
             "Network Control Protocol information";
           leaf ncp-protocol {
             type string;
             description
               "Network protocol for this NCP instance";
           }
           leaf ncp-state {
             type string;
             description
               "State of this NCP instance";
           }
         }
         container virtual-circuit-information {
           description
             "Operational information and statistics for a virtual circuit";
           leaf vpi {
             type int32;
             description
               "Virtual path identifier";
           }
           leaf vci {
             type int32;
             description
               "Virtual circuit identifier";
           }
           leaf psn-tag {
             type string;
             description
               "VPI/VCI swapping configuration";
           }
           leaf psn-vpi {
             type int32;
             description
               "PSN virtual path identifier";
           }
           leaf psn-vci {
             type int32;
             description
               "PSN virtual circuit identifier";
           }
           leaf trunk {
             type int32;
             description
               "ATM trunk identifier";
           }
           leaf dlci {
             type int32;
           }
           leaf swapping {
             type string;
             description
               "VPI/VCI swapping configuration";
           }
           leaf trunk-bandwidth {
             type int32;
             description
               "ATM trunk bandwidth";
           }
           leaf atm-tm-cbr {
             type empty;
             description
               "Constant bit rate";
           }
           leaf atm-tm-vbr {
             type empty;
             description
               "Variable bit rate";
           }
           leaf atm-tm-rtvbr {
             type empty;
             description
               "Real-time variable bit rate";
           }
           leaf peak {
             type int32;
           }
           leaf sustained {
             type int32;
           }
           leaf burst {
             type int32;
           }
           leaf cdvt {
             type int32;
           }
           leaf queue-limit {
             type int32;
           }
           leaf down-time {
             type int32;
             description
               "Total down time for this circuit";
           }
           leaf last-down-time {
             type int32;
             description
               "Time elapsed since circuit last went down";
           }
           leaf ifvc-epd {
             type int32;
             description
               "Early packet discard threshold";
           }
           leaf ifvc-weight {
             type int32;
             description
               "Transmit weight";
           }
           leaf ifvc-epd-plp0 {
             type int32;
             description
               "Early packet discard threshold for PLP 0";
           }
           leaf ifvc-epd-plp1 {
             type int32;
             description
               "Early packet discard threshold for PLP 1";
           }
           container dlci-statistics {
             description
               "DLCI statistics for an interface";
             leaf dlci-active {
               type int32;
               description
                 "Number of DLCIs in active state";
             }
             leaf dlci-inactive {
               type int32;
               description
                 "Number of DLCIs in inactive state";
             }
           }
           container vci-range {
             description
               "ATM VCI range";
             leaf vpi {
               type int32;
               description
                 "Virtual path identifier";
             }
             leaf start-vci {
               type int32;
               description
                 "ATM VCI range's start value";
             }
             leaf end-vci {
               type int32;
               description
                 "ATM VCI range's end value";
             }
           }
           container ifvc-flags {
             leaf ifvc-down {
               type empty;
             }
             leaf ifvc-none {
               type empty;
             }
             leaf ifvc-active {
               type empty;
             }
             leaf ifvc-closed {
               type empty;
             }
             leaf ifvc-inverse-arp {
               type empty;
             }
             leaf ifvc-ilmi {
               type empty;
             }
             leaf ifvc-oam {
               type empty;
             }
             leaf ifvc-shaping {
               type empty;
             }
             leaf ifvc-passiveoam {
               type empty;
             }
             leaf ifvc-multicast {
               type empty;
             }
             leaf ifvc-ccc-down {
               type empty;
             }
             leaf ifvc-configured {
               type empty;
               description
                 "DCE-end is configured";
             }
             leaf ifvc-unconfigured {
               type empty;
               description
                 "DCE-end is unconfigured";
             }
             leaf generic-value {
               type int32;
               description
                 "Hexadecimal value of unknown flag bits";
             }
           }
           container ifvc-multipoint-destination {
             leaf multipoint-address {
               type string;
               description
                 "Protocol address of the remote side of this connection";
             }
           }
           container oam-parameters {
             leaf period {
               type int32;
             }
             leaf up-count {
               type int32;
             }
             leaf down-count {
               type int32;
             }
           }
           container oam-statistics {
             description
               "Container tag for OAM statistics";
             leaf oam-total-received-count {
               type int32;
             }
             leaf oam-total-transmitted-count {
               type int32;
             }
             leaf oam-total-received-count-4 {
               type int32;
             }
             leaf oam-total-transmitted-count-4 {
               type int32;
             }
             leaf oam-loopback-received-count {
               type int32;
             }
             leaf oam-loopback-transmitted-count {
               type int32;
             }
             leaf oam-loopback-received-last {
               type string;
             }
             leaf oam-loopback-transmitted-last {
               type string;
             }
             leaf oam-rdi-received-count {
               type int32;
             }
             leaf oam-rdi-transmitted-count {
               type int32;
             }
             leaf oam-rdi-received-last {
               type string;
             }
             leaf oam-rdi-transmitted-last {
               type string;
             }
             leaf oam-ais-received-count {
               type int32;
             }
             leaf oam-ais-transmitted-count {
               type int32;
             }
             leaf oam-ais-received-last {
               type string;
             }
             leaf oam-ais-transmitted-last {
               type string;
             }
           }
           container traffic-statistics {
             leaf input-bps {
               type int32;
             }
             leaf input-pps {
               type int32;
             }
             leaf output-bps {
               type int32;
             }
             leaf output-pps {
               type int32;
             }
             leaf input-packets {
               type uint64;
             }
             leaf output-packets {
               type uint64;
             }
             container ipv4-traffic-statistics {
               leaf input-bps {
                 type int32;
               }
               leaf output-bps {
                 type int32;
               }
               leaf input-pps {
                 type int32;
               }
               leaf output-pps {
                 type int32;
               }
               leaf input-bytes {
                 type int32;
               }
               leaf output-bytes {
                 type int32;
               }
               leaf input-packets {
                 type uint64;
               }
               leaf output-packets {
                 type uint64;
               }
             }
             leaf input-bytes {
               type int32;
             }
             leaf output-bytes {
               type int32;
             }
             container ipv6-transit-statistics {
               leaf input-bytes {
                 type int32;
               }
               leaf input-bps {
                 type int32;
               }
               leaf output-bytes {
                 type int32;
               }
               leaf output-bps {
                 type int32;
               }
               leaf input-packets {
                 type uint64;
               }
               leaf input-pps {
                 type int32;
               }
               leaf output-packets {
                 type uint64;
               }
               leaf output-pps {
                 type int32;
               }
             }
             container ipv6-traffic-statistics {
               leaf input-bytes {
                 type int32;
               }
               leaf input-bps {
                 type int32;
               }
               leaf output-bytes {
                 type int32;
               }
               leaf output-bps {
                 type int32;
               }
               leaf input-packets {
                 type uint64;
               }
               leaf input-pps {
                 type int32;
               }
               leaf output-packets {
                 type uint64;
               }
               leaf output-pps {
                 type int32;
               }
             }
             container ipv6-total-statistics {
               leaf input-bytes {
                 type int32;
               }
               leaf input-bps {
                 type int32;
               }
               leaf output-bytes {
                 type int32;
               }
               leaf output-bps {
                 type int32;
               }
               leaf input-packets {
                 type uint64;
               }
               leaf input-pps {
                 type int32;
               }
               leaf output-packets {
                 type uint64;
               }
               leaf output-pps {
                 type int32;
               }
             }
           }
           container atm-policer-statistics {
             leaf non-conform-clp0-cells {
               type int32;
               description
                 "UPC non-conforming ATM CLP0 cell";
             }
             leaf non-conform-clp1-cells {
               type int32;
               description
                 "UPC non-conforming ATM CLP1 cell";
             }
             leaf tagged-cells {
               type int32;
               description
                 "UPC tagged cell";
             }
           }
           container atm-statistics {
             leaf vc-queue-drops {
               type int32;
             }
           }
           container atm-cos-information {
             leaf vc-cos-mode {
               type string;
               description
                 "Virtual circuit CoS scheduling mode";
             }
             list atm-cos-queue {
               container atm-cos-queue-parameters {
                 leaf cos-forwarding-class-name {
                   type string;
                   description
                     "Forwarding class name associated with queue";
                 }
                 leaf cos-queue-number {
                   type int32;
                   description
                     "Queue number";
                 }
                 leaf scheduling-priority {
                   type string;
                   description
                     "Scheduling priority";
                 }
                 leaf transmit-weight-cells {
                   type int32;
                   description
                     "Weight to apply to scheduling as number of cells";
                 }
                 leaf transmit-weight-percent {
                   type int32;
                   description
                     "Weight to apply to scheduling as fill percentage";
                 }
                 leaf epd-threshold {
                   type int32;
                   description
                     "Early packet drop threshold";
                 }
                 leaf epd-threshold-plp0 {
                   type int32;
                   description
                     "Early packet drop threshold for PLP 0";
                 }
                 leaf epd-threshold-plp1 {
                   type int32;
                   description
                     "Early packet drop threshold for PLP 1";
                 }
                 container linear-red-drop-profile {
                   leaf queue-depth {
                     type int32;
                     description
                       "Maximum queue depth";
                   }
                   leaf low-red {
                     type int32;
                     description
                       "Fill level percentage when linear RED is applied for
                       low PLP";
                   }
                   leaf high-red {
                     type int32;
                     description
                       "Fill level percentage when linear RED is applied for
                       high PLP";
                   }
                   leaf max-low-red {
                     type int32;
                     description
                       "Fill level percentage with 100% packet drop for low 
                       PLP";
                   }
                   leaf max-high-red {
                     type int32;
                     description
                       "Fill level percentage with 100% packet drop for high
                       PLP";
                   }
                 }
               }
               container atm-cos-queue-statistics {
                 leaf atm-output-bytes {
                   type int32;
                 }
                 leaf atm-output-packets {
                   type int32;
                 }
                 leaf atm-packet-drops {
                   type int32;
                 }
               }
               container atm-cos-plp-statistics {
                 leaf atm-plp0-output-bytes {
                   type int32;
                 }
                 leaf atm-plp1-output-bytes {
                   type int32;
                 }
                 leaf atm-plp0-output-packets {
                   type int32;
                 }
                 leaf atm-plp1-output-packets {
                   type int32;
                 }
                 leaf atm-plp0-byte-drops {
                   type int32;
                 }
                 leaf atm-plp1-byte-drops {
                   type int32;
                 }
                 leaf atm-plp0-packet-drops {
                   type int32;
                 }
                 leaf atm-plp1-packet-drops {
                   type int32;
                 }
               }
             }
           }
           container in-arp-statistics {
             description
               "Container tag for ARP statistics";
             leaf received-count {
               type int32;
               description
                 "Number of ARPs received";
             }
             leaf transmitted-count {
               type int32;
               description
                 "Number of ARPs sent";
             }
             leaf denied-count {
               type int32;
               description
                 "Number of ARPs denied";
             }
             leaf operation-not-supported-count {
               type int32;
               description
                 "Number of ARPs with operation not supported";
             }
             leaf bad-packet-length-count {
               type int32;
               description
                 "Number of ARPs with bad packet length";
             }
             leaf bad-protocol-count {
               type int32;
               description
                 "Number of ARPs with bad protocol";
             }
             leaf bad-protocol-length-count {
               type int32;
               description
                 "Number of ARPs with bad protocol length";
             }
             leaf bad-hardware-length-count {
               type int32;
               description
                 "Number of ARPs with bad hardware length";
             }
             leaf dropped-count {
               type int32;
               description
                 "Number of ARPs dropped";
             }
             leaf last-received {
               type string;
               description
                 "Time an ARP was last received";
             }
             leaf last-transmitted {
               type string;
               description
                 "Time an ARP was last sent";
             }
           }
         }
         list filter-information {
           leaf-list filter-input {
             type string;
             description
               "Name of the input filter";
           }
           leaf-list filter-input-precedence {
             type uint32;
             description
               "Precedence of the input filter";
           }
           leaf-list filter-output {
             type string;
             description
               "Name of the output filter";
           }
           leaf-list filter-output-precedence {
             type uint32;
             description
               "Precedence of the output filter";
           }
         }
         container allowed-host-inbound-traffic {
           description
             "List of allowed system services and protocols";
           leaf inbound-all-protocols {
             type empty;
             description
               "All protocols";
           }
           leaf inbound-any-service {
             type empty;
             description
               "Any service";
           }
           leaf inbound-bootp {
             type empty;
             description
               "Bootp and dhcp relay-agent service";
           }
           leaf inbound-bfd {
             type empty;
             description
               "Bidirectional Forwarding Detection";
           }
           leaf inbound-bgp {
             type empty;
             description
               "Border Gateway Protocol";
           }
           leaf inbound-dns {
             type empty;
             description
               "DNS and DNS-proxy service";
           }
           leaf inbound-dvmrp {
             type empty;
             description
               "Distance Vector Multicast Routing Protocol";
           }
           leaf inbound-igmp {
             type empty;
             description
               "Internet Group Management Protocol";
           }
           leaf inbound-ldp {
             type empty;
             description
               "Label Distribution Protocol";
           }
           leaf inbound-msdp {
             type empty;
             description
               "Multicast Source Discovery Protocol";
           }
           leaf inbound-nhrp {
             type empty;
             description
               "Next Hop Resolution Protocol";
           }
           leaf inbound-ospf {
             type empty;
             description
               "Open Shortest Path First";
           }
           leaf inbound-ospf3 {
             type empty;
             description
               "Open Shortest Path First version 3";
           }
           leaf inbound-pgm {
             type empty;
             description
               "Pragmatic General Multicast";
           }
           leaf inbound-pim {
             type empty;
             description
               "Protocol Independent Multicast";
           }
           leaf inbound-rip {
             type empty;
             description
               "Routing Information Protocol";
           }
           leaf inbound-ripng {
             type empty;
             description
               "Routing Information Protocol next generation";
           }
           leaf inbound-router-discovery {
             type empty;
             description
               "Router Discovery";
           }
           leaf inbound-rsvp {
             type empty;
             description
               "Resource Reservation Protocol";
           }
           leaf inbound-sap {
             type empty;
             description
               "Session Announcement Protocol";
           }
           leaf inbound-vrrp {
             type empty;
             description
               "Virtual Router Redundancy Protocol";
           }
           leaf inbound-all-services {
             type empty;
             description
               "All system services";
           }
           leaf inbound-dhcp {
             type empty;
             description
               "Dynamic Host Configuration Protocol";
           }
           leaf inbound-finger {
             type empty;
             description
               "Finger service";
           }
           leaf inbound-ftp {
             type empty;
             description
               "File Transfer Protocol";
           }
           leaf inbound-tftp {
             type empty;
             description
               "Trivial File Transfer Protocol";
           }
           leaf ident-reset {
             type empty;
             description
               "Send back TCP RST to IDENT request for port 113";
           }
           leaf inbound-http {
             type empty;
             description
               "Web management service using HTTP";
           }
           leaf inbound-https {
             type empty;
             description
               "Web management service using HTTP secured by SSL";
           }
           leaf inbound-ike {
             type empty;
             description
               "Internet Key Exchange";
           }
           leaf inbound-netconf {
             type empty;
             description
               "NETCONF service";
           }
           leaf inbound-ping {
             type empty;
             description
               "Internet Control Message Protocol echo requests";
           }
           leaf inbound-reverse-telnet {
             type empty;
             description
               "Reverse telnet service";
           }
           leaf inbound-reverse-ssh {
             type empty;
             description
               "Reverse SSH service";
           }
           leaf inbound-rlogin {
             type empty;
             description
               "Rlogin service";
           }
           leaf inbound-rpm {
             type empty;
             description
               "Real-time performance monitoring";
           }
           leaf inbound-rsh {
             type empty;
             description
               "Rsh service";
           }
           leaf inbound-snmp {
             type empty;
             description
               "Simple Network Management Protocol service";
           }
           leaf inbound-snmp-trap {
             type empty;
             description
               "Simple Network Management Protocol traps";
           }
           leaf inbound-ssh {
             type empty;
             description
               "SSH service";
           }
           leaf inbound-telnet {
             type empty;
             description
               "Telnet service";
           }
           leaf inbound-traceroute {
             type empty;
             description
               "Traceroute service";
           }
           leaf inbound-xnm-clear-text {
             type empty;
             description
               "JUNOScript API for unencrypted traffic over TCP";
           }
           leaf inbound-xnm-ssl {
             type empty;
             description
               "JUNOScript API service over SSL";
           }
           leaf inbound-lsping {
             type empty;
             description
               "Label Switched Path ping service";
           }
           leaf inbound-lsselfping {
             type empty;
             description
               "Label Switched Path self ping service";
           }
           leaf inbound-ntp {
             type empty;
             description
               "Network Time Protocol service";
           }
           leaf inbound-sip {
             type empty;
             description
               "Session Initiation Protocol service";
           }
           leaf inbound-dhcpv6 {
             type empty;
             description
               "Dynamic Host Configuration Protocol for IPv6 service";
           }
           leaf inbound-r2cp {
             type empty;
             description
               "Radio Router Control Protocol service";
           }
           leaf inbound-webapi-clear-text {
             type empty;
             description
               "Webapi service using http";
           }
           leaf inbound-webapi-ssl {
             type empty;
             description
               "Webapi service using HTTP secured by SSL";
           }
           leaf inbound-tcp-encap {
             type empty;
             description
               "Tcp encapsulation service";
           }
           leaf inbound-sdwan-appqoe {
             type empty;
             description
               "Sdwan Appqoe service";
           }
           leaf inbound-high-availability {
             type empty;
             description
               "High Availability  service";
           }
         }
         list address-family {
           key "address-family-name";
           leaf compression-device-name {
             type string;
             description
               "Name of the link service device";
           }
           leaf address-family-name {
             type string;
           }
           leaf multilink-bundle-name {
             type string;
             description
               "Name of the multilink bundle for this address family";
           }
           leaf as-bundle-name {
             type string;
             description
               "Name of the aggregated SONET bundle for this address family";
           }
           leaf ae-bundle-name {
             type string;
             description
               "Name of the aggregated Ethernet bundle";
           }
           leaf es-sa-name {
             type string;
             description
               "Name of the IPSec security association for this address 
               family";
           }
           leaf mtu {
             type string;
             description
               "MTU size on this interface";
           }
           leaf maximum-labels {
             type uint32;
             description
               "Maximum labels on MPLS iffamily";
           }
           leaf generation {
             type string;
             description
               "Generation number used to distinguish between successive 
               instances of this interface";
           }
           leaf route-table {
             type int32;
           }
           leaf vpls-mesh-group {
             type string;
           }
           leaf es-sa-fail-count {
             type int32;
             description
               "Number of failures for IPSec security association for this 
               family";
           }
           leaf es-sa-xmt-seq-num {
             type int32;
             description
               "Transmit sequence number of IPSec security association 
               family";
           }
           leaf es-sa-recv-seq-num {
             type int32;
             description
               "Receive sequence number of IPSec security association family";
           }
           leaf evpn-multihomed-status {
             type string;
           }
           leaf evpn-mh-esi-sh-label {
             type string;
           }
           leaf iff-next-hop {
             type int32;
             description
               "Interface family next-hop";
           }
           leaf iff-vpls-status {
             type string;
             description
               "Interface family vpls status";
           }
           leaf max-local-cache {
             type uint32;
             description
               "Max local nh cache size";
           }
           leaf new-hold-limit {
             type uint32;
             description
               "Max limit on new unresolved nh";
           }
           leaf intf-curr-cnt {
             type uint32;
             description
               "Current nh total cache size on this interface";
           }
           leaf intf-unresolved-cnt {
             type uint32;
             description
               "Current new unresolved nh cache size on this interface";
           }
           leaf intf-dropcnt {
             type uint32;
             description
               "Current interface nh drop count";
           }
           leaf intf-hold-nh-dropcnt {
             type uint32;
             description
               "Current interface Hold NextHop drop count by RED";
           }
           leaf ft-iff-dest-port {
             type uint32;
             description
               "Destination UDP port to be used for this family";
           }
           leaf mlppp-service-interface {
             type string;
             description
               "Name of the multilink service interface for this address 
               family";
           }
           leaf mlppp-service-dev-pool {
             type string;
             description
               "Name of the multilink service device pool for this address 
               family";
           }
           leaf mlppp-dynamic-profile {
             type string;
             description
               "Name of the multilink dynamic profile for this address 
               family";
           }
           leaf arp-respond-any-local-address {
             type string;
             description
               "Respond to ARP requests for any local address";
           }
           container address-family-flags {
             leaf ifff-none {
               type empty;
             }
             leaf ifff-primary {
               type empty;
             }
             leaf ifff-redirects {
               type empty;
             }
             leaf ifff-no-redirects {
               type empty;
             }
             leaf ifff-no-neighbor-learn {
               type empty;
             }
             leaf ifff-targeted-broadcast {
               type empty;
             }
             leaf ifff-sendbcast-pkt-to-re {
               type empty;
             }
             leaf ifff-hard-down {
               type empty;
             }
             leaf ifff-down {
               type empty;
             }
             leaf ifff-up {
               type empty;
             }
             leaf ifff-func1 {
               type empty;
             }
             leaf ifff-func2 {
               type empty;
             }
             leaf ifff-is-primary {
               type empty;
             }
             leaf ifff-recv-options {
               type empty;
             }
             leaf ifff-recv-ttl-exceeded {
               type empty;
             }
             leaf ifff-dst-class-usage {
               type empty;
             }
             leaf ifff-src-class-input {
               type empty;
             }
             leaf ifff-src-class-output {
               type empty;
             }
             leaf ifff-mtu-user-conf {
               type empty;
             }
             leaf ifff-mac-validate-strict {
               type empty;
             }
             leaf ifff-mac-validate-loose {
               type empty;
             }
             leaf ifff-rpf-check {
               type empty;
             }
             leaf ifff-rpf-loose-mode {
               type empty;
             }
             leaf ifff-sample-input {
               type empty;
             }
             leaf ifff-sample-output {
               type empty;
             }
             leaf ifff-no-asynch-notification {
               type empty;
             }
             leaf ifff-negotiate-address {
               type empty;
             }
             leaf ifff-port-mode-trunk {
               type empty;
             }
             leaf ifff-inter-switch-link {
               type empty;
             }
             leaf ifff-mtu-protocol-adj {
               type empty;
             }
             leaf ifff-unnumbered {
               type empty;
             }
             leaf ifff-tcc-mpls {
               type empty;
             }
             leaf ifff-tcc-inet {
               type empty;
             }
             leaf ifff-tcc-inet6 {
               type empty;
             }
             leaf ifff-tcc-iso {
               type empty;
             }
             leaf ifff-port-mode-isid-trunk {
               type empty;
             }
             leaf iff-clear-df {
               type empty;
             }
             leaf ifff-tunnel-loopback {
               type empty;
             }
             leaf ifff-class-based-filtering-scu {
               type empty;
             }
             leaf ifff-class-based-filtering-dcu {
               type empty;
             }
             leaf internal-flags {
               type string;
               description
                 "Hexadecimal value of internal flag bits";
             }
             leaf generic-value {
               type int32;
               description
                 "Hexadecimal value of unknown flag bits";
             }
           }
           list address-family-unnumbered {
             key "unnumbered-family-donor-interface-name";
             description
               "Information about an unnumbered address family";
             leaf unnumbered-family-donor-interface-name {
               type string;
               description
                 "Donor interface name";
             }
             leaf unnumbered-family-donor-interface-index {
               type string;
               description
                 "Donor interface index";
             }
             leaf unnumbered-family-preferred-source-address {
               type string;
               description
                 "Unnumbered interface preferred source address";
             }
           }
           container pppoe-underlying-information {
             description
               "PPPoE Underlying information";
             list pppoe-underlying-interface {
               leaf dynamic-profile {
                 type string;
                 description
                   "Dynamic Profile name";
               }
               leaf service-name-table {
                 type string;
                 description
                   "Name of Service Name Table";
               }
               leaf max-sessions {
                 type int32;
                 description
                   "Maximum number of PPPoE sessions";
               }
               leaf max-sessions-vsa-ignore {
                 type string;
                 description
                   "Ignore max-sessions VSA";
               }
               leaf duplicate-protection {
                 type string;
                 description
                   "Duplicate protection mode";
               }
               leaf short-cycle-protection {
                 type string;
                 description
                   "Short cycle protection mode";
               }
               leaf direct-connect {
                 type string;
                 description
                   "Direct connect mode";
               }
               leaf ac-name {
                 type string;
                 description
                   "Access Concentrator name";
               }
               leaf underlying-interface-name {
                 type string;
                 description
                   "Underlying interface name";
               }
               leaf underlying-interface-index {
                 type string;
                 description
                   "Underlying interface index";
               }
               leaf encapsulation-type-identifier {
                 type string;
                 description
                   "Encapsulation type identifier";
               }
               leaf state {
                 type string;
                 description
                   "State";
               }
               leaf active-sessions {
                 type int32;
                 description
                   "Number of active PPPoE sessions";
               }
               leaf aci-autosensing {
                 type string;
                 description
                   "ACI VLAN Autosensing mode";
               }
               leaf line-identity-autosensing {
                 type string;
                 description
                   "Line Identity Autosensing mode";
               }
             }
           }
           list filter-information {
             leaf-list filter-input {
               type string;
               description
                 "Name of the input filter";
             }
             leaf-list filter-input-precedence {
               type uint32;
               description
                 "Precedence of the input filter";
             }
             leaf-list filter-output {
               type string;
               description
                 "Name of the output filter";
             }
             leaf-list filter-output-precedence {
               type uint32;
               description
                 "Precedence of the output filter";
             }
           }
           list policer-information {
             description
               "Interface policer information";
             leaf policer-input {
               type string;
               description
                 "Name of the input policer";
             }
             leaf policer-output {
               type string;
               description
                 "Name of the output policer";
             }
           }
           list interface-address {
             key "ifa-local";
             leaf-list interface-address.heading {
               type string;
             }
             leaf ifa-destination {
               type string;
               description
                 "Protocol address of the remote side of this connection";
             }
             leaf ifa-local {
               type string;
               description
                 "Protocol address on this interface";
             }
             leaf ifa-broadcast {
               type string;
               description
                 "Network broadcast address";
             }
             leaf ifa-primary-dns {
               type string;
               description
                 "Primary DNS server address";
             }
             leaf ifa-primary-nbns {
               type string;
               description
                 "Primary Netbios Name server address";
             }
             leaf ifa-secondary-dns {
               type string;
               description
                 "Secondary DNS server address";
             }
             leaf ifa-secondary-nbns {
               type string;
               description
                 "Secondary Netbios Name server address";
             }
             leaf ifa-address-pool {
               type string;
               description
                 "Address pool name";
             }
             leaf generation {
               type string;
               description
                 "Generation number used to distinguish between successive 
                 instances of this interface";
             }
             container ifa-flags {
               leaf ifaf-none {
                 type empty;
               }
               leaf ifaf-primary {
                 type empty;
               }
               leaf ifaf-preferred {
                 type empty;
               }
               leaf ifaf-master-only {
                 type empty;
               }
               leaf ifaf-down {
                 type empty;
               }
               leaf ifaf-kernel {
                 type empty;
               }
               leaf ifaf-current-default {
                 type empty;
               }
               leaf ifaf-current-preferred {
                 type empty;
               }
               leaf ifaf-current-primary {
                 type empty;
               }
               leaf ifaf-duplicate {
                 type empty;
               }
               leaf ifaf-webauth-http {
                 type empty;
               }
               leaf generic-value {
                 type int32;
                 description
                   "Hexadecimal value of unknown flag bits";
               }
               leaf internal-flags {
                 type string;
                 description
                   "Hexadecimal value of internal flag bits";
               }
             }
             container in6-addr-flags {
               leaf ifaf-none {
                 type empty;
               }
               leaf in6-anycast {
                 type empty;
               }
               leaf in6-tentative {
                 type empty;
               }
               leaf in6-duplicate {
                 type empty;
               }
               leaf in6-detached {
                 type empty;
               }
               leaf in6-deprecated {
                 type empty;
               }
               leaf in6-nodad {
                 type empty;
               }
               leaf in6-temporary {
                 type empty;
               }
               leaf in6-autoconf {
                 type empty;
               }
               leaf in6-nopfxmgmt {
                 type empty;
               }
             }
           }
           container mac-validate-statistics {
             description
               "SRC MAC validate statistics";
             leaf mac-validate-packets {
               type int32;
               description
                 "Number of packets that have failed the mac-validate check";
             }
             leaf mac-validate-bytes {
               type int32;
               description
                 "Number of bytes that have failed the mac-validate check";
             }
           }
           container route-rpf-statistics {
             description
               "Unicast reverse-path forwarding (RPF) statistics";
             leaf route-rpf-packets {
               type int32;
               description
                 "Number of packets that have failed the RPF check";
             }
             leaf route-rpf-bytes {
               type int32;
               description
                 "Number of bytes that have failed the RPF check";
             }
           }
           container destination-class-statistics {
             description
               "Destination class usage (DCU) statistics";
             list destination-class {
               description
                 "DCU statistics for a single class";
               leaf dcu-class-name {
                 type string;
                 description
                   "Name of DCU class";
               }
               leaf dcu-class-packets {
                 type int32;
                 description
                   "Number of packets counted by DCU for this class";
               }
               leaf dcu-class-bytes {
                 type int32;
                 description
                   "Number of bytes counted by DCU for this class";
               }
               leaf dcu-class-pps {
                 type int32;
                 description
                   "Packet-per-seconds counted by DCU for this class";
               }
               leaf dcu-class-bps {
                 type int32;
                 description
                   "Bit-per-seconds counted by DCU for this class";
               }
             }
           }
           container source-class-statistics {
             description
               "Source class usage (SCU) statistics";
             list source-class {
               description
                 "SCU statistics for a single class";
               leaf scu-class-name {
                 type string;
                 description
                   "Name of SCU class";
               }
               leaf scu-class-packets {
                 type int32;
                 description
                   "Number of packets counted by SCU for this class";
               }
               leaf scu-class-bytes {
                 type int32;
                 description
                   "Number of bytes counted by SCU for this class";
               }
               leaf scu-class-pps {
                 type int32;
                 description
                   "Packet-per-seconds counted by SCU for this class";
               }
               leaf scu-class-bps {
                 type int32;
                 description
                   "Bit-per-seconds counted by SCU for this class";
               }
             }
           }
           list local-bias-information {
             leaf local-bias-vtep-ifl-name {
               type string;
               description
                 "Interface name";
             }
             leaf local-bias-vtep-ifl-index {
               type uint32;
               description
                 "Interface index";
             }
             leaf local-bias-vtep-address {
               type string;
               description
                 "Protocol address of the connection";
             }
           }
         }
         list bridge-iff-properties {
           description
             "Information about Ethernet-switching address family";
         }
         container l2circuit-info {
           leaf out-of-sequence {
             type int32;
           }
           leaf denied-packets {
             type int32;
           }
           leaf cell-bundle-size {
             type int32;
           }
           leaf cell-bundle-timeout {
             type int32;
           }
           leaf cell-timeout-count {
             type int32;
           }
         }
         container irb-domain {
           leaf irb-routing-instance {
             type string;
             description
               "Name of the Routing Instance";
           }
           leaf irb-bridge {
             type string;
             description
               "Name of the Bridging Domain";
           }
         }
         container media-information {
           description
             "Information about media alarms";
           leaf media-type {
             type string;
             description
               "Type of media this information is for";
           }
           list media-alarm {
             leaf media-alarm-name {
               type string;
             }
             leaf media-alarm-count {
               type int32;
             }
             leaf media-alarm-seconds {
               type int32;
             }
             leaf media-alarm-state {
               type string;
             }
             leaf ce-counter-name {
               type string;
               description
                 "Circuit Emulation counter information";
             }
             leaf ce-counter-packets {
               type int32;
               description
                 "Circuit Emulation number of packets";
             }
             leaf ce-counter-bytes {
               type int32;
               description
                 "Circuit Emulation number of bytes";
             }
             leaf ce-counter-count {
               type int32;
               description
                 "Circuit Emulation number of event occurrences";
             }
           }
           leaf ds1-timeslots {
             type string;
           }
           leaf ds1-line-encoding {
             type string;
           }
           leaf ds1-byte-encoding {
             type string;
           }
           leaf ds1-data-inversion {
             type string;
           }
           leaf idle-cycle-flag {
             type string;
           }
           leaf start-end-flag {
             type string;
           }
           leaf ds0-byte-encoding {
             type string;
           }
           leaf ds0-data-inversion {
             type string;
           }
           leaf e3-data-inversion {
             type string;
           }
           leaf ds1-buildout {
             type string;
             description
               "Number of feet";
           }
         }
         container vtep-info {
           leaf vtep-type {
             type string;
             description
               "Type of VXLAN endpoint";
           }
           leaf vtep-address {
             type string;
             description
               "Protocol address of the connection";
           }
           leaf vtep-l2-routing-instance {
             type string;
             description
               "Name of the layer-2 routing instance";
           }
           leaf vtep-l3-routing-instance {
             type string;
             description
               "Name of the layer-3 routing instance";
           }
           leaf primary-vtep-address {
             type string;
             description
               "Primary Protocol address of the connection";
           }
           leaf vtep-token-count {
             type int32;
             description
               "VTEP additional tokens";
           }
           leaf-list vtep-token-array {
             type string;
             description
               "VTEP token array";
           }
         }
         container ft-info {
           leaf ft-dest-port {
             type int32;
             description
               "Destnation UDP port used in encap";
           }
           leaf ft-src-port-min {
             type int32;
             description
               "Source UDP port start range used in encap";
           }
           leaf ft-src-port-max {
             type int32;
             description
               "Source UDP port end range used in encap";
           }
           leaf ft-vnid {
             type int32;
             description
               "VNI value used in encap";
           }
           leaf ft-src-addr {
             type string;
             description
               "Source address used for encap";
           }
           leaf ft-dst-addr {
             type string;
             description
               "Destination address used for encap";
           }
           leaf ft-name {
             type string;
             description
               "Test interface name";
           }
           leaf ft-vlan-id {
             type int32;
             description
               "Vlan id of corresponding test interface";
           }
           leaf ft-mac {
             type string;
             description
               "Mac address";
           }
         }
         container rbeb-info {
           leaf rbeb-address {
             type string;
             description
               "Protocol address of the connection";
           }
           leaf rbeb-l2-routing-instance {
             type string;
             description
               "Name of the layer-2 routing instance";
           }
         }
         container macsec-statistics {
           description
             "MACSec Statistics ";
           leaf macsec-tx-sc-protected {
             type int32;
             description
               "Protected Secure Channel MACSec packets transmitted";
           }
           leaf macsec-tx-sc-encrypted {
             type int32;
             description
               "Encrypted Secure Channel MACSec packets transmitted";
           }
           leaf macsec-tx-sc-protectedbytes {
             type int32;
             description
               "Protected Secure Channel MACSec bytes transmitted";
           }
           leaf macsec-tx-sc-encryptedbytes {
             type int32;
             description
               "Encrypted Secure Channel MACSec bytes transmitted";
           }
           leaf macsec-rx-sc-ok {
             type int32;
             description
               "OK Secure Association MACSec packets received";
           }
           leaf macsec-rx-sc-validatedbytes {
             type int32;
             description
               "Validated Secure Association MACSec bytes received";
           }
           leaf macsec-rx-sc-decryptedbytes {
             type int32;
             description
               "Validated Secure Association MACSec bytes received";
           }
         }
         container security-input-flow-statistics {
           description
             "Flow input statistics for the interface";
           leaf flow-input-self-packets {
             type int32;
             description
               "Input Self packets";
           }
           leaf flow-input-icmp-packets {
             type int32;
             description
               "Input ICMP packets";
           }
           leaf flow-input-vpn-packets {
             type int32;
             description
               "Input VPN packets";
           }
           leaf flow-input-multicast-packets {
             type int32;
             description
               "Input multicast packets";
           }
           leaf flow-input-policy-bytes {
             type int32;
             description
               "Input policy bytes";
           }
           leaf flow-input-connections {
             type int32;
             description
               "Input connections";
           }
         }
         container security-output-flow-statistics {
           description
             "Flow output statistics for the interface";
           leaf flow-output-multicast-packets {
             type int32;
             description
               "Output multicast packets";
           }
           leaf flow-output-policy-bytes {
             type int32;
             description
               "Output bytes permitted by policy";
           }
         }
         container security-error-flow-statistics {
           description
             "Flow error statistics for the interface";
           leaf flow-error-policy-denied {
             type int32;
             description
               "Policy denied";
           }
           leaf flow-error-no-gate-parent {
             type int32;
             description
               "No parent for gate";
           }
           leaf flow-error-syn-protection {
             type int32;
             description
               "Syn-attack protection";
           }
           leaf flow-error-incoming-nat {
             type int32;
             description
               "Incoming NAT errors";
           }
           leaf flow-error-no-tunnel {
             type int32;
             description
               "No tunnel found";
           }
           leaf flow-error-no-more-session {
             type int32;
             description
               "No more sessions";
           }
           leaf flow-error-invalid-zone {
             type int32;
             description
               "Invalid zone received packet";
           }
           leaf flow-error-user-authentication {
             type int32;
             description
               "User authentication errors";
           }
           leaf flow-error-multiple-auth {
             type int32;
             description
               "Multiple user authentications";
           }
           leaf flow-error-multiple-incoming-nat {
             type int32;
             description
               "Multiple incoming NAT";
           }
           leaf flow-error-address-spoofing {
             type int32;
             description
               "Address spoofing";
           }
           leaf flow-error-null-zone {
             type int32;
             description
               "No zone or NULL zone binding";
           }
           leaf flow-error-no-nat-gate {
             type int32;
             description
               "No NAT gate";
           }
           leaf flow-error-no-minor-session {
             type int32;
             description
               "No minor session";
           }
           leaf flow-error-no-session-gate {
             type int32;
             description
               "No session for a gate";
           }
           leaf flow-error-seq-outside-window {
             type int32;
             description
               "TCP sequence number out of window";
           }
           leaf flow-error-no-route-present {
             type int32;
             description
               "No route present";
           }
           leaf flow-error-authentication-failed {
             type int32;
             description
               "Authentication failed";
           }
           leaf flow-error-security-association-missing {
             type int32;
             description
               "Security association not active";
           }
           leaf flow-error-no-sa-for-spi {
             type int32;
             description
               "No SA for incoming SPI";
           }
           leaf flow-error-no-interest-self-packet {
             type int32;
             description
               "No one interested in self packets";
           }
         }
         container multilink-bundle-status {
           description
             "Multilink bundle status";
           leaf rx-sequence-number {
             type string;
             description
               "Received sequence number";
           }
           leaf tx-sequence-number {
             type string;
             description
               "Transmitted sequence number";
           }
           leaf packet-drops {
             type int32;
             description
               "Number of packets dropped";
           }
           leaf packet-drop-bytes {
             type int32;
             description
               "Number of bytes in dropped packets";
           }
           leaf fragment-drops {
             type int32;
             description
               "Number of fragments dropped";
           }
           leaf fragment-drop-bytes {
             type int32;
             description
               "Number of bytes in dropped fragments";
           }
           leaf mrru-exceeded {
             type int32;
             description
               "Number of assembled packets that exceeded MRRU";
           }
           leaf processing-errors {
             type int32;
             description
               "Number of errors encountered in assembling packets";
           }
           leaf fragment-timeout {
             type int32;
             description
               "Fragments timed out during assembly";
           }
           leaf sequence-number-missing {
             type int32;
             description
               "Gap detected in sequence numbers";
           }
           leaf out-of-order-sequence-number {
             type int32;
             description
               "Fragments with an out-of-order sequence number";
           }
           leaf out-of-range-sequence-number {
             type int32;
             description
               "Fragments with an out-of-range sequence number";
           }
           leaf packet-buffer-overflow {
             type int32;
             description
               "Number of times the packet data buffer overflowed";
           }
           leaf fragment-buffer-overflow {
             type int32;
             description
               "Number of times the fragment data buffer overflowed";
           }
         }
         container multilink-bundle-class {
           description
             "Multilink class status";
           leaf multilink-class-id {
             type int32;
             description
               "Multilink class ID";
           }
           leaf rx-sequence-number {
             type string;
             description
               "Received sequence number";
           }
           leaf tx-sequence-number {
             type string;
             description
               "Transmitted sequence number";
           }
           leaf packet-drops {
             type int32;
             description
               "Number of packets dropped";
           }
           leaf packet-drop-bytes {
             type int32;
             description
               "Number of bytes in dropped packets";
           }
           leaf fragment-drops {
             type int32;
             description
               "Number of fragments dropped";
           }
           leaf fragment-drop-bytes {
             type int32;
             description
               "Number of bytes in dropped fragments";
           }
           leaf mrru-exceeded {
             type int32;
             description
               "Number of assembled packets that exceeded MRRU";
           }
           leaf processing-errors {
             type int32;
             description
               "Number of errors encountered in assembling packets";
           }
           leaf fragment-timeout {
             type int32;
             description
               "Fragments timed out during assembly";
           }
           leaf sequence-number-missing {
             type int32;
             description
               "Gap detected in sequence numbers";
           }
           leaf out-of-order-sequence-number {
             type int32;
             description
               "Fragments with an out-of-order sequence number";
           }
           leaf out-of-range-sequence-number {
             type int32;
             description
               "Fragments with an out-of-range sequence number";
           }
           leaf packet-buffer-overflow {
             type int32;
             description
               "Number of times the packet data buffer overflowed";
           }
           leaf fragment-buffer-overflow {
             type int32;
             description
               "Number of times the fragment data buffer overflowed";
           }
           leaf multilink-class-drop-timeout {
             type int32;
             description
               "Drop timeout for multilink class (milliseconds)";
           }
         }
         container lag-traffic-statistics {
           container lag-bundle {
             leaf input-packets {
               type uint64;
             }
             leaf input-pps {
               type int32;
             }
             leaf input-bytes {
               type int32;
             }
             leaf input-bps {
               type int32;
             }
             leaf output-packets {
               type uint64;
             }
             leaf output-pps {
               type int32;
             }
             leaf output-bytes {
               type int32;
             }
             leaf output-bps {
               type int32;
             }
           }
           container lag-adaptive-statistics {
             leaf adaptive-adjusts {
               type int32;
             }
             leaf adaptive-scans {
               type int32;
             }
             leaf adaptive-updates {
               type int32;
             }
           }
           container lag-multicast-statistics {
             leaf lag-multicast-statistics-header {
               type empty;
             }
             container lag-ipv4-multicast-statistics {
               leaf input-packets {
                 type uint64;
               }
               leaf input-pps {
                 type int32;
               }
               leaf input-bytes {
                 type int32;
               }
               leaf input-bps {
                 type int32;
               }
               leaf output-packets {
                 type uint64;
               }
               leaf output-pps {
                 type int32;
               }
               leaf output-bytes {
                 type int32;
               }
               leaf output-bps {
                 type int32;
               }
             }
             container lag-ipv6-multicast-statistics {
               leaf input-packets {
                 type uint64;
               }
               leaf input-pps {
                 type int32;
               }
               leaf input-bytes {
                 type int32;
               }
               leaf input-bps {
                 type int32;
               }
               leaf output-packets {
                 type uint64;
               }
               leaf output-pps {
                 type int32;
               }
               leaf output-bytes {
                 type int32;
               }
               leaf output-bps {
                 type int32;
               }
             }
           }
           container aggregate-member-info {
             leaf aggregate-member-count {
               type uint32;
             }
           }
           list lag-link {
             key "name";
             leaf name {
               type string;
               description
                 "Name of this item";
             }
             leaf down {
               type empty;
               description
                 "Link is down";
             }
             leaf input-packets {
               type uint64;
             }
             leaf input-pps {
               type int32;
             }
             leaf input-bytes {
               type int32;
             }
             leaf input-bps {
               type int32;
             }
             leaf output-packets {
               type uint64;
             }
             leaf output-pps {
               type int32;
             }
             leaf output-bytes {
               type int32;
             }
             leaf output-bps {
               type int32;
             }
           }
           list lag-bfd-view {
             key "name";
             leaf name {
               type string;
               description
                 "Name of this item";
             }
             leaf link-usability {
               type string;
             }
           }
           list lag-targeting-summary {
             leaf targeting-intf-name {
               type string;
             }
             leaf targeting-intf-type {
               type string;
             }
             leaf targeting-intf-link-state {
               type string;
             }
           }
           list lag-marker {
             key "name";
             leaf name {
               type string;
               description
                 "Name of this item";
             }
             leaf marker-rx-packets {
               type string;
             }
             leaf marker-response-tx-packets {
               type string;
             }
             leaf lacp-rx-packets {
               type string;
               description
                 "Number of LACP packets received";
             }
             leaf lacp-tx-packets {
               type string;
               description
                 "Number of LACP packets transmitted";
             }
             leaf unknown-rx-packets {
               type string;
               description
                 "Number of unknown type packets received";
             }
             leaf illegal-rx-packets {
               type string;
               description
                 "Number of ill formed packets received";
             }
           }
           list lag-lacp-statistics {
             key "name";
             leaf name {
               type string;
               description
                 "Name of this item";
             }
             leaf lacp-rx-packets {
               type string;
               description
                 "Number of LACP packets received";
             }
             leaf lacp-tx-packets {
               type string;
               description
                 "Number of LACP packets transmitted";
             }
             leaf unknown-rx-packets {
               type string;
               description
                 "Number of unknown type packets received";
             }
             leaf illegal-rx-packets {
               type string;
               description
                 "Number of ill formed packets received";
             }
           }
           list if-distribution-list-information {
             leaf list-type {
               type string;
             }
             leaf list-status {
               type string;
             }
             list if-list {
               leaf if-child-name {
                 type string;
               }
               leaf if-status {
                 type string;
               }
             }
           }
           list lag-link-protection-subgrp {
             key "name";
             leaf name {
               type string;
               description
                 "Name of this item";
             }
             leaf lag-link-protection-subgrp-name {
               type string;
             }
             leaf lag-link-protection-subgrp-state {
               type string;
             }
           }
           list lag-lacp-info {
             key "name";
             description
               "LACP information";
             leaf name {
               type string;
               description
                 "Name of this item";
             }
             leaf lacp-role {
               type string;
               description
                 "Whether it is an actor or partner";
             }
             leaf lacp-sys-priority {
               type string;
               description
                 "System priority";
             }
             leaf lacp-system-id {
               type string;
               description
                 "LACP system identifier";
             }
             leaf lacp-port-priority {
               type string;
               description
                 "Priority of the port";
             }
             leaf lacp-port-number {
               type string;
               description
                 "Port number";
             }
             leaf lacp-port-key {
               type string;
               description
                 "Operational key of the port";
             }
           }
           list lag-lacp-state {
             key "name";
             description
               "LACP protocol state information";
             leaf name {
               type string;
               description
                 "Name of this item";
             }
             leaf lacp-role {
               type string;
               description
                 "Whether it is an actor or partner";
             }
             leaf lacp-expired {
               type string;
               description
                 "State of the receive lacp machine is EXPIRED?";
             }
             leaf lacp-defaulted {
               type string;
               description
                 "State of the receive lacp machine is DEFAULTED?";
             }
             leaf lacp-distributing {
               type string;
               description
                 "State of the mux lacp machine is DISTRIBUTING?";
             }
             leaf lacp-collecting {
               type string;
               description
                 "State of the mux lacp machine is COLLECTING?";
             }
             leaf lacp-synchronization {
               type string;
               description
                 "Actor view of partner information is in sync";
             }
             leaf lacp-aggregation {
               type string;
               description
                 "Actor view of partner information is in sync";
             }
             leaf lacp-timeout {
               type string;
               description
                 "Configured as either fast or slow periodic";
             }
             leaf lacp-activity {
               type string;
               description
                 "Configured as either active or passive";
             }
           }
           list lag-lacp-protocol {
             key "name";
             description
               "LACP protocol information";
             leaf name {
               type string;
               description
                 "Name of this item";
             }
             leaf lacp-receive-state {
               type string;
               description
                 "State of the receive lacp machine";
             }
             leaf lacp-transmit-state {
               type string;
               description
                 "State of the transmit lacp machine";
             }
             leaf lacp-mux-state {
               type string;
               description
                 "State of the mux lacp machine";
             }
           }
           list lag-lacp-bfd {
             key "name";
             description
               "BFD protocol information";
             leaf name {
               type string;
               description
                 "Name of this item";
             }
             leaf lacp-bfd-state {
               type string;
               description
                 "State of the BFD session";
             }
           }
           list lacp-hold-up-information {
             key "name";
             description
               "LACP hold-up information";
             leaf name {
               type string;
               description
                 "Name of this item";
             }
             leaf status {
               type string;
             }
             leaf restart-count {
               type int32;
             }
             leaf time-to-expire {
               type int32;
             }
             leaf start-time {
               type string;
             }
           }
           container ifd-lag-traffic-statistics {
           }
         }
         container ifd-lag-traffic-statistics {
           list ifd-lag-members-list {
             key "name";
             leaf name {
               type string;
               description
                 "Name of this item";
             }
             leaf down {
               type empty;
               description
                 "Link is down";
             }
             leaf input-packets {
               type uint64;
             }
             leaf input-pps {
               type int32;
             }
             leaf input-bytes {
               type int32;
             }
             leaf input-bps {
               type int32;
             }
             leaf output-packets {
               type uint64;
             }
             leaf output-pps {
               type int32;
             }
             leaf output-bytes {
               type int32;
             }
             leaf output-bps {
               type int32;
             }
           }
         }
         container layer2-input-policer-statistics {
           description
             "Layer 2 input policer statistics for interface";
           leaf policer-low-iq2-frames {
             type int32;
             description
               "Number of loss priority low frames";
           }
           leaf policer-medium-low-iq2-frames {
             type int32;
             description
               "Number of loss priority medium low frames";
           }
           leaf policer-medium-high-iq2-frames {
             type int32;
             description
               "Number of loss priority medium high frames";
           }
           leaf policer-high-iq2-frames {
             type int32;
             description
               "Number of loss priority high frames";
           }
           leaf policer-dropped-iq2-frames {
             type int32;
             description
               "Number of dropped frames";
           }
           leaf policer-low-bytes {
             type int32;
             description
               "Number of loss priority low bytes";
           }
           leaf policer-low-frames {
             type int32;
             description
               "Number of loss priority low frames";
           }
           leaf policer-low-rate {
             type int32;
             description
               "Rate of loss priority low pkts";
           }
           leaf policer-medium-high-bytes {
             type int32;
             description
               "Number of loss priority medium high bytes";
           }
           leaf policer-medium-high-frames {
             type int32;
             description
               "Number of loss priority medium high frames";
           }
           leaf policer-medium-high-rate {
             type int32;
             description
               "Rate of loss priority medium high rate";
           }
           leaf policer-high-bytes {
             type int32;
             description
               "Number of loss priority high bytes";
           }
           leaf policer-high-frames {
             type int32;
             description
               "Number of loss priority high frames";
           }
           leaf policer-high-rate {
             type int32;
             description
               "Rate of loss priority high rate";
           }
           leaf policer-dropped-bytes {
             type int32;
             description
               "Number of dropped bytes";
           }
           leaf policer-dropped-frames {
             type int32;
             description
               "Number of dropped frames";
           }
           leaf policer-dropped-rate {
             type int32;
             description
               "Number of dropped rate";
           }
           leaf policer-medium-low-frames {
             type int32;
             description
               "Number of loss priority medium low frames";
           }
           leaf policer-medium-low-bytes {
             type int32;
             description
               "Number of loss priority medium low bytes";
           }
           leaf policer-medium-low-rate {
             type int32;
             description
               "Rate of loss priority medium low pkts";
           }
         }
         container layer2-output-policer-statistics {
           description
             "Layer 2 output policer statistics for interface";
           leaf policer-low-iq2-frames {
             type int32;
             description
               "Number of loss priority low frames";
           }
           leaf policer-medium-low-iq2-frames {
             type int32;
             description
               "Number of loss priority medium low frames";
           }
           leaf policer-medium-high-iq2-frames {
             type int32;
             description
               "Number of loss priority medium high frames";
           }
           leaf policer-high-iq2-frames {
             type int32;
             description
               "Number of loss priority high frames";
           }
           leaf policer-dropped-iq2-frames {
             type int32;
             description
               "Number of dropped frames";
           }
           leaf policer-low-bytes {
             type int32;
             description
               "Number of loss priority low bytes";
           }
           leaf policer-low-frames {
             type int32;
             description
               "Number of loss priority low frames";
           }
           leaf policer-low-rate {
             type int32;
             description
               "Rate of loss priority low pkts";
           }
           leaf policer-medium-high-bytes {
             type int32;
             description
               "Number of loss priority medium high bytes";
           }
           leaf policer-medium-high-frames {
             type int32;
             description
               "Number of loss priority medium high frames";
           }
           leaf policer-medium-high-rate {
             type int32;
             description
               "Rate of loss priority medium high rate";
           }
           leaf policer-high-bytes {
             type int32;
             description
               "Number of loss priority high bytes";
           }
           leaf policer-high-frames {
             type int32;
             description
               "Number of loss priority high frames";
           }
           leaf policer-high-rate {
             type int32;
             description
               "Rate of loss priority high rate";
           }
           leaf policer-dropped-bytes {
             type int32;
             description
               "Number of dropped bytes";
           }
           leaf policer-dropped-frames {
             type int32;
             description
               "Number of dropped frames";
           }
           leaf policer-dropped-rate {
             type int32;
             description
               "Number of dropped rate";
           }
           leaf policer-medium-low-frames {
             type int32;
             description
               "Number of loss priority medium low frames";
           }
           leaf policer-medium-low-bytes {
             type int32;
             description
               "Number of loss priority medium low bytes";
           }
           leaf policer-medium-low-rate {
             type int32;
             description
               "Rate of loss priority medium low pkts";
           }
         }
         container atm-input-policer-statistics {
           description
             "ATM input Policer Statistics for interface";
           leaf atm-policer-traffic-count-cells {
             type int32;
             description
               "Stats for counted ATM Cells";
           }
           leaf atm-policer-traffic-discard-cells {
             type int32;
             description
               "Stats for discarded ATM Cells";
           }
           leaf atm-policer-traffic-discard-tag-cells {
             type int32;
             description
               "Stats for discard-tag ATM Cells";
           }
         }
         container mac-policer-information {
           leaf mac-address {
             type jt:mac-addr;
           }
           leaf mac-entry-type {
             type string;
           }
           leaf receive-bytes {
             type int32;
           }
           leaf transmit-bytes {
             type int32;
           }
           leaf receive-frames {
             type int32;
           }
           leaf transmit-frames {
             type int32;
           }
           container ether-policer-list {
             list ether-policer-record {
               leaf policer-type {
                 type string;
               }
               leaf out-of-spec-frames {
                 type int32;
               }
               leaf out-of-spec-bytes {
                 type int32;
               }
             }
           }
         }
         leaf admin-status {
           type string;
           description
             "Desired state of the interface";
         }
         leaf oper-status {
           type string;
           description
             "Current operational state of the interface";
         }
         leaf vrfname {
           type string;
           description
             "Routing instance name";
         }
         leaf zonename {
           type string;
           description
             "Zone name";
         }
       }
       container active-alarms-otn {
         leaf type-otn {
           type string;
           description
             "OTN type for associated interface alarms";
         }
         container interface-alarms {
           description
             "Container tag for interface alarms";
           leaf alarm-not-present {
             type empty;
             description
               "No alarm indicated";
           }
           leaf sonet-alarm-lol {
             type empty;
             description
               "Loss of light alarm";
           }
           leaf sonet-alarm-pll {
             type empty;
             description
               "PLL lock alarm";
           }
           leaf sonet-alarm-lof {
             type empty;
             description
               "Loss of frame alarm";
           }
           leaf sonet-alarm-los {
             type empty;
             description
               "Loss of signal alarm";
           }
           leaf sonet-alarm-sef {
             type empty;
             description
               "Severely errored frame alarm";
           }
           leaf sonet-alarm-lais {
             type empty;
             description
               "Line AIS alarm";
           }
           leaf sonet-alarm-pais {
             type empty;
             description
               "Path AIS alarm";
           }
           leaf sonet-alarm-lop {
             type empty;
             description
               "Loss of pointer alarm";
           }
           leaf sonet-alarm-berr-sd {
             type empty;
             description
               "Bit error rate alarm, defect";
           }
           leaf sonet-alarm-berr-sf {
             type empty;
             description
               "Bit error rate alarm, fault";
           }
           leaf sonet-alarm-lrdi {
             type empty;
             description
               "Line remote defect indicator alarm";
           }
           leaf sonet-alarm-prdi {
             type empty;
             description
               "Path remote defect indicator alarm";
           }
           leaf sonet-alarm-rei {
             type empty;
             description
               "Path remote error indicator alarm";
           }
           leaf sonet-alarm-uneq {
             type empty;
             description
               "Unequipped alarm";
           }
           leaf sonet-alarm-pmis {
             type empty;
             description
               "Path payload level mismatch alarm";
           }
           leaf sonet-alarm-loc {
             type empty;
             description
               "Loss of cell delineation alarm";
           }
           leaf sonet-alarm-vais {
             type empty;
             description
               "VT AIS alarm";
           }
           leaf sonet-alarm-vlop {
             type empty;
             description
               "VT loss of pointer alarm";
           }
           leaf sonet-alarm-vrdi {
             type empty;
             description
               "VT remote defect indicator alarm";
           }
           leaf sonet-alarm-vuneq {
             type empty;
             description
               "VT unequipped alarm";
           }
           leaf sonet-alarm-vmis {
             type empty;
             description
               "VT label mismatch alarm";
           }
           leaf sonet-alarm-vloc {
             type empty;
             description
               "VT loss of cell delineation alarm";
           }
           leaf sdh-alarm-lol {
             type empty;
             description
               "Loss of light alarm";
           }
           leaf sdh-alarm-pll {
             type empty;
             description
               "PLL lock alarm";
           }
           leaf sdh-alarm-lof {
             type empty;
             description
               "Loss of frame alarm";
           }
           leaf sdh-alarm-los {
             type empty;
             description
               "Loss of signal alarm";
           }
           leaf sdh-alarm-oof {
             type empty;
             description
               "Out of frame alarm";
           }
           leaf sdh-alarm-msais {
             type empty;
             description
               "Multiplex section AIS alarm";
           }
           leaf sdh-alarm-hpais {
             type empty;
             description
               "High order path AIS alarm";
           }
           leaf sdh-alarm-lop {
             type empty;
             description
               "Loss of pointer alarm";
           }
           leaf sdh-alarm-berr-sd {
             type empty;
             description
               "Bit error rate alarm, defect";
           }
           leaf sdh-alarm-berr-sf {
             type empty;
             description
               "Bit error rate alarm, fault";
           }
           leaf sdh-alarm-msferf {
             type empty;
             description
               "Multiplex section far-end remote failure alarm";
           }
           leaf sdh-alarm-hpferf {
             type empty;
             description
               "High order path far-end remote failure alarm";
           }
           leaf sdh-alarm-hpfebe {
             type empty;
             description
               "High order path far-end block error alarm";
           }
           leaf sdh-alarm-hpuneq {
             type empty;
             description
               "High order path unequipped alarm";
           }
           leaf sdh-alarm-hpplm {
             type empty;
             description
               "High order path payload level mismatch alarm";
           }
           leaf sdh-alarm-loc {
             type empty;
             description
               "Loss of cell delineation alarm";
           }
           leaf sdh-alarm-tuais {
             type empty;
             description
               "TU AIS alarm";
           }
           leaf sdh-alarm-tulop {
             type empty;
             description
               "TU loss of pointer alarm";
           }
           leaf sdh-alarm-turdi {
             type empty;
             description
               "TU remote defect indicator alarm";
           }
           leaf sdh-alarm-tuuneq {
             type empty;
             description
               "TU unequipped alarm";
           }
           leaf sdh-alarm-tumis {
             type empty;
             description
               "TU label mismatch error";
           }
           leaf sdh-alarm-tuloc {
             type empty;
             description
               "TU loss of cell delineation alarm";
           }
           leaf ds3-alarm-pll {
             type empty;
             description
               "PLL lock alarm";
           }
           leaf ds3-alarm-ais {
             type empty;
             description
               "AIS alarm";
           }
           leaf ds3-alarm-lof {
             type empty;
             description
               "Loss of frame alarm";
           }
           leaf ds3-alarm-los {
             type empty;
             description
               "Loss of signal alarm";
           }
           leaf ds3-alarm-lcv {
             type empty;
             description
               "Line code violation alarm";
           }
           leaf ds3-alarm-exz {
             type empty;
             description
               "Excessive zeros alarm";
           }
           leaf ds3-alarm-ferf {
             type empty;
             description
               "Far-end receive failure alarm";
           }
           leaf ds3-alarm-ylw {
             type empty;
             description
               "Yellow alarm";
           }
           leaf ds3-alarm-idle {
             type empty;
             description
               "Idle alarm";
           }
           leaf ds1-alarm-ais {
             type empty;
             description
               "AIS alarm";
           }
           leaf ds1-alarm-lof {
             type empty;
             description
               "Loss of frame alarm";
           }
           leaf ds1-alarm-los {
             type empty;
             description
               "Loss of signal alarm";
           }
           leaf ds1-alarm-ylw {
             type empty;
             description
               "Yellow alarm";
           }
           leaf ds1-alarm-crc-major {
             type empty;
             description
               "CRC errors crossed major threshold";
           }
           leaf ds1-alarm-crc-minor {
             type empty;
             description
               "CRC errors crossed minor threshold";
           }
           leaf dsl-alarm-lof {
             type empty;
             description
               "Loss of frame alarm";
           }
           leaf dsl-alarm-los {
             type empty;
             description
               "Loss of signal alarm";
           }
           leaf dsl-alarm-lom {
             type empty;
             description
               "Loss of multiframe alarm";
           }
           leaf dsl-alarm-locdi {
             type empty;
             description
               "Loss of cell delineation alarm for interleaved channel";
           }
           leaf dsl-alarm-locdni {
             type empty;
             description
               "Loss of cell delineation alarm for non-interleaved channel";
           }
           leaf dsl-alarm-lop {
             type empty;
             description
               "Loss of power alarm";
           }
           leaf dsl-alarm-far-lof {
             type empty;
             description
               "Far-end loss-of-frame alarm";
           }
           leaf dsl-alarm-far-los {
             type empty;
             description
               "Far-end loss-of-signal alarm";
           }
           leaf dsl-alarm-far-locdi {
             type empty;
             description
               "Far-end loss-of-cell-delineation alarm for interleaved 
               channel";
           }
           leaf dsl-alarm-far-locdni {
             type empty;
             description
               "Far-end loss-of-cell-delineation alarm for non-interleaved 
               channel";
           }
           leaf fibrechannel-alarm-link-down {
             type empty;
             description
               "Link alive failure";
           }
           leaf ethernet-alarm-link-down {
             type empty;
             description
               "Link alive failure";
           }
           leaf ethernet-alarm-an-not-supported {
             type empty;
             description
               "AN not supported";
           }
           leaf ethernet-alarm-link-local-fault {
             type empty;
             description
               "Link local fault";
           }
           leaf ethernet-alarm-link-remote-fault {
             type empty;
             description
               "Link remote fault";
           }
           leaf ethernet-alarm-link-local-degrade {
             type empty;
             description
               "Link local degrade";
           }
           leaf ethernet-alarm-link-remote-degrade {
             type empty;
             description
               "Link remote degrade";
           }
           leaf ethernet-alarm-lcdp {
             type empty;
             description
               "Loss of code-group delineation";
           }
           leaf isdn-alarm-los {
             type empty;
             description
               "Loss of signal alarm";
           }
           leaf isdn-alarm-lof {
             type empty;
             description
               "Loss of frame alarm";
           }
           leaf shdsl-alarm-losd {
             type empty;
             description
               "Loss of signal alarm";
           }
           leaf shdsl-alarm-losw {
             type empty;
             description
               "Loss of sync word alarm";
           }
           leaf shdsl-alarm-line1-losd {
             type empty;
             description
               "Loss of signal (line 1) alarm";
           }
           leaf shdsl-alarm-line1-losw {
             type empty;
             description
               "Loss of sync word (line 1) alarm";
           }
           leaf shdsl-alarm-line2-losd {
             type empty;
             description
               "Loss of signal (line 2) alarm";
           }
           leaf shdsl-alarm-line2-losw {
             type empty;
             description
               "Loss of sync word (line 2) alarm";
           }
           leaf shdsl-efm-alarm-losd {
             type empty;
             description
               "Loss of signal alarm";
           }
           leaf shdsl-efm-alarm-losw {
             type empty;
             description
               "Loss of sync word alarm";
           }
           leaf otn-alarm-los {
             type empty;
             description
               "Loss of signal alarm";
           }
           leaf otn-alarm-lof {
             type empty;
             description
               "Loss of frame alarm";
           }
           leaf otn-alarm-lom {
             type empty;
             description
               "Loss of multiframe alarm";
           }
           leaf otn-alarm-wavelength-lock {
             type empty;
             description
               "Loss of Wavelength Lock alarm";
           }
           leaf otn-alarm-otu-ais {
             type empty;
             description
               "OTU Alarm Indication Signal alarm";
           }
           leaf otn-alarm-otu-bdi {
             type empty;
             description
               "OTU Background Block Error alarm";
           }
           leaf otn-alarm-otu-ttim {
             type empty;
             description
               "OTU Trail Trace Identifier Mismatch alarm";
           }
           leaf otn-alarm-otu-iae {
             type empty;
             description
               "OTU Incoming Alignment alarm";
           }
           leaf otn-alarm-otu-sd {
             type empty;
             description
               "OTU Signal Degrade alarm";
           }
           leaf otn-alarm-otu-sf {
             type empty;
             description
               "OTU Signal Fail alarm";
           }
           leaf otn-alarm-otu-biae {
             type empty;
             description
               "OTU Backward Incoming Alignment alarm";
           }
           leaf otn-alarm-otu-tsf {
             type empty;
             description
               "OTU Trail Signal Fail alarm";
           }
           leaf otn-alarm-otu-ssf {
             type empty;
             description
               "OTU Server Signal Fail alarm";
           }
           leaf otn-alarm-otu-fec-excessive {
             type empty;
             description
               "OTU FEC Excessive alarm";
           }
           leaf otn-alarm-otu-fec-degraded {
             type empty;
             description
               "OTU FEC Degraded alarm";
           }
           leaf otn-alarm-otu-fe-fec-degraded {
             type empty;
             description
               "OTU FE FEC Degraded/Excessive alarm";
           }
           leaf otn-alarm-otu-threshold-bbe {
             type empty;
             description
               "OTU Background Block Error threshold alarm";
           }
           leaf otn-alarm-otu-threshold-es {
             type empty;
             description
               "OTU Errored Seconds threshold alarm";
           }
           leaf otn-alarm-otu-threshold-ses {
             type empty;
             description
               "OTU Severely Errored Seconds threshold alarm";
           }
           leaf otn-alarm-otu-threshold-uas {
             type empty;
             description
               "OTU Unavailable Seconds threshold alarm";
           }
           leaf otn-alarm-odu-ais {
             type empty;
             description
               "ODU  Alarm Indiaction Signal alarm";
           }
           leaf otn-alarm-odu-oci {
             type empty;
             description
               "ODU Open Connection Indication alarm";
           }
           leaf otn-alarm-odu-lck {
             type empty;
             description
               "ODU Locked alarm";
           }
           leaf otn-alarm-odu-bdi {
             type empty;
             description
               "ODU Backward Defect Indication alarm";
           }
           leaf otn-alarm-odu-ttim {
             type empty;
             description
               "ODU Trail Trace Identifier Mismatch alarm";
           }
           leaf otn-alarm-odu-sd {
             type empty;
             description
               "ODU Signal Degrade alarm";
           }
           leaf otn-alarm-odu-sf {
             type empty;
             description
               "ODU Signal Fail alarm";
           }
           leaf otn-alarm-odu-iae {
             type empty;
             description
               "ODU Incoming Alignment alarm";
           }
           leaf otn-alarm-odu-ltc {
             type empty;
             description
               "ODU Loss of Tandem Connection alarm";
           }
           leaf otn-alarm-odu-csf {
             type empty;
             description
               "ODU Client Signal Fail alarm";
           }
           leaf otn-alarm-odu-tsf {
             type empty;
             description
               "ODU Trail Signal Fail alarm";
           }
           leaf otn-alarm-odu-ssf {
             type empty;
             description
               "ODU Server Signal Fail alarm";
           }
           leaf otn-alarm-odu-rx-aps-change {
             type empty;
             description
               "ODU Rx Aps Change alarm";
           }
           leaf otn-alarm-odu-threshold-bbe {
             type empty;
             description
               "ODU Background Block Error threshold alarm";
           }
           leaf otn-alarm-odu-threshold-es {
             type empty;
             description
               "ODU Errored Seconds threshold alarm";
           }
           leaf otn-alarm-odu-threshold-ses {
             type empty;
             description
               "ODU Severely Errored Seconds threshold alarm";
           }
           leaf otn-alarm-odu-threshold-uas {
             type empty;
             description
               "ODU Unavailable Seconds threshold alarm";
           }
           leaf otn-alarm-opu-pmi {
             type empty;
             description
               "OPU Payload Mismatch alarm";
           }
           leaf otn-alarm-pre-fec-sd {
             type empty;
             description
               "Pre-FEC SD alarm";
           }
           leaf otn-alarm-fe-pre-fec-sd {
             type empty;
             description
               "Far end pre-FEC SD alarm";
           }
           leaf optics-alarms-mod-fault {
             type empty;
             description
               "Module Fault alarm";
           }
           leaf optics-alarms-lol {
             type empty;
             description
               "Loss of Lock alarm";
           }
           leaf optics-alarms-los {
             type empty;
             description
               "Loss of Signal alarms";
           }
           leaf optics-alarms-lof {
             type empty;
             description
               "Loss of frame alarm";
           }
           leaf optics-alarms-lom {
             type empty;
             description
               "Loss of multi-frame alarm";
           }
           leaf optics-alarms-otu-bdi {
             type empty;
             description
               "Backward defect indiacation alarm";
           }
           leaf optics-alarms-rmsf {
             type empty;
             description
               "Rx Modem sysnc fault alarm";
           }
           leaf optics-alarms-rmlol {
             type empty;
             description
               "Rx Modem loss of lock alarm";
           }
           leaf optics-alarms-rloa {
             type empty;
             description
               "Rx loss of alignment alarm";
           }
           leaf optics-alarms-mbclf {
             type empty;
             description
               "Modulator Bias control loop fail alarm";
           }
           leaf optics-alarms-itlaf {
             type empty;
             description
               "ITLA Fault alarm";
           }
           leaf optics-alarms-daccf {
             type empty;
             description
               "DAC Calibration Fault alarm";
           }
           leaf optics-alarms-adccf {
             type empty;
             description
               "ADC Calibration Fault alarm";
           }
           leaf optics-alarms-fec-degrade {
             type empty;
             description
               "FEC Degrade alarm";
           }
           leaf optics-alarms-fec-excessive {
             type empty;
             description
               "FEC Excessive alarm";
           }
           leaf optics-alarms-fe-fec-degrade {
             type empty;
             description
               "Far-end FEC Degrade alarm";
           }
           leaf optics-alarms-fe-fec-excessive {
             type empty;
             description
               "Far-end FEC Excessive alarm";
           }
           leaf ima-alarm-startup-fe {
             type empty;
             description
               "IMA group startup far-end alarm";
           }
           leaf ima-alarm-config-abort {
             type empty;
             description
               "IMA group config abort alarm";
           }
           leaf ima-alarm-config-abort-fe {
             type empty;
             description
               "IMA group config abort far-end alarm";
           }
           leaf ima-alarm-insufficient-links {
             type empty;
             description
               "IMA group insufficient links alarm";
           }
           leaf ima-alarm-insufficient-links-fe {
             type empty;
             description
               "IMA group insufficient links far-end alarm";
           }
           leaf ima-alarm-blocked {
             type empty;
             description
               "IMA group blocked alarm";
           }
           leaf ima-alarm-blocked-fe {
             type empty;
             description
               "IMA group blocked far-end alarm";
           }
           leaf ima-alarm-timing-mismatch {
             type empty;
             description
               "IMA group timing mismatch alarm";
           }
           leaf ima-alarm-version-mismatch {
             type empty;
             description
               "IMA group version mismatch alarm";
           }
           leaf ima-alarm-lif {
             type empty;
             description
               "IMA link loss of IMA frame alarm";
           }
           leaf ima-alarm-lods {
             type empty;
             description
               "IMA link out of delay synchronization alarm";
           }
           leaf ima-alarm-rdi {
             type empty;
             description
               "IMA link remote defect indicator alarm";
           }
           leaf ima-alarm-tx-misconnected {
             type empty;
             description
               "IMA link tx misconnected alarm";
           }
           leaf ima-alarm-rx-misconnected {
             type empty;
             description
               "IMA link rx misconnected alarm";
           }
           leaf ima-alarm-fault {
             type empty;
             description
               "IMA link fault alarm";
           }
           leaf ima-alarm-tx-unusable-fe {
             type empty;
             description
               "IMA link Tx unusable far-end alarm";
           }
           leaf ima-alarm-rx-unusable-fe {
             type empty;
             description
               "IMA link Tx unusable far-end alarm";
           }
           leaf generic-value {
             type int32;
             description
               "Hexadecimal value of unknown flag bits";
           }
         }
       }
       container active-defects-otn {
         leaf type-otn {
           type string;
           description
             "OTN type for associated interface alarms";
         }
         container interface-alarms {
           description
             "Container tag for interface alarms";
           leaf alarm-not-present {
             type empty;
             description
               "No alarm indicated";
           }
           leaf sonet-alarm-lol {
             type empty;
             description
               "Loss of light alarm";
           }
           leaf sonet-alarm-pll {
             type empty;
             description
               "PLL lock alarm";
           }
           leaf sonet-alarm-lof {
             type empty;
             description
               "Loss of frame alarm";
           }
           leaf sonet-alarm-los {
             type empty;
             description
               "Loss of signal alarm";
           }
           leaf sonet-alarm-sef {
             type empty;
             description
               "Severely errored frame alarm";
           }
           leaf sonet-alarm-lais {
             type empty;
             description
               "Line AIS alarm";
           }
           leaf sonet-alarm-pais {
             type empty;
             description
               "Path AIS alarm";
           }
           leaf sonet-alarm-lop {
             type empty;
             description
               "Loss of pointer alarm";
           }
           leaf sonet-alarm-berr-sd {
             type empty;
             description
               "Bit error rate alarm, defect";
           }
           leaf sonet-alarm-berr-sf {
             type empty;
             description
               "Bit error rate alarm, fault";
           }
           leaf sonet-alarm-lrdi {
             type empty;
             description
               "Line remote defect indicator alarm";
           }
           leaf sonet-alarm-prdi {
             type empty;
             description
               "Path remote defect indicator alarm";
           }
           leaf sonet-alarm-rei {
             type empty;
             description
               "Path remote error indicator alarm";
           }
           leaf sonet-alarm-uneq {
             type empty;
             description
               "Unequipped alarm";
           }
           leaf sonet-alarm-pmis {
             type empty;
             description
               "Path payload level mismatch alarm";
           }
           leaf sonet-alarm-loc {
             type empty;
             description
               "Loss of cell delineation alarm";
           }
           leaf sonet-alarm-vais {
             type empty;
             description
               "VT AIS alarm";
           }
           leaf sonet-alarm-vlop {
             type empty;
             description
               "VT loss of pointer alarm";
           }
           leaf sonet-alarm-vrdi {
             type empty;
             description
               "VT remote defect indicator alarm";
           }
           leaf sonet-alarm-vuneq {
             type empty;
             description
               "VT unequipped alarm";
           }
           leaf sonet-alarm-vmis {
             type empty;
             description
               "VT label mismatch alarm";
           }
           leaf sonet-alarm-vloc {
             type empty;
             description
               "VT loss of cell delineation alarm";
           }
           leaf sdh-alarm-lol {
             type empty;
             description
               "Loss of light alarm";
           }
           leaf sdh-alarm-pll {
             type empty;
             description
               "PLL lock alarm";
           }
           leaf sdh-alarm-lof {
             type empty;
             description
               "Loss of frame alarm";
           }
           leaf sdh-alarm-los {
             type empty;
             description
               "Loss of signal alarm";
           }
           leaf sdh-alarm-oof {
             type empty;
             description
               "Out of frame alarm";
           }
           leaf sdh-alarm-msais {
             type empty;
             description
               "Multiplex section AIS alarm";
           }
           leaf sdh-alarm-hpais {
             type empty;
             description
               "High order path AIS alarm";
           }
           leaf sdh-alarm-lop {
             type empty;
             description
               "Loss of pointer alarm";
           }
           leaf sdh-alarm-berr-sd {
             type empty;
             description
               "Bit error rate alarm, defect";
           }
           leaf sdh-alarm-berr-sf {
             type empty;
             description
               "Bit error rate alarm, fault";
           }
           leaf sdh-alarm-msferf {
             type empty;
             description
               "Multiplex section far-end remote failure alarm";
           }
           leaf sdh-alarm-hpferf {
             type empty;
             description
               "High order path far-end remote failure alarm";
           }
           leaf sdh-alarm-hpfebe {
             type empty;
             description
               "High order path far-end block error alarm";
           }
           leaf sdh-alarm-hpuneq {
             type empty;
             description
               "High order path unequipped alarm";
           }
           leaf sdh-alarm-hpplm {
             type empty;
             description
               "High order path payload level mismatch alarm";
           }
           leaf sdh-alarm-loc {
             type empty;
             description
               "Loss of cell delineation alarm";
           }
           leaf sdh-alarm-tuais {
             type empty;
             description
               "TU AIS alarm";
           }
           leaf sdh-alarm-tulop {
             type empty;
             description
               "TU loss of pointer alarm";
           }
           leaf sdh-alarm-turdi {
             type empty;
             description
               "TU remote defect indicator alarm";
           }
           leaf sdh-alarm-tuuneq {
             type empty;
             description
               "TU unequipped alarm";
           }
           leaf sdh-alarm-tumis {
             type empty;
             description
               "TU label mismatch error";
           }
           leaf sdh-alarm-tuloc {
             type empty;
             description
               "TU loss of cell delineation alarm";
           }
           leaf ds3-alarm-pll {
             type empty;
             description
               "PLL lock alarm";
           }
           leaf ds3-alarm-ais {
             type empty;
             description
               "AIS alarm";
           }
           leaf ds3-alarm-lof {
             type empty;
             description
               "Loss of frame alarm";
           }
           leaf ds3-alarm-los {
             type empty;
             description
               "Loss of signal alarm";
           }
           leaf ds3-alarm-lcv {
             type empty;
             description
               "Line code violation alarm";
           }
           leaf ds3-alarm-exz {
             type empty;
             description
               "Excessive zeros alarm";
           }
           leaf ds3-alarm-ferf {
             type empty;
             description
               "Far-end receive failure alarm";
           }
           leaf ds3-alarm-ylw {
             type empty;
             description
               "Yellow alarm";
           }
           leaf ds3-alarm-idle {
             type empty;
             description
               "Idle alarm";
           }
           leaf ds1-alarm-ais {
             type empty;
             description
               "AIS alarm";
           }
           leaf ds1-alarm-lof {
             type empty;
             description
               "Loss of frame alarm";
           }
           leaf ds1-alarm-los {
             type empty;
             description
               "Loss of signal alarm";
           }
           leaf ds1-alarm-ylw {
             type empty;
             description
               "Yellow alarm";
           }
           leaf ds1-alarm-crc-major {
             type empty;
             description
               "CRC errors crossed major threshold";
           }
           leaf ds1-alarm-crc-minor {
             type empty;
             description
               "CRC errors crossed minor threshold";
           }
           leaf dsl-alarm-lof {
             type empty;
             description
               "Loss of frame alarm";
           }
           leaf dsl-alarm-los {
             type empty;
             description
               "Loss of signal alarm";
           }
           leaf dsl-alarm-lom {
             type empty;
             description
               "Loss of multiframe alarm";
           }
           leaf dsl-alarm-locdi {
             type empty;
             description
               "Loss of cell delineation alarm for interleaved channel";
           }
           leaf dsl-alarm-locdni {
             type empty;
             description
               "Loss of cell delineation alarm for non-interleaved channel";
           }
           leaf dsl-alarm-lop {
             type empty;
             description
               "Loss of power alarm";
           }
           leaf dsl-alarm-far-lof {
             type empty;
             description
               "Far-end loss-of-frame alarm";
           }
           leaf dsl-alarm-far-los {
             type empty;
             description
               "Far-end loss-of-signal alarm";
           }
           leaf dsl-alarm-far-locdi {
             type empty;
             description
               "Far-end loss-of-cell-delineation alarm for interleaved 
               channel";
           }
           leaf dsl-alarm-far-locdni {
             type empty;
             description
               "Far-end loss-of-cell-delineation alarm for non-interleaved 
               channel";
           }
           leaf fibrechannel-alarm-link-down {
             type empty;
             description
               "Link alive failure";
           }
           leaf ethernet-alarm-link-down {
             type empty;
             description
               "Link alive failure";
           }
           leaf ethernet-alarm-an-not-supported {
             type empty;
             description
               "AN not supported";
           }
           leaf ethernet-alarm-link-local-fault {
             type empty;
             description
               "Link local fault";
           }
           leaf ethernet-alarm-link-remote-fault {
             type empty;
             description
               "Link remote fault";
           }
           leaf ethernet-alarm-link-local-degrade {
             type empty;
             description
               "Link local degrade";
           }
           leaf ethernet-alarm-link-remote-degrade {
             type empty;
             description
               "Link remote degrade";
           }
           leaf ethernet-alarm-lcdp {
             type empty;
             description
               "Loss of code-group delineation";
           }
           leaf isdn-alarm-los {
             type empty;
             description
               "Loss of signal alarm";
           }
           leaf isdn-alarm-lof {
             type empty;
             description
               "Loss of frame alarm";
           }
           leaf shdsl-alarm-losd {
             type empty;
             description
               "Loss of signal alarm";
           }
           leaf shdsl-alarm-losw {
             type empty;
             description
               "Loss of sync word alarm";
           }
           leaf shdsl-alarm-line1-losd {
             type empty;
             description
               "Loss of signal (line 1) alarm";
           }
           leaf shdsl-alarm-line1-losw {
             type empty;
             description
               "Loss of sync word (line 1) alarm";
           }
           leaf shdsl-alarm-line2-losd {
             type empty;
             description
               "Loss of signal (line 2) alarm";
           }
           leaf shdsl-alarm-line2-losw {
             type empty;
             description
               "Loss of sync word (line 2) alarm";
           }
           leaf shdsl-efm-alarm-losd {
             type empty;
             description
               "Loss of signal alarm";
           }
           leaf shdsl-efm-alarm-losw {
             type empty;
             description
               "Loss of sync word alarm";
           }
           leaf otn-alarm-los {
             type empty;
             description
               "Loss of signal alarm";
           }
           leaf otn-alarm-lof {
             type empty;
             description
               "Loss of frame alarm";
           }
           leaf otn-alarm-lom {
             type empty;
             description
               "Loss of multiframe alarm";
           }
           leaf otn-alarm-wavelength-lock {
             type empty;
             description
               "Loss of Wavelength Lock alarm";
           }
           leaf otn-alarm-otu-ais {
             type empty;
             description
               "OTU Alarm Indication Signal alarm";
           }
           leaf otn-alarm-otu-bdi {
             type empty;
             description
               "OTU Background Block Error alarm";
           }
           leaf otn-alarm-otu-ttim {
             type empty;
             description
               "OTU Trail Trace Identifier Mismatch alarm";
           }
           leaf otn-alarm-otu-iae {
             type empty;
             description
               "OTU Incoming Alignment alarm";
           }
           leaf otn-alarm-otu-sd {
             type empty;
             description
               "OTU Signal Degrade alarm";
           }
           leaf otn-alarm-otu-sf {
             type empty;
             description
               "OTU Signal Fail alarm";
           }
           leaf otn-alarm-otu-biae {
             type empty;
             description
               "OTU Backward Incoming Alignment alarm";
           }
           leaf otn-alarm-otu-tsf {
             type empty;
             description
               "OTU Trail Signal Fail alarm";
           }
           leaf otn-alarm-otu-ssf {
             type empty;
             description
               "OTU Server Signal Fail alarm";
           }
           leaf otn-alarm-otu-fec-excessive {
             type empty;
             description
               "OTU FEC Excessive alarm";
           }
           leaf otn-alarm-otu-fec-degraded {
             type empty;
             description
               "OTU FEC Degraded alarm";
           }
           leaf otn-alarm-otu-fe-fec-degraded {
             type empty;
             description
               "OTU FE FEC Degraded/Excessive alarm";
           }
           leaf otn-alarm-otu-threshold-bbe {
             type empty;
             description
               "OTU Background Block Error threshold alarm";
           }
           leaf otn-alarm-otu-threshold-es {
             type empty;
             description
               "OTU Errored Seconds threshold alarm";
           }
           leaf otn-alarm-otu-threshold-ses {
             type empty;
             description
               "OTU Severely Errored Seconds threshold alarm";
           }
           leaf otn-alarm-otu-threshold-uas {
             type empty;
             description
               "OTU Unavailable Seconds threshold alarm";
           }
           leaf otn-alarm-odu-ais {
             type empty;
             description
               "ODU  Alarm Indiaction Signal alarm";
           }
           leaf otn-alarm-odu-oci {
             type empty;
             description
               "ODU Open Connection Indication alarm";
           }
           leaf otn-alarm-odu-lck {
             type empty;
             description
               "ODU Locked alarm";
           }
           leaf otn-alarm-odu-bdi {
             type empty;
             description
               "ODU Backward Defect Indication alarm";
           }
           leaf otn-alarm-odu-ttim {
             type empty;
             description
               "ODU Trail Trace Identifier Mismatch alarm";
           }
           leaf otn-alarm-odu-sd {
             type empty;
             description
               "ODU Signal Degrade alarm";
           }
           leaf otn-alarm-odu-sf {
             type empty;
             description
               "ODU Signal Fail alarm";
           }
           leaf otn-alarm-odu-iae {
             type empty;
             description
               "ODU Incoming Alignment alarm";
           }
           leaf otn-alarm-odu-ltc {
             type empty;
             description
               "ODU Loss of Tandem Connection alarm";
           }
           leaf otn-alarm-odu-csf {
             type empty;
             description
               "ODU Client Signal Fail alarm";
           }
           leaf otn-alarm-odu-tsf {
             type empty;
             description
               "ODU Trail Signal Fail alarm";
           }
           leaf otn-alarm-odu-ssf {
             type empty;
             description
               "ODU Server Signal Fail alarm";
           }
           leaf otn-alarm-odu-rx-aps-change {
             type empty;
             description
               "ODU Rx Aps Change alarm";
           }
           leaf otn-alarm-odu-threshold-bbe {
             type empty;
             description
               "ODU Background Block Error threshold alarm";
           }
           leaf otn-alarm-odu-threshold-es {
             type empty;
             description
               "ODU Errored Seconds threshold alarm";
           }
           leaf otn-alarm-odu-threshold-ses {
             type empty;
             description
               "ODU Severely Errored Seconds threshold alarm";
           }
           leaf otn-alarm-odu-threshold-uas {
             type empty;
             description
               "ODU Unavailable Seconds threshold alarm";
           }
           leaf otn-alarm-opu-pmi {
             type empty;
             description
               "OPU Payload Mismatch alarm";
           }
           leaf otn-alarm-pre-fec-sd {
             type empty;
             description
               "Pre-FEC SD alarm";
           }
           leaf otn-alarm-fe-pre-fec-sd {
             type empty;
             description
               "Far end pre-FEC SD alarm";
           }
           leaf optics-alarms-mod-fault {
             type empty;
             description
               "Module Fault alarm";
           }
           leaf optics-alarms-lol {
             type empty;
             description
               "Loss of Lock alarm";
           }
           leaf optics-alarms-los {
             type empty;
             description
               "Loss of Signal alarms";
           }
           leaf optics-alarms-lof {
             type empty;
             description
               "Loss of frame alarm";
           }
           leaf optics-alarms-lom {
             type empty;
             description
               "Loss of multi-frame alarm";
           }
           leaf optics-alarms-otu-bdi {
             type empty;
             description
               "Backward defect indiacation alarm";
           }
           leaf optics-alarms-rmsf {
             type empty;
             description
               "Rx Modem sysnc fault alarm";
           }
           leaf optics-alarms-rmlol {
             type empty;
             description
               "Rx Modem loss of lock alarm";
           }
           leaf optics-alarms-rloa {
             type empty;
             description
               "Rx loss of alignment alarm";
           }
           leaf optics-alarms-mbclf {
             type empty;
             description
               "Modulator Bias control loop fail alarm";
           }
           leaf optics-alarms-itlaf {
             type empty;
             description
               "ITLA Fault alarm";
           }
           leaf optics-alarms-daccf {
             type empty;
             description
               "DAC Calibration Fault alarm";
           }
           leaf optics-alarms-adccf {
             type empty;
             description
               "ADC Calibration Fault alarm";
           }
           leaf optics-alarms-fec-degrade {
             type empty;
             description
               "FEC Degrade alarm";
           }
           leaf optics-alarms-fec-excessive {
             type empty;
             description
               "FEC Excessive alarm";
           }
           leaf optics-alarms-fe-fec-degrade {
             type empty;
             description
               "Far-end FEC Degrade alarm";
           }
           leaf optics-alarms-fe-fec-excessive {
             type empty;
             description
               "Far-end FEC Excessive alarm";
           }
           leaf ima-alarm-startup-fe {
             type empty;
             description
               "IMA group startup far-end alarm";
           }
           leaf ima-alarm-config-abort {
             type empty;
             description
               "IMA group config abort alarm";
           }
           leaf ima-alarm-config-abort-fe {
             type empty;
             description
               "IMA group config abort far-end alarm";
           }
           leaf ima-alarm-insufficient-links {
             type empty;
             description
               "IMA group insufficient links alarm";
           }
           leaf ima-alarm-insufficient-links-fe {
             type empty;
             description
               "IMA group insufficient links far-end alarm";
           }
           leaf ima-alarm-blocked {
             type empty;
             description
               "IMA group blocked alarm";
           }
           leaf ima-alarm-blocked-fe {
             type empty;
             description
               "IMA group blocked far-end alarm";
           }
           leaf ima-alarm-timing-mismatch {
             type empty;
             description
               "IMA group timing mismatch alarm";
           }
           leaf ima-alarm-version-mismatch {
             type empty;
             description
               "IMA group version mismatch alarm";
           }
           leaf ima-alarm-lif {
             type empty;
             description
               "IMA link loss of IMA frame alarm";
           }
           leaf ima-alarm-lods {
             type empty;
             description
               "IMA link out of delay synchronization alarm";
           }
           leaf ima-alarm-rdi {
             type empty;
             description
               "IMA link remote defect indicator alarm";
           }
           leaf ima-alarm-tx-misconnected {
             type empty;
             description
               "IMA link tx misconnected alarm";
           }
           leaf ima-alarm-rx-misconnected {
             type empty;
             description
               "IMA link rx misconnected alarm";
           }
           leaf ima-alarm-fault {
             type empty;
             description
               "IMA link fault alarm";
           }
           leaf ima-alarm-tx-unusable-fe {
             type empty;
             description
               "IMA link Tx unusable far-end alarm";
           }
           leaf ima-alarm-rx-unusable-fe {
             type empty;
             description
               "IMA link Tx unusable far-end alarm";
           }
           leaf generic-value {
             type int32;
             description
               "Hexadecimal value of unknown flag bits";
           }
         }
       }
       container active-alarms-optics {
         leaf type-optics {
           type string;
           description
             "Optics type for associated interface alarms";
         }
         container interface-alarms {
           description
             "Container tag for interface alarms";
           leaf alarm-not-present {
             type empty;
             description
               "No alarm indicated";
           }
           leaf sonet-alarm-lol {
             type empty;
             description
               "Loss of light alarm";
           }
           leaf sonet-alarm-pll {
             type empty;
             description
               "PLL lock alarm";
           }
           leaf sonet-alarm-lof {
             type empty;
             description
               "Loss of frame alarm";
           }
           leaf sonet-alarm-los {
             type empty;
             description
               "Loss of signal alarm";
           }
           leaf sonet-alarm-sef {
             type empty;
             description
               "Severely errored frame alarm";
           }
           leaf sonet-alarm-lais {
             type empty;
             description
               "Line AIS alarm";
           }
           leaf sonet-alarm-pais {
             type empty;
             description
               "Path AIS alarm";
           }
           leaf sonet-alarm-lop {
             type empty;
             description
               "Loss of pointer alarm";
           }
           leaf sonet-alarm-berr-sd {
             type empty;
             description
               "Bit error rate alarm, defect";
           }
           leaf sonet-alarm-berr-sf {
             type empty;
             description
               "Bit error rate alarm, fault";
           }
           leaf sonet-alarm-lrdi {
             type empty;
             description
               "Line remote defect indicator alarm";
           }
           leaf sonet-alarm-prdi {
             type empty;
             description
               "Path remote defect indicator alarm";
           }
           leaf sonet-alarm-rei {
             type empty;
             description
               "Path remote error indicator alarm";
           }
           leaf sonet-alarm-uneq {
             type empty;
             description
               "Unequipped alarm";
           }
           leaf sonet-alarm-pmis {
             type empty;
             description
               "Path payload level mismatch alarm";
           }
           leaf sonet-alarm-loc {
             type empty;
             description
               "Loss of cell delineation alarm";
           }
           leaf sonet-alarm-vais {
             type empty;
             description
               "VT AIS alarm";
           }
           leaf sonet-alarm-vlop {
             type empty;
             description
               "VT loss of pointer alarm";
           }
           leaf sonet-alarm-vrdi {
             type empty;
             description
               "VT remote defect indicator alarm";
           }
           leaf sonet-alarm-vuneq {
             type empty;
             description
               "VT unequipped alarm";
           }
           leaf sonet-alarm-vmis {
             type empty;
             description
               "VT label mismatch alarm";
           }
           leaf sonet-alarm-vloc {
             type empty;
             description
               "VT loss of cell delineation alarm";
           }
           leaf sdh-alarm-lol {
             type empty;
             description
               "Loss of light alarm";
           }
           leaf sdh-alarm-pll {
             type empty;
             description
               "PLL lock alarm";
           }
           leaf sdh-alarm-lof {
             type empty;
             description
               "Loss of frame alarm";
           }
           leaf sdh-alarm-los {
             type empty;
             description
               "Loss of signal alarm";
           }
           leaf sdh-alarm-oof {
             type empty;
             description
               "Out of frame alarm";
           }
           leaf sdh-alarm-msais {
             type empty;
             description
               "Multiplex section AIS alarm";
           }
           leaf sdh-alarm-hpais {
             type empty;
             description
               "High order path AIS alarm";
           }
           leaf sdh-alarm-lop {
             type empty;
             description
               "Loss of pointer alarm";
           }
           leaf sdh-alarm-berr-sd {
             type empty;
             description
               "Bit error rate alarm, defect";
           }
           leaf sdh-alarm-berr-sf {
             type empty;
             description
               "Bit error rate alarm, fault";
           }
           leaf sdh-alarm-msferf {
             type empty;
             description
               "Multiplex section far-end remote failure alarm";
           }
           leaf sdh-alarm-hpferf {
             type empty;
             description
               "High order path far-end remote failure alarm";
           }
           leaf sdh-alarm-hpfebe {
             type empty;
             description
               "High order path far-end block error alarm";
           }
           leaf sdh-alarm-hpuneq {
             type empty;
             description
               "High order path unequipped alarm";
           }
           leaf sdh-alarm-hpplm {
             type empty;
             description
               "High order path payload level mismatch alarm";
           }
           leaf sdh-alarm-loc {
             type empty;
             description
               "Loss of cell delineation alarm";
           }
           leaf sdh-alarm-tuais {
             type empty;
             description
               "TU AIS alarm";
           }
           leaf sdh-alarm-tulop {
             type empty;
             description
               "TU loss of pointer alarm";
           }
           leaf sdh-alarm-turdi {
             type empty;
             description
               "TU remote defect indicator alarm";
           }
           leaf sdh-alarm-tuuneq {
             type empty;
             description
               "TU unequipped alarm";
           }
           leaf sdh-alarm-tumis {
             type empty;
             description
               "TU label mismatch error";
           }
           leaf sdh-alarm-tuloc {
             type empty;
             description
               "TU loss of cell delineation alarm";
           }
           leaf ds3-alarm-pll {
             type empty;
             description
               "PLL lock alarm";
           }
           leaf ds3-alarm-ais {
             type empty;
             description
               "AIS alarm";
           }
           leaf ds3-alarm-lof {
             type empty;
             description
               "Loss of frame alarm";
           }
           leaf ds3-alarm-los {
             type empty;
             description
               "Loss of signal alarm";
           }
           leaf ds3-alarm-lcv {
             type empty;
             description
               "Line code violation alarm";
           }
           leaf ds3-alarm-exz {
             type empty;
             description
               "Excessive zeros alarm";
           }
           leaf ds3-alarm-ferf {
             type empty;
             description
               "Far-end receive failure alarm";
           }
           leaf ds3-alarm-ylw {
             type empty;
             description
               "Yellow alarm";
           }
           leaf ds3-alarm-idle {
             type empty;
             description
               "Idle alarm";
           }
           leaf ds1-alarm-ais {
             type empty;
             description
               "AIS alarm";
           }
           leaf ds1-alarm-lof {
             type empty;
             description
               "Loss of frame alarm";
           }
           leaf ds1-alarm-los {
             type empty;
             description
               "Loss of signal alarm";
           }
           leaf ds1-alarm-ylw {
             type empty;
             description
               "Yellow alarm";
           }
           leaf ds1-alarm-crc-major {
             type empty;
             description
               "CRC errors crossed major threshold";
           }
           leaf ds1-alarm-crc-minor {
             type empty;
             description
               "CRC errors crossed minor threshold";
           }
           leaf dsl-alarm-lof {
             type empty;
             description
               "Loss of frame alarm";
           }
           leaf dsl-alarm-los {
             type empty;
             description
               "Loss of signal alarm";
           }
           leaf dsl-alarm-lom {
             type empty;
             description
               "Loss of multiframe alarm";
           }
           leaf dsl-alarm-locdi {
             type empty;
             description
               "Loss of cell delineation alarm for interleaved channel";
           }
           leaf dsl-alarm-locdni {
             type empty;
             description
               "Loss of cell delineation alarm for non-interleaved channel";
           }
           leaf dsl-alarm-lop {
             type empty;
             description
               "Loss of power alarm";
           }
           leaf dsl-alarm-far-lof {
             type empty;
             description
               "Far-end loss-of-frame alarm";
           }
           leaf dsl-alarm-far-los {
             type empty;
             description
               "Far-end loss-of-signal alarm";
           }
           leaf dsl-alarm-far-locdi {
             type empty;
             description
               "Far-end loss-of-cell-delineation alarm for interleaved 
               channel";
           }
           leaf dsl-alarm-far-locdni {
             type empty;
             description
               "Far-end loss-of-cell-delineation alarm for non-interleaved 
               channel";
           }
           leaf fibrechannel-alarm-link-down {
             type empty;
             description
               "Link alive failure";
           }
           leaf ethernet-alarm-link-down {
             type empty;
             description
               "Link alive failure";
           }
           leaf ethernet-alarm-an-not-supported {
             type empty;
             description
               "AN not supported";
           }
           leaf ethernet-alarm-link-local-fault {
             type empty;
             description
               "Link local fault";
           }
           leaf ethernet-alarm-link-remote-fault {
             type empty;
             description
               "Link remote fault";
           }
           leaf ethernet-alarm-link-local-degrade {
             type empty;
             description
               "Link local degrade";
           }
           leaf ethernet-alarm-link-remote-degrade {
             type empty;
             description
               "Link remote degrade";
           }
           leaf ethernet-alarm-lcdp {
             type empty;
             description
               "Loss of code-group delineation";
           }
           leaf isdn-alarm-los {
             type empty;
             description
               "Loss of signal alarm";
           }
           leaf isdn-alarm-lof {
             type empty;
             description
               "Loss of frame alarm";
           }
           leaf shdsl-alarm-losd {
             type empty;
             description
               "Loss of signal alarm";
           }
           leaf shdsl-alarm-losw {
             type empty;
             description
               "Loss of sync word alarm";
           }
           leaf shdsl-alarm-line1-losd {
             type empty;
             description
               "Loss of signal (line 1) alarm";
           }
           leaf shdsl-alarm-line1-losw {
             type empty;
             description
               "Loss of sync word (line 1) alarm";
           }
           leaf shdsl-alarm-line2-losd {
             type empty;
             description
               "Loss of signal (line 2) alarm";
           }
           leaf shdsl-alarm-line2-losw {
             type empty;
             description
               "Loss of sync word (line 2) alarm";
           }
           leaf shdsl-efm-alarm-losd {
             type empty;
             description
               "Loss of signal alarm";
           }
           leaf shdsl-efm-alarm-losw {
             type empty;
             description
               "Loss of sync word alarm";
           }
           leaf otn-alarm-los {
             type empty;
             description
               "Loss of signal alarm";
           }
           leaf otn-alarm-lof {
             type empty;
             description
               "Loss of frame alarm";
           }
           leaf otn-alarm-lom {
             type empty;
             description
               "Loss of multiframe alarm";
           }
           leaf otn-alarm-wavelength-lock {
             type empty;
             description
               "Loss of Wavelength Lock alarm";
           }
           leaf otn-alarm-otu-ais {
             type empty;
             description
               "OTU Alarm Indication Signal alarm";
           }
           leaf otn-alarm-otu-bdi {
             type empty;
             description
               "OTU Background Block Error alarm";
           }
           leaf otn-alarm-otu-ttim {
             type empty;
             description
               "OTU Trail Trace Identifier Mismatch alarm";
           }
           leaf otn-alarm-otu-iae {
             type empty;
             description
               "OTU Incoming Alignment alarm";
           }
           leaf otn-alarm-otu-sd {
             type empty;
             description
               "OTU Signal Degrade alarm";
           }
           leaf otn-alarm-otu-sf {
             type empty;
             description
               "OTU Signal Fail alarm";
           }
           leaf otn-alarm-otu-biae {
             type empty;
             description
               "OTU Backward Incoming Alignment alarm";
           }
           leaf otn-alarm-otu-tsf {
             type empty;
             description
               "OTU Trail Signal Fail alarm";
           }
           leaf otn-alarm-otu-ssf {
             type empty;
             description
               "OTU Server Signal Fail alarm";
           }
           leaf otn-alarm-otu-fec-excessive {
             type empty;
             description
               "OTU FEC Excessive alarm";
           }
           leaf otn-alarm-otu-fec-degraded {
             type empty;
             description
               "OTU FEC Degraded alarm";
           }
           leaf otn-alarm-otu-fe-fec-degraded {
             type empty;
             description
               "OTU FE FEC Degraded/Excessive alarm";
           }
           leaf otn-alarm-otu-threshold-bbe {
             type empty;
             description
               "OTU Background Block Error threshold alarm";
           }
           leaf otn-alarm-otu-threshold-es {
             type empty;
             description
               "OTU Errored Seconds threshold alarm";
           }
           leaf otn-alarm-otu-threshold-ses {
             type empty;
             description
               "OTU Severely Errored Seconds threshold alarm";
           }
           leaf otn-alarm-otu-threshold-uas {
             type empty;
             description
               "OTU Unavailable Seconds threshold alarm";
           }
           leaf otn-alarm-odu-ais {
             type empty;
             description
               "ODU  Alarm Indiaction Signal alarm";
           }
           leaf otn-alarm-odu-oci {
             type empty;
             description
               "ODU Open Connection Indication alarm";
           }
           leaf otn-alarm-odu-lck {
             type empty;
             description
               "ODU Locked alarm";
           }
           leaf otn-alarm-odu-bdi {
             type empty;
             description
               "ODU Backward Defect Indication alarm";
           }
           leaf otn-alarm-odu-ttim {
             type empty;
             description
               "ODU Trail Trace Identifier Mismatch alarm";
           }
           leaf otn-alarm-odu-sd {
             type empty;
             description
               "ODU Signal Degrade alarm";
           }
           leaf otn-alarm-odu-sf {
             type empty;
             description
               "ODU Signal Fail alarm";
           }
           leaf otn-alarm-odu-iae {
             type empty;
             description
               "ODU Incoming Alignment alarm";
           }
           leaf otn-alarm-odu-ltc {
             type empty;
             description
               "ODU Loss of Tandem Connection alarm";
           }
           leaf otn-alarm-odu-csf {
             type empty;
             description
               "ODU Client Signal Fail alarm";
           }
           leaf otn-alarm-odu-tsf {
             type empty;
             description
               "ODU Trail Signal Fail alarm";
           }
           leaf otn-alarm-odu-ssf {
             type empty;
             description
               "ODU Server Signal Fail alarm";
           }
           leaf otn-alarm-odu-rx-aps-change {
             type empty;
             description
               "ODU Rx Aps Change alarm";
           }
           leaf otn-alarm-odu-threshold-bbe {
             type empty;
             description
               "ODU Background Block Error threshold alarm";
           }
           leaf otn-alarm-odu-threshold-es {
             type empty;
             description
               "ODU Errored Seconds threshold alarm";
           }
           leaf otn-alarm-odu-threshold-ses {
             type empty;
             description
               "ODU Severely Errored Seconds threshold alarm";
           }
           leaf otn-alarm-odu-threshold-uas {
             type empty;
             description
               "ODU Unavailable Seconds threshold alarm";
           }
           leaf otn-alarm-opu-pmi {
             type empty;
             description
               "OPU Payload Mismatch alarm";
           }
           leaf otn-alarm-pre-fec-sd {
             type empty;
             description
               "Pre-FEC SD alarm";
           }
           leaf otn-alarm-fe-pre-fec-sd {
             type empty;
             description
               "Far end pre-FEC SD alarm";
           }
           leaf optics-alarms-mod-fault {
             type empty;
             description
               "Module Fault alarm";
           }
           leaf optics-alarms-lol {
             type empty;
             description
               "Loss of Lock alarm";
           }
           leaf optics-alarms-los {
             type empty;
             description
               "Loss of Signal alarms";
           }
           leaf optics-alarms-lof {
             type empty;
             description
               "Loss of frame alarm";
           }
           leaf optics-alarms-lom {
             type empty;
             description
               "Loss of multi-frame alarm";
           }
           leaf optics-alarms-otu-bdi {
             type empty;
             description
               "Backward defect indiacation alarm";
           }
           leaf optics-alarms-rmsf {
             type empty;
             description
               "Rx Modem sysnc fault alarm";
           }
           leaf optics-alarms-rmlol {
             type empty;
             description
               "Rx Modem loss of lock alarm";
           }
           leaf optics-alarms-rloa {
             type empty;
             description
               "Rx loss of alignment alarm";
           }
           leaf optics-alarms-mbclf {
             type empty;
             description
               "Modulator Bias control loop fail alarm";
           }
           leaf optics-alarms-itlaf {
             type empty;
             description
               "ITLA Fault alarm";
           }
           leaf optics-alarms-daccf {
             type empty;
             description
               "DAC Calibration Fault alarm";
           }
           leaf optics-alarms-adccf {
             type empty;
             description
               "ADC Calibration Fault alarm";
           }
           leaf optics-alarms-fec-degrade {
             type empty;
             description
               "FEC Degrade alarm";
           }
           leaf optics-alarms-fec-excessive {
             type empty;
             description
               "FEC Excessive alarm";
           }
           leaf optics-alarms-fe-fec-degrade {
             type empty;
             description
               "Far-end FEC Degrade alarm";
           }
           leaf optics-alarms-fe-fec-excessive {
             type empty;
             description
               "Far-end FEC Excessive alarm";
           }
           leaf ima-alarm-startup-fe {
             type empty;
             description
               "IMA group startup far-end alarm";
           }
           leaf ima-alarm-config-abort {
             type empty;
             description
               "IMA group config abort alarm";
           }
           leaf ima-alarm-config-abort-fe {
             type empty;
             description
               "IMA group config abort far-end alarm";
           }
           leaf ima-alarm-insufficient-links {
             type empty;
             description
               "IMA group insufficient links alarm";
           }
           leaf ima-alarm-insufficient-links-fe {
             type empty;
             description
               "IMA group insufficient links far-end alarm";
           }
           leaf ima-alarm-blocked {
             type empty;
             description
               "IMA group blocked alarm";
           }
           leaf ima-alarm-blocked-fe {
             type empty;
             description
               "IMA group blocked far-end alarm";
           }
           leaf ima-alarm-timing-mismatch {
             type empty;
             description
               "IMA group timing mismatch alarm";
           }
           leaf ima-alarm-version-mismatch {
             type empty;
             description
               "IMA group version mismatch alarm";
           }
           leaf ima-alarm-lif {
             type empty;
             description
               "IMA link loss of IMA frame alarm";
           }
           leaf ima-alarm-lods {
             type empty;
             description
               "IMA link out of delay synchronization alarm";
           }
           leaf ima-alarm-rdi {
             type empty;
             description
               "IMA link remote defect indicator alarm";
           }
           leaf ima-alarm-tx-misconnected {
             type empty;
             description
               "IMA link tx misconnected alarm";
           }
           leaf ima-alarm-rx-misconnected {
             type empty;
             description
               "IMA link rx misconnected alarm";
           }
           leaf ima-alarm-fault {
             type empty;
             description
               "IMA link fault alarm";
           }
           leaf ima-alarm-tx-unusable-fe {
             type empty;
             description
               "IMA link Tx unusable far-end alarm";
           }
           leaf ima-alarm-rx-unusable-fe {
             type empty;
             description
               "IMA link Tx unusable far-end alarm";
           }
           leaf generic-value {
             type int32;
             description
               "Hexadecimal value of unknown flag bits";
           }
         }
       }
       container active-defects-optics {
         leaf type-optics {
           type string;
           description
             "Optics type for associated interface alarms";
         }
         container interface-alarms {
           description
             "Container tag for interface alarms";
           leaf alarm-not-present {
             type empty;
             description
               "No alarm indicated";
           }
           leaf sonet-alarm-lol {
             type empty;
             description
               "Loss of light alarm";
           }
           leaf sonet-alarm-pll {
             type empty;
             description
               "PLL lock alarm";
           }
           leaf sonet-alarm-lof {
             type empty;
             description
               "Loss of frame alarm";
           }
           leaf sonet-alarm-los {
             type empty;
             description
               "Loss of signal alarm";
           }
           leaf sonet-alarm-sef {
             type empty;
             description
               "Severely errored frame alarm";
           }
           leaf sonet-alarm-lais {
             type empty;
             description
               "Line AIS alarm";
           }
           leaf sonet-alarm-pais {
             type empty;
             description
               "Path AIS alarm";
           }
           leaf sonet-alarm-lop {
             type empty;
             description
               "Loss of pointer alarm";
           }
           leaf sonet-alarm-berr-sd {
             type empty;
             description
               "Bit error rate alarm, defect";
           }
           leaf sonet-alarm-berr-sf {
             type empty;
             description
               "Bit error rate alarm, fault";
           }
           leaf sonet-alarm-lrdi {
             type empty;
             description
               "Line remote defect indicator alarm";
           }
           leaf sonet-alarm-prdi {
             type empty;
             description
               "Path remote defect indicator alarm";
           }
           leaf sonet-alarm-rei {
             type empty;
             description
               "Path remote error indicator alarm";
           }
           leaf sonet-alarm-uneq {
             type empty;
             description
               "Unequipped alarm";
           }
           leaf sonet-alarm-pmis {
             type empty;
             description
               "Path payload level mismatch alarm";
           }
           leaf sonet-alarm-loc {
             type empty;
             description
               "Loss of cell delineation alarm";
           }
           leaf sonet-alarm-vais {
             type empty;
             description
               "VT AIS alarm";
           }
           leaf sonet-alarm-vlop {
             type empty;
             description
               "VT loss of pointer alarm";
           }
           leaf sonet-alarm-vrdi {
             type empty;
             description
               "VT remote defect indicator alarm";
           }
           leaf sonet-alarm-vuneq {
             type empty;
             description
               "VT unequipped alarm";
           }
           leaf sonet-alarm-vmis {
             type empty;
             description
               "VT label mismatch alarm";
           }
           leaf sonet-alarm-vloc {
             type empty;
             description
               "VT loss of cell delineation alarm";
           }
           leaf sdh-alarm-lol {
             type empty;
             description
               "Loss of light alarm";
           }
           leaf sdh-alarm-pll {
             type empty;
             description
               "PLL lock alarm";
           }
           leaf sdh-alarm-lof {
             type empty;
             description
               "Loss of frame alarm";
           }
           leaf sdh-alarm-los {
             type empty;
             description
               "Loss of signal alarm";
           }
           leaf sdh-alarm-oof {
             type empty;
             description
               "Out of frame alarm";
           }
           leaf sdh-alarm-msais {
             type empty;
             description
               "Multiplex section AIS alarm";
           }
           leaf sdh-alarm-hpais {
             type empty;
             description
               "High order path AIS alarm";
           }
           leaf sdh-alarm-lop {
             type empty;
             description
               "Loss of pointer alarm";
           }
           leaf sdh-alarm-berr-sd {
             type empty;
             description
               "Bit error rate alarm, defect";
           }
           leaf sdh-alarm-berr-sf {
             type empty;
             description
               "Bit error rate alarm, fault";
           }
           leaf sdh-alarm-msferf {
             type empty;
             description
               "Multiplex section far-end remote failure alarm";
           }
           leaf sdh-alarm-hpferf {
             type empty;
             description
               "High order path far-end remote failure alarm";
           }
           leaf sdh-alarm-hpfebe {
             type empty;
             description
               "High order path far-end block error alarm";
           }
           leaf sdh-alarm-hpuneq {
             type empty;
             description
               "High order path unequipped alarm";
           }
           leaf sdh-alarm-hpplm {
             type empty;
             description
               "High order path payload level mismatch alarm";
           }
           leaf sdh-alarm-loc {
             type empty;
             description
               "Loss of cell delineation alarm";
           }
           leaf sdh-alarm-tuais {
             type empty;
             description
               "TU AIS alarm";
           }
           leaf sdh-alarm-tulop {
             type empty;
             description
               "TU loss of pointer alarm";
           }
           leaf sdh-alarm-turdi {
             type empty;
             description
               "TU remote defect indicator alarm";
           }
           leaf sdh-alarm-tuuneq {
             type empty;
             description
               "TU unequipped alarm";
           }
           leaf sdh-alarm-tumis {
             type empty;
             description
               "TU label mismatch error";
           }
           leaf sdh-alarm-tuloc {
             type empty;
             description
               "TU loss of cell delineation alarm";
           }
           leaf ds3-alarm-pll {
             type empty;
             description
               "PLL lock alarm";
           }
           leaf ds3-alarm-ais {
             type empty;
             description
               "AIS alarm";
           }
           leaf ds3-alarm-lof {
             type empty;
             description
               "Loss of frame alarm";
           }
           leaf ds3-alarm-los {
             type empty;
             description
               "Loss of signal alarm";
           }
           leaf ds3-alarm-lcv {
             type empty;
             description
               "Line code violation alarm";
           }
           leaf ds3-alarm-exz {
             type empty;
             description
               "Excessive zeros alarm";
           }
           leaf ds3-alarm-ferf {
             type empty;
             description
               "Far-end receive failure alarm";
           }
           leaf ds3-alarm-ylw {
             type empty;
             description
               "Yellow alarm";
           }
           leaf ds3-alarm-idle {
             type empty;
             description
               "Idle alarm";
           }
           leaf ds1-alarm-ais {
             type empty;
             description
               "AIS alarm";
           }
           leaf ds1-alarm-lof {
             type empty;
             description
               "Loss of frame alarm";
           }
           leaf ds1-alarm-los {
             type empty;
             description
               "Loss of signal alarm";
           }
           leaf ds1-alarm-ylw {
             type empty;
             description
               "Yellow alarm";
           }
           leaf ds1-alarm-crc-major {
             type empty;
             description
               "CRC errors crossed major threshold";
           }
           leaf ds1-alarm-crc-minor {
             type empty;
             description
               "CRC errors crossed minor threshold";
           }
           leaf dsl-alarm-lof {
             type empty;
             description
               "Loss of frame alarm";
           }
           leaf dsl-alarm-los {
             type empty;
             description
               "Loss of signal alarm";
           }
           leaf dsl-alarm-lom {
             type empty;
             description
               "Loss of multiframe alarm";
           }
           leaf dsl-alarm-locdi {
             type empty;
             description
               "Loss of cell delineation alarm for interleaved channel";
           }
           leaf dsl-alarm-locdni {
             type empty;
             description
               "Loss of cell delineation alarm for non-interleaved channel";
           }
           leaf dsl-alarm-lop {
             type empty;
             description
               "Loss of power alarm";
           }
           leaf dsl-alarm-far-lof {
             type empty;
             description
               "Far-end loss-of-frame alarm";
           }
           leaf dsl-alarm-far-los {
             type empty;
             description
               "Far-end loss-of-signal alarm";
           }
           leaf dsl-alarm-far-locdi {
             type empty;
             description
               "Far-end loss-of-cell-delineation alarm for interleaved 
               channel";
           }
           leaf dsl-alarm-far-locdni {
             type empty;
             description
               "Far-end loss-of-cell-delineation alarm for non-interleaved 
               channel";
           }
           leaf fibrechannel-alarm-link-down {
             type empty;
             description
               "Link alive failure";
           }
           leaf ethernet-alarm-link-down {
             type empty;
             description
               "Link alive failure";
           }
           leaf ethernet-alarm-an-not-supported {
             type empty;
             description
               "AN not supported";
           }
           leaf ethernet-alarm-link-local-fault {
             type empty;
             description
               "Link local fault";
           }
           leaf ethernet-alarm-link-remote-fault {
             type empty;
             description
               "Link remote fault";
           }
           leaf ethernet-alarm-link-local-degrade {
             type empty;
             description
               "Link local degrade";
           }
           leaf ethernet-alarm-link-remote-degrade {
             type empty;
             description
               "Link remote degrade";
           }
           leaf ethernet-alarm-lcdp {
             type empty;
             description
               "Loss of code-group delineation";
           }
           leaf isdn-alarm-los {
             type empty;
             description
               "Loss of signal alarm";
           }
           leaf isdn-alarm-lof {
             type empty;
             description
               "Loss of frame alarm";
           }
           leaf shdsl-alarm-losd {
             type empty;
             description
               "Loss of signal alarm";
           }
           leaf shdsl-alarm-losw {
             type empty;
             description
               "Loss of sync word alarm";
           }
           leaf shdsl-alarm-line1-losd {
             type empty;
             description
               "Loss of signal (line 1) alarm";
           }
           leaf shdsl-alarm-line1-losw {
             type empty;
             description
               "Loss of sync word (line 1) alarm";
           }
           leaf shdsl-alarm-line2-losd {
             type empty;
             description
               "Loss of signal (line 2) alarm";
           }
           leaf shdsl-alarm-line2-losw {
             type empty;
             description
               "Loss of sync word (line 2) alarm";
           }
           leaf shdsl-efm-alarm-losd {
             type empty;
             description
               "Loss of signal alarm";
           }
           leaf shdsl-efm-alarm-losw {
             type empty;
             description
               "Loss of sync word alarm";
           }
           leaf otn-alarm-los {
             type empty;
             description
               "Loss of signal alarm";
           }
           leaf otn-alarm-lof {
             type empty;
             description
               "Loss of frame alarm";
           }
           leaf otn-alarm-lom {
             type empty;
             description
               "Loss of multiframe alarm";
           }
           leaf otn-alarm-wavelength-lock {
             type empty;
             description
               "Loss of Wavelength Lock alarm";
           }
           leaf otn-alarm-otu-ais {
             type empty;
             description
               "OTU Alarm Indication Signal alarm";
           }
           leaf otn-alarm-otu-bdi {
             type empty;
             description
               "OTU Background Block Error alarm";
           }
           leaf otn-alarm-otu-ttim {
             type empty;
             description
               "OTU Trail Trace Identifier Mismatch alarm";
           }
           leaf otn-alarm-otu-iae {
             type empty;
             description
               "OTU Incoming Alignment alarm";
           }
           leaf otn-alarm-otu-sd {
             type empty;
             description
               "OTU Signal Degrade alarm";
           }
           leaf otn-alarm-otu-sf {
             type empty;
             description
               "OTU Signal Fail alarm";
           }
           leaf otn-alarm-otu-biae {
             type empty;
             description
               "OTU Backward Incoming Alignment alarm";
           }
           leaf otn-alarm-otu-tsf {
             type empty;
             description
               "OTU Trail Signal Fail alarm";
           }
           leaf otn-alarm-otu-ssf {
             type empty;
             description
               "OTU Server Signal Fail alarm";
           }
           leaf otn-alarm-otu-fec-excessive {
             type empty;
             description
               "OTU FEC Excessive alarm";
           }
           leaf otn-alarm-otu-fec-degraded {
             type empty;
             description
               "OTU FEC Degraded alarm";
           }
           leaf otn-alarm-otu-fe-fec-degraded {
             type empty;
             description
               "OTU FE FEC Degraded/Excessive alarm";
           }
           leaf otn-alarm-otu-threshold-bbe {
             type empty;
             description
               "OTU Background Block Error threshold alarm";
           }
           leaf otn-alarm-otu-threshold-es {
             type empty;
             description
               "OTU Errored Seconds threshold alarm";
           }
           leaf otn-alarm-otu-threshold-ses {
             type empty;
             description
               "OTU Severely Errored Seconds threshold alarm";
           }
           leaf otn-alarm-otu-threshold-uas {
             type empty;
             description
               "OTU Unavailable Seconds threshold alarm";
           }
           leaf otn-alarm-odu-ais {
             type empty;
             description
               "ODU  Alarm Indiaction Signal alarm";
           }
           leaf otn-alarm-odu-oci {
             type empty;
             description
               "ODU Open Connection Indication alarm";
           }
           leaf otn-alarm-odu-lck {
             type empty;
             description
               "ODU Locked alarm";
           }
           leaf otn-alarm-odu-bdi {
             type empty;
             description
               "ODU Backward Defect Indication alarm";
           }
           leaf otn-alarm-odu-ttim {
             type empty;
             description
               "ODU Trail Trace Identifier Mismatch alarm";
           }
           leaf otn-alarm-odu-sd {
             type empty;
             description
               "ODU Signal Degrade alarm";
           }
           leaf otn-alarm-odu-sf {
             type empty;
             description
               "ODU Signal Fail alarm";
           }
           leaf otn-alarm-odu-iae {
             type empty;
             description
               "ODU Incoming Alignment alarm";
           }
           leaf otn-alarm-odu-ltc {
             type empty;
             description
               "ODU Loss of Tandem Connection alarm";
           }
           leaf otn-alarm-odu-csf {
             type empty;
             description
               "ODU Client Signal Fail alarm";
           }
           leaf otn-alarm-odu-tsf {
             type empty;
             description
               "ODU Trail Signal Fail alarm";
           }
           leaf otn-alarm-odu-ssf {
             type empty;
             description
               "ODU Server Signal Fail alarm";
           }
           leaf otn-alarm-odu-rx-aps-change {
             type empty;
             description
               "ODU Rx Aps Change alarm";
           }
           leaf otn-alarm-odu-threshold-bbe {
             type empty;
             description
               "ODU Background Block Error threshold alarm";
           }
           leaf otn-alarm-odu-threshold-es {
             type empty;
             description
               "ODU Errored Seconds threshold alarm";
           }
           leaf otn-alarm-odu-threshold-ses {
             type empty;
             description
               "ODU Severely Errored Seconds threshold alarm";
           }
           leaf otn-alarm-odu-threshold-uas {
             type empty;
             description
               "ODU Unavailable Seconds threshold alarm";
           }
           leaf otn-alarm-opu-pmi {
             type empty;
             description
               "OPU Payload Mismatch alarm";
           }
           leaf otn-alarm-pre-fec-sd {
             type empty;
             description
               "Pre-FEC SD alarm";
           }
           leaf otn-alarm-fe-pre-fec-sd {
             type empty;
             description
               "Far end pre-FEC SD alarm";
           }
           leaf optics-alarms-mod-fault {
             type empty;
             description
               "Module Fault alarm";
           }
           leaf optics-alarms-lol {
             type empty;
             description
               "Loss of Lock alarm";
           }
           leaf optics-alarms-los {
             type empty;
             description
               "Loss of Signal alarms";
           }
           leaf optics-alarms-lof {
             type empty;
             description
               "Loss of frame alarm";
           }
           leaf optics-alarms-lom {
             type empty;
             description
               "Loss of multi-frame alarm";
           }
           leaf optics-alarms-otu-bdi {
             type empty;
             description
               "Backward defect indiacation alarm";
           }
           leaf optics-alarms-rmsf {
             type empty;
             description
               "Rx Modem sysnc fault alarm";
           }
           leaf optics-alarms-rmlol {
             type empty;
             description
               "Rx Modem loss of lock alarm";
           }
           leaf optics-alarms-rloa {
             type empty;
             description
               "Rx loss of alignment alarm";
           }
           leaf optics-alarms-mbclf {
             type empty;
             description
               "Modulator Bias control loop fail alarm";
           }
           leaf optics-alarms-itlaf {
             type empty;
             description
               "ITLA Fault alarm";
           }
           leaf optics-alarms-daccf {
             type empty;
             description
               "DAC Calibration Fault alarm";
           }
           leaf optics-alarms-adccf {
             type empty;
             description
               "ADC Calibration Fault alarm";
           }
           leaf optics-alarms-fec-degrade {
             type empty;
             description
               "FEC Degrade alarm";
           }
           leaf optics-alarms-fec-excessive {
             type empty;
             description
               "FEC Excessive alarm";
           }
           leaf optics-alarms-fe-fec-degrade {
             type empty;
             description
               "Far-end FEC Degrade alarm";
           }
           leaf optics-alarms-fe-fec-excessive {
             type empty;
             description
               "Far-end FEC Excessive alarm";
           }
           leaf ima-alarm-startup-fe {
             type empty;
             description
               "IMA group startup far-end alarm";
           }
           leaf ima-alarm-config-abort {
             type empty;
             description
               "IMA group config abort alarm";
           }
           leaf ima-alarm-config-abort-fe {
             type empty;
             description
               "IMA group config abort far-end alarm";
           }
           leaf ima-alarm-insufficient-links {
             type empty;
             description
               "IMA group insufficient links alarm";
           }
           leaf ima-alarm-insufficient-links-fe {
             type empty;
             description
               "IMA group insufficient links far-end alarm";
           }
           leaf ima-alarm-blocked {
             type empty;
             description
               "IMA group blocked alarm";
           }
           leaf ima-alarm-blocked-fe {
             type empty;
             description
               "IMA group blocked far-end alarm";
           }
           leaf ima-alarm-timing-mismatch {
             type empty;
             description
               "IMA group timing mismatch alarm";
           }
           leaf ima-alarm-version-mismatch {
             type empty;
             description
               "IMA group version mismatch alarm";
           }
           leaf ima-alarm-lif {
             type empty;
             description
               "IMA link loss of IMA frame alarm";
           }
           leaf ima-alarm-lods {
             type empty;
             description
               "IMA link out of delay synchronization alarm";
           }
           leaf ima-alarm-rdi {
             type empty;
             description
               "IMA link remote defect indicator alarm";
           }
           leaf ima-alarm-tx-misconnected {
             type empty;
             description
               "IMA link tx misconnected alarm";
           }
           leaf ima-alarm-rx-misconnected {
             type empty;
             description
               "IMA link rx misconnected alarm";
           }
           leaf ima-alarm-fault {
             type empty;
             description
               "IMA link fault alarm";
           }
           leaf ima-alarm-tx-unusable-fe {
             type empty;
             description
               "IMA link Tx unusable far-end alarm";
           }
           leaf ima-alarm-rx-unusable-fe {
             type empty;
             description
               "IMA link Tx unusable far-end alarm";
           }
           leaf generic-value {
             type int32;
             description
               "Hexadecimal value of unknown flag bits";
           }
         }
       }
       container optics-defect-information {
         list media-alarm {
           leaf media-alarm-name {
             type string;
           }
           leaf media-alarm-seconds {
             type int32;
           }
           leaf media-alarm-count {
             type int32;
           }
           leaf media-alarm-state {
             type string;
           }
         }
       }
       container optics-fec-information {
         list media-alarm {
           leaf media-alarm-name {
             type string;
           }
           leaf media-alarm-seconds {
             type int32;
           }
           leaf media-alarm-count {
             type int32;
           }
           leaf media-alarm-state {
             type string;
           }
         }
       }
       container active-alerts-otn {
         leaf type-otn {
           type string;
           description
             "OTN type for associated interface alarms";
         }
         container interface-alarms {
           description
             "Container tag for interface alarms";
           leaf alarm-not-present {
             type empty;
             description
               "No alarm indicated";
           }
           leaf sonet-alarm-lol {
             type empty;
             description
               "Loss of light alarm";
           }
           leaf sonet-alarm-pll {
             type empty;
             description
               "PLL lock alarm";
           }
           leaf sonet-alarm-lof {
             type empty;
             description
               "Loss of frame alarm";
           }
           leaf sonet-alarm-los {
             type empty;
             description
               "Loss of signal alarm";
           }
           leaf sonet-alarm-sef {
             type empty;
             description
               "Severely errored frame alarm";
           }
           leaf sonet-alarm-lais {
             type empty;
             description
               "Line AIS alarm";
           }
           leaf sonet-alarm-pais {
             type empty;
             description
               "Path AIS alarm";
           }
           leaf sonet-alarm-lop {
             type empty;
             description
               "Loss of pointer alarm";
           }
           leaf sonet-alarm-berr-sd {
             type empty;
             description
               "Bit error rate alarm, defect";
           }
           leaf sonet-alarm-berr-sf {
             type empty;
             description
               "Bit error rate alarm, fault";
           }
           leaf sonet-alarm-lrdi {
             type empty;
             description
               "Line remote defect indicator alarm";
           }
           leaf sonet-alarm-prdi {
             type empty;
             description
               "Path remote defect indicator alarm";
           }
           leaf sonet-alarm-rei {
             type empty;
             description
               "Path remote error indicator alarm";
           }
           leaf sonet-alarm-uneq {
             type empty;
             description
               "Unequipped alarm";
           }
           leaf sonet-alarm-pmis {
             type empty;
             description
               "Path payload level mismatch alarm";
           }
           leaf sonet-alarm-loc {
             type empty;
             description
               "Loss of cell delineation alarm";
           }
           leaf sonet-alarm-vais {
             type empty;
             description
               "VT AIS alarm";
           }
           leaf sonet-alarm-vlop {
             type empty;
             description
               "VT loss of pointer alarm";
           }
           leaf sonet-alarm-vrdi {
             type empty;
             description
               "VT remote defect indicator alarm";
           }
           leaf sonet-alarm-vuneq {
             type empty;
             description
               "VT unequipped alarm";
           }
           leaf sonet-alarm-vmis {
             type empty;
             description
               "VT label mismatch alarm";
           }
           leaf sonet-alarm-vloc {
             type empty;
             description
               "VT loss of cell delineation alarm";
           }
           leaf sdh-alarm-lol {
             type empty;
             description
               "Loss of light alarm";
           }
           leaf sdh-alarm-pll {
             type empty;
             description
               "PLL lock alarm";
           }
           leaf sdh-alarm-lof {
             type empty;
             description
               "Loss of frame alarm";
           }
           leaf sdh-alarm-los {
             type empty;
             description
               "Loss of signal alarm";
           }
           leaf sdh-alarm-oof {
             type empty;
             description
               "Out of frame alarm";
           }
           leaf sdh-alarm-msais {
             type empty;
             description
               "Multiplex section AIS alarm";
           }
           leaf sdh-alarm-hpais {
             type empty;
             description
               "High order path AIS alarm";
           }
           leaf sdh-alarm-lop {
             type empty;
             description
               "Loss of pointer alarm";
           }
           leaf sdh-alarm-berr-sd {
             type empty;
             description
               "Bit error rate alarm, defect";
           }
           leaf sdh-alarm-berr-sf {
             type empty;
             description
               "Bit error rate alarm, fault";
           }
           leaf sdh-alarm-msferf {
             type empty;
             description
               "Multiplex section far-end remote failure alarm";
           }
           leaf sdh-alarm-hpferf {
             type empty;
             description
               "High order path far-end remote failure alarm";
           }
           leaf sdh-alarm-hpfebe {
             type empty;
             description
               "High order path far-end block error alarm";
           }
           leaf sdh-alarm-hpuneq {
             type empty;
             description
               "High order path unequipped alarm";
           }
           leaf sdh-alarm-hpplm {
             type empty;
             description
               "High order path payload level mismatch alarm";
           }
           leaf sdh-alarm-loc {
             type empty;
             description
               "Loss of cell delineation alarm";
           }
           leaf sdh-alarm-tuais {
             type empty;
             description
               "TU AIS alarm";
           }
           leaf sdh-alarm-tulop {
             type empty;
             description
               "TU loss of pointer alarm";
           }
           leaf sdh-alarm-turdi {
             type empty;
             description
               "TU remote defect indicator alarm";
           }
           leaf sdh-alarm-tuuneq {
             type empty;
             description
               "TU unequipped alarm";
           }
           leaf sdh-alarm-tumis {
             type empty;
             description
               "TU label mismatch error";
           }
           leaf sdh-alarm-tuloc {
             type empty;
             description
               "TU loss of cell delineation alarm";
           }
           leaf ds3-alarm-pll {
             type empty;
             description
               "PLL lock alarm";
           }
           leaf ds3-alarm-ais {
             type empty;
             description
               "AIS alarm";
           }
           leaf ds3-alarm-lof {
             type empty;
             description
               "Loss of frame alarm";
           }
           leaf ds3-alarm-los {
             type empty;
             description
               "Loss of signal alarm";
           }
           leaf ds3-alarm-lcv {
             type empty;
             description
               "Line code violation alarm";
           }
           leaf ds3-alarm-exz {
             type empty;
             description
               "Excessive zeros alarm";
           }
           leaf ds3-alarm-ferf {
             type empty;
             description
               "Far-end receive failure alarm";
           }
           leaf ds3-alarm-ylw {
             type empty;
             description
               "Yellow alarm";
           }
           leaf ds3-alarm-idle {
             type empty;
             description
               "Idle alarm";
           }
           leaf ds1-alarm-ais {
             type empty;
             description
               "AIS alarm";
           }
           leaf ds1-alarm-lof {
             type empty;
             description
               "Loss of frame alarm";
           }
           leaf ds1-alarm-los {
             type empty;
             description
               "Loss of signal alarm";
           }
           leaf ds1-alarm-ylw {
             type empty;
             description
               "Yellow alarm";
           }
           leaf ds1-alarm-crc-major {
             type empty;
             description
               "CRC errors crossed major threshold";
           }
           leaf ds1-alarm-crc-minor {
             type empty;
             description
               "CRC errors crossed minor threshold";
           }
           leaf dsl-alarm-lof {
             type empty;
             description
               "Loss of frame alarm";
           }
           leaf dsl-alarm-los {
             type empty;
             description
               "Loss of signal alarm";
           }
           leaf dsl-alarm-lom {
             type empty;
             description
               "Loss of multiframe alarm";
           }
           leaf dsl-alarm-locdi {
             type empty;
             description
               "Loss of cell delineation alarm for interleaved channel";
           }
           leaf dsl-alarm-locdni {
             type empty;
             description
               "Loss of cell delineation alarm for non-interleaved channel";
           }
           leaf dsl-alarm-lop {
             type empty;
             description
               "Loss of power alarm";
           }
           leaf dsl-alarm-far-lof {
             type empty;
             description
               "Far-end loss-of-frame alarm";
           }
           leaf dsl-alarm-far-los {
             type empty;
             description
               "Far-end loss-of-signal alarm";
           }
           leaf dsl-alarm-far-locdi {
             type empty;
             description
               "Far-end loss-of-cell-delineation alarm for interleaved 
               channel";
           }
           leaf dsl-alarm-far-locdni {
             type empty;
             description
               "Far-end loss-of-cell-delineation alarm for non-interleaved 
               channel";
           }
           leaf fibrechannel-alarm-link-down {
             type empty;
             description
               "Link alive failure";
           }
           leaf ethernet-alarm-link-down {
             type empty;
             description
               "Link alive failure";
           }
           leaf ethernet-alarm-an-not-supported {
             type empty;
             description
               "AN not supported";
           }
           leaf ethernet-alarm-link-local-fault {
             type empty;
             description
               "Link local fault";
           }
           leaf ethernet-alarm-link-remote-fault {
             type empty;
             description
               "Link remote fault";
           }
           leaf ethernet-alarm-link-local-degrade {
             type empty;
             description
               "Link local degrade";
           }
           leaf ethernet-alarm-link-remote-degrade {
             type empty;
             description
               "Link remote degrade";
           }
           leaf ethernet-alarm-lcdp {
             type empty;
             description
               "Loss of code-group delineation";
           }
           leaf isdn-alarm-los {
             type empty;
             description
               "Loss of signal alarm";
           }
           leaf isdn-alarm-lof {
             type empty;
             description
               "Loss of frame alarm";
           }
           leaf shdsl-alarm-losd {
             type empty;
             description
               "Loss of signal alarm";
           }
           leaf shdsl-alarm-losw {
             type empty;
             description
               "Loss of sync word alarm";
           }
           leaf shdsl-alarm-line1-losd {
             type empty;
             description
               "Loss of signal (line 1) alarm";
           }
           leaf shdsl-alarm-line1-losw {
             type empty;
             description
               "Loss of sync word (line 1) alarm";
           }
           leaf shdsl-alarm-line2-losd {
             type empty;
             description
               "Loss of signal (line 2) alarm";
           }
           leaf shdsl-alarm-line2-losw {
             type empty;
             description
               "Loss of sync word (line 2) alarm";
           }
           leaf shdsl-efm-alarm-losd {
             type empty;
             description
               "Loss of signal alarm";
           }
           leaf shdsl-efm-alarm-losw {
             type empty;
             description
               "Loss of sync word alarm";
           }
           leaf otn-alarm-los {
             type empty;
             description
               "Loss of signal alarm";
           }
           leaf otn-alarm-lof {
             type empty;
             description
               "Loss of frame alarm";
           }
           leaf otn-alarm-lom {
             type empty;
             description
               "Loss of multiframe alarm";
           }
           leaf otn-alarm-wavelength-lock {
             type empty;
             description
               "Loss of Wavelength Lock alarm";
           }
           leaf otn-alarm-otu-ais {
             type empty;
             description
               "OTU Alarm Indication Signal alarm";
           }
           leaf otn-alarm-otu-bdi {
             type empty;
             description
               "OTU Background Block Error alarm";
           }
           leaf otn-alarm-otu-ttim {
             type empty;
             description
               "OTU Trail Trace Identifier Mismatch alarm";
           }
           leaf otn-alarm-otu-iae {
             type empty;
             description
               "OTU Incoming Alignment alarm";
           }
           leaf otn-alarm-otu-sd {
             type empty;
             description
               "OTU Signal Degrade alarm";
           }
           leaf otn-alarm-otu-sf {
             type empty;
             description
               "OTU Signal Fail alarm";
           }
           leaf otn-alarm-otu-biae {
             type empty;
             description
               "OTU Backward Incoming Alignment alarm";
           }
           leaf otn-alarm-otu-tsf {
             type empty;
             description
               "OTU Trail Signal Fail alarm";
           }
           leaf otn-alarm-otu-ssf {
             type empty;
             description
               "OTU Server Signal Fail alarm";
           }
           leaf otn-alarm-otu-fec-excessive {
             type empty;
             description
               "OTU FEC Excessive alarm";
           }
           leaf otn-alarm-otu-fec-degraded {
             type empty;
             description
               "OTU FEC Degraded alarm";
           }
           leaf otn-alarm-otu-fe-fec-degraded {
             type empty;
             description
               "OTU FE FEC Degraded/Excessive alarm";
           }
           leaf otn-alarm-otu-threshold-bbe {
             type empty;
             description
               "OTU Background Block Error threshold alarm";
           }
           leaf otn-alarm-otu-threshold-es {
             type empty;
             description
               "OTU Errored Seconds threshold alarm";
           }
           leaf otn-alarm-otu-threshold-ses {
             type empty;
             description
               "OTU Severely Errored Seconds threshold alarm";
           }
           leaf otn-alarm-otu-threshold-uas {
             type empty;
             description
               "OTU Unavailable Seconds threshold alarm";
           }
           leaf otn-alarm-odu-ais {
             type empty;
             description
               "ODU  Alarm Indiaction Signal alarm";
           }
           leaf otn-alarm-odu-oci {
             type empty;
             description
               "ODU Open Connection Indication alarm";
           }
           leaf otn-alarm-odu-lck {
             type empty;
             description
               "ODU Locked alarm";
           }
           leaf otn-alarm-odu-bdi {
             type empty;
             description
               "ODU Backward Defect Indication alarm";
           }
           leaf otn-alarm-odu-ttim {
             type empty;
             description
               "ODU Trail Trace Identifier Mismatch alarm";
           }
           leaf otn-alarm-odu-sd {
             type empty;
             description
               "ODU Signal Degrade alarm";
           }
           leaf otn-alarm-odu-sf {
             type empty;
             description
               "ODU Signal Fail alarm";
           }
           leaf otn-alarm-odu-iae {
             type empty;
             description
               "ODU Incoming Alignment alarm";
           }
           leaf otn-alarm-odu-ltc {
             type empty;
             description
               "ODU Loss of Tandem Connection alarm";
           }
           leaf otn-alarm-odu-csf {
             type empty;
             description
               "ODU Client Signal Fail alarm";
           }
           leaf otn-alarm-odu-tsf {
             type empty;
             description
               "ODU Trail Signal Fail alarm";
           }
           leaf otn-alarm-odu-ssf {
             type empty;
             description
               "ODU Server Signal Fail alarm";
           }
           leaf otn-alarm-odu-rx-aps-change {
             type empty;
             description
               "ODU Rx Aps Change alarm";
           }
           leaf otn-alarm-odu-threshold-bbe {
             type empty;
             description
               "ODU Background Block Error threshold alarm";
           }
           leaf otn-alarm-odu-threshold-es {
             type empty;
             description
               "ODU Errored Seconds threshold alarm";
           }
           leaf otn-alarm-odu-threshold-ses {
             type empty;
             description
               "ODU Severely Errored Seconds threshold alarm";
           }
           leaf otn-alarm-odu-threshold-uas {
             type empty;
             description
               "ODU Unavailable Seconds threshold alarm";
           }
           leaf otn-alarm-opu-pmi {
             type empty;
             description
               "OPU Payload Mismatch alarm";
           }
           leaf otn-alarm-pre-fec-sd {
             type empty;
             description
               "Pre-FEC SD alarm";
           }
           leaf otn-alarm-fe-pre-fec-sd {
             type empty;
             description
               "Far end pre-FEC SD alarm";
           }
           leaf optics-alarms-mod-fault {
             type empty;
             description
               "Module Fault alarm";
           }
           leaf optics-alarms-lol {
             type empty;
             description
               "Loss of Lock alarm";
           }
           leaf optics-alarms-los {
             type empty;
             description
               "Loss of Signal alarms";
           }
           leaf optics-alarms-lof {
             type empty;
             description
               "Loss of frame alarm";
           }
           leaf optics-alarms-lom {
             type empty;
             description
               "Loss of multi-frame alarm";
           }
           leaf optics-alarms-otu-bdi {
             type empty;
             description
               "Backward defect indiacation alarm";
           }
           leaf optics-alarms-rmsf {
             type empty;
             description
               "Rx Modem sysnc fault alarm";
           }
           leaf optics-alarms-rmlol {
             type empty;
             description
               "Rx Modem loss of lock alarm";
           }
           leaf optics-alarms-rloa {
             type empty;
             description
               "Rx loss of alignment alarm";
           }
           leaf optics-alarms-mbclf {
             type empty;
             description
               "Modulator Bias control loop fail alarm";
           }
           leaf optics-alarms-itlaf {
             type empty;
             description
               "ITLA Fault alarm";
           }
           leaf optics-alarms-daccf {
             type empty;
             description
               "DAC Calibration Fault alarm";
           }
           leaf optics-alarms-adccf {
             type empty;
             description
               "ADC Calibration Fault alarm";
           }
           leaf optics-alarms-fec-degrade {
             type empty;
             description
               "FEC Degrade alarm";
           }
           leaf optics-alarms-fec-excessive {
             type empty;
             description
               "FEC Excessive alarm";
           }
           leaf optics-alarms-fe-fec-degrade {
             type empty;
             description
               "Far-end FEC Degrade alarm";
           }
           leaf optics-alarms-fe-fec-excessive {
             type empty;
             description
               "Far-end FEC Excessive alarm";
           }
           leaf ima-alarm-startup-fe {
             type empty;
             description
               "IMA group startup far-end alarm";
           }
           leaf ima-alarm-config-abort {
             type empty;
             description
               "IMA group config abort alarm";
           }
           leaf ima-alarm-config-abort-fe {
             type empty;
             description
               "IMA group config abort far-end alarm";
           }
           leaf ima-alarm-insufficient-links {
             type empty;
             description
               "IMA group insufficient links alarm";
           }
           leaf ima-alarm-insufficient-links-fe {
             type empty;
             description
               "IMA group insufficient links far-end alarm";
           }
           leaf ima-alarm-blocked {
             type empty;
             description
               "IMA group blocked alarm";
           }
           leaf ima-alarm-blocked-fe {
             type empty;
             description
               "IMA group blocked far-end alarm";
           }
           leaf ima-alarm-timing-mismatch {
             type empty;
             description
               "IMA group timing mismatch alarm";
           }
           leaf ima-alarm-version-mismatch {
             type empty;
             description
               "IMA group version mismatch alarm";
           }
           leaf ima-alarm-lif {
             type empty;
             description
               "IMA link loss of IMA frame alarm";
           }
           leaf ima-alarm-lods {
             type empty;
             description
               "IMA link out of delay synchronization alarm";
           }
           leaf ima-alarm-rdi {
             type empty;
             description
               "IMA link remote defect indicator alarm";
           }
           leaf ima-alarm-tx-misconnected {
             type empty;
             description
               "IMA link tx misconnected alarm";
           }
           leaf ima-alarm-rx-misconnected {
             type empty;
             description
               "IMA link rx misconnected alarm";
           }
           leaf ima-alarm-fault {
             type empty;
             description
               "IMA link fault alarm";
           }
           leaf ima-alarm-tx-unusable-fe {
             type empty;
             description
               "IMA link Tx unusable far-end alarm";
           }
           leaf ima-alarm-rx-unusable-fe {
             type empty;
             description
               "IMA link Tx unusable far-end alarm";
           }
           leaf generic-value {
             type int32;
             description
               "Hexadecimal value of unknown flag bits";
           }
         }
       }
       container links {
         description
           "Aggregated SONET/SDH link information";
         list link-entry {
           description
             "SONET/SDH link information";
           leaf link-id {
             type int32;
             description
               "Link id for aggregated SONET/SDH interface";
           }
           leaf sonet-rx-overhead {
             type string;
           }
           leaf sonet-tx-overhead {
             type string;
           }
           leaf sonet-rx-path-trace {
             type string;
             description
               "Received SONET path trace";
           }
           leaf sonet-tx-path-trace {
             type string;
             description
               "Transmitted SONET path trace";
           }
           leaf sonet-payload-pointer-curptr {
             type string;
             description
               "Value of the SONET/SDH payload pointer, derived from the H1 
               and H2 overhead bytes";
           }
           leaf sonet-payload-pointer-ptrinc-count {
             type string;
             description
               "Number of times the value of the SONET/SDH payload pointer 
               had positive justification";
           }
           leaf sonet-payload-pointer-ptrdec-count {
             type string;
             description
               "Number of times the value of the SONET/SDH payload pointer 
               had negative justification";
           }
           leaf sonet-payload-pointer-newptr-ndf-count {
             type string;
             description
               "Number of times a new payload pointer was created with the 
               New Data Found flag set";
           }
           container active-alarms {
             leaf type {
               type string;
               description
                 "Media type for associated interface alarms";
             }
             container interface-alarms {
               description
                 "Container tag for interface alarms";
               leaf alarm-not-present {
                 type empty;
                 description
                   "No alarm indicated";
               }
               leaf sonet-alarm-lol {
                 type empty;
                 description
                   "Loss of light alarm";
               }
               leaf sonet-alarm-pll {
                 type empty;
                 description
                   "PLL lock alarm";
               }
               leaf sonet-alarm-lof {
                 type empty;
                 description
                   "Loss of frame alarm";
               }
               leaf sonet-alarm-los {
                 type empty;
                 description
                   "Loss of signal alarm";
               }
               leaf sonet-alarm-sef {
                 type empty;
                 description
                   "Severely errored frame alarm";
               }
               leaf sonet-alarm-lais {
                 type empty;
                 description
                   "Line AIS alarm";
               }
               leaf sonet-alarm-pais {
                 type empty;
                 description
                   "Path AIS alarm";
               }
               leaf sonet-alarm-lop {
                 type empty;
                 description
                   "Loss of pointer alarm";
               }
               leaf sonet-alarm-berr-sd {
                 type empty;
                 description
                   "Bit error rate alarm, defect";
               }
               leaf sonet-alarm-berr-sf {
                 type empty;
                 description
                   "Bit error rate alarm, fault";
               }
               leaf sonet-alarm-lrdi {
                 type empty;
                 description
                   "Line remote defect indicator alarm";
               }
               leaf sonet-alarm-prdi {
                 type empty;
                 description
                   "Path remote defect indicator alarm";
               }
               leaf sonet-alarm-rei {
                 type empty;
                 description
                   "Path remote error indicator alarm";
               }
               leaf sonet-alarm-uneq {
                 type empty;
                 description
                   "Unequipped alarm";
               }
               leaf sonet-alarm-pmis {
                 type empty;
                 description
                   "Path payload level mismatch alarm";
               }
               leaf sonet-alarm-loc {
                 type empty;
                 description
                   "Loss of cell delineation alarm";
               }
               leaf sonet-alarm-vais {
                 type empty;
                 description
                   "VT AIS alarm";
               }
               leaf sonet-alarm-vlop {
                 type empty;
                 description
                   "VT loss of pointer alarm";
               }
               leaf sonet-alarm-vrdi {
                 type empty;
                 description
                   "VT remote defect indicator alarm";
               }
               leaf sonet-alarm-vuneq {
                 type empty;
                 description
                   "VT unequipped alarm";
               }
               leaf sonet-alarm-vmis {
                 type empty;
                 description
                   "VT label mismatch alarm";
               }
               leaf sonet-alarm-vloc {
                 type empty;
                 description
                   "VT loss of cell delineation alarm";
               }
               leaf sdh-alarm-lol {
                 type empty;
                 description
                   "Loss of light alarm";
               }
               leaf sdh-alarm-pll {
                 type empty;
                 description
                   "PLL lock alarm";
               }
               leaf sdh-alarm-lof {
                 type empty;
                 description
                   "Loss of frame alarm";
               }
               leaf sdh-alarm-los {
                 type empty;
                 description
                   "Loss of signal alarm";
               }
               leaf sdh-alarm-oof {
                 type empty;
                 description
                   "Out of frame alarm";
               }
               leaf sdh-alarm-msais {
                 type empty;
                 description
                   "Multiplex section AIS alarm";
               }
               leaf sdh-alarm-hpais {
                 type empty;
                 description
                   "High order path AIS alarm";
               }
               leaf sdh-alarm-lop {
                 type empty;
                 description
                   "Loss of pointer alarm";
               }
               leaf sdh-alarm-berr-sd {
                 type empty;
                 description
                   "Bit error rate alarm, defect";
               }
               leaf sdh-alarm-berr-sf {
                 type empty;
                 description
                   "Bit error rate alarm, fault";
               }
               leaf sdh-alarm-msferf {
                 type empty;
                 description
                   "Multiplex section far-end remote failure alarm";
               }
               leaf sdh-alarm-hpferf {
                 type empty;
                 description
                   "High order path far-end remote failure alarm";
               }
               leaf sdh-alarm-hpfebe {
                 type empty;
                 description
                   "High order path far-end block error alarm";
               }
               leaf sdh-alarm-hpuneq {
                 type empty;
                 description
                   "High order path unequipped alarm";
               }
               leaf sdh-alarm-hpplm {
                 type empty;
                 description
                   "High order path payload level mismatch alarm";
               }
               leaf sdh-alarm-loc {
                 type empty;
                 description
                   "Loss of cell delineation alarm";
               }
               leaf sdh-alarm-tuais {
                 type empty;
                 description
                   "TU AIS alarm";
               }
               leaf sdh-alarm-tulop {
                 type empty;
                 description
                   "TU loss of pointer alarm";
               }
               leaf sdh-alarm-turdi {
                 type empty;
                 description
                   "TU remote defect indicator alarm";
               }
               leaf sdh-alarm-tuuneq {
                 type empty;
                 description
                   "TU unequipped alarm";
               }
               leaf sdh-alarm-tumis {
                 type empty;
                 description
                   "TU label mismatch error";
               }
               leaf sdh-alarm-tuloc {
                 type empty;
                 description
                   "TU loss of cell delineation alarm";
               }
               leaf ds3-alarm-pll {
                 type empty;
                 description
                   "PLL lock alarm";
               }
               leaf ds3-alarm-ais {
                 type empty;
                 description
                   "AIS alarm";
               }
               leaf ds3-alarm-lof {
                 type empty;
                 description
                   "Loss of frame alarm";
               }
               leaf ds3-alarm-los {
                 type empty;
                 description
                   "Loss of signal alarm";
               }
               leaf ds3-alarm-lcv {
                 type empty;
                 description
                   "Line code violation alarm";
               }
               leaf ds3-alarm-exz {
                 type empty;
                 description
                   "Excessive zeros alarm";
               }
               leaf ds3-alarm-ferf {
                 type empty;
                 description
                   "Far-end receive failure alarm";
               }
               leaf ds3-alarm-ylw {
                 type empty;
                 description
                   "Yellow alarm";
               }
               leaf ds3-alarm-idle {
                 type empty;
                 description
                   "Idle alarm";
               }
               leaf ds1-alarm-ais {
                 type empty;
                 description
                   "AIS alarm";
               }
               leaf ds1-alarm-lof {
                 type empty;
                 description
                   "Loss of frame alarm";
               }
               leaf ds1-alarm-los {
                 type empty;
                 description
                   "Loss of signal alarm";
               }
               leaf ds1-alarm-ylw {
                 type empty;
                 description
                   "Yellow alarm";
               }
               leaf ds1-alarm-crc-major {
                 type empty;
                 description
                   "CRC errors crossed major threshold";
               }
               leaf ds1-alarm-crc-minor {
                 type empty;
                 description
                   "CRC errors crossed minor threshold";
               }
               leaf dsl-alarm-lof {
                 type empty;
                 description
                   "Loss of frame alarm";
               }
               leaf dsl-alarm-los {
                 type empty;
                 description
                   "Loss of signal alarm";
               }
               leaf dsl-alarm-lom {
                 type empty;
                 description
                   "Loss of multiframe alarm";
               }
               leaf dsl-alarm-locdi {
                 type empty;
                 description
                   "Loss of cell delineation alarm for interleaved channel";
               }
               leaf dsl-alarm-locdni {
                 type empty;
                 description
                   "Loss of cell delineation alarm for non-interleaved 
                   channel";
               }
               leaf dsl-alarm-lop {
                 type empty;
                 description
                   "Loss of power alarm";
               }
               leaf dsl-alarm-far-lof {
                 type empty;
                 description
                   "Far-end loss-of-frame alarm";
               }
               leaf dsl-alarm-far-los {
                 type empty;
                 description
                   "Far-end loss-of-signal alarm";
               }
               leaf dsl-alarm-far-locdi {
                 type empty;
                 description
                   "Far-end loss-of-cell-delineation alarm for interleaved 
                   channel";
               }
               leaf dsl-alarm-far-locdni {
                 type empty;
                 description
                   "Far-end loss-of-cell-delineation alarm for 
                   non-interleaved channel";
               }
               leaf fibrechannel-alarm-link-down {
                 type empty;
                 description
                   "Link alive failure";
               }
               leaf ethernet-alarm-link-down {
                 type empty;
                 description
                   "Link alive failure";
               }
               leaf ethernet-alarm-an-not-supported {
                 type empty;
                 description
                   "AN not supported";
               }
               leaf ethernet-alarm-link-local-fault {
                 type empty;
                 description
                   "Link local fault";
               }
               leaf ethernet-alarm-link-remote-fault {
                 type empty;
                 description
                   "Link remote fault";
               }
               leaf ethernet-alarm-link-local-degrade {
                 type empty;
                 description
                   "Link local degrade";
               }
               leaf ethernet-alarm-link-remote-degrade {
                 type empty;
                 description
                   "Link remote degrade";
               }
               leaf ethernet-alarm-lcdp {
                 type empty;
                 description
                   "Loss of code-group delineation";
               }
               leaf isdn-alarm-los {
                 type empty;
                 description
                   "Loss of signal alarm";
               }
               leaf isdn-alarm-lof {
                 type empty;
                 description
                   "Loss of frame alarm";
               }
               leaf shdsl-alarm-losd {
                 type empty;
                 description
                   "Loss of signal alarm";
               }
               leaf shdsl-alarm-losw {
                 type empty;
                 description
                   "Loss of sync word alarm";
               }
               leaf shdsl-alarm-line1-losd {
                 type empty;
                 description
                   "Loss of signal (line 1) alarm";
               }
               leaf shdsl-alarm-line1-losw {
                 type empty;
                 description
                   "Loss of sync word (line 1) alarm";
               }
               leaf shdsl-alarm-line2-losd {
                 type empty;
                 description
                   "Loss of signal (line 2) alarm";
               }
               leaf shdsl-alarm-line2-losw {
                 type empty;
                 description
                   "Loss of sync word (line 2) alarm";
               }
               leaf shdsl-efm-alarm-losd {
                 type empty;
                 description
                   "Loss of signal alarm";
               }
               leaf shdsl-efm-alarm-losw {
                 type empty;
                 description
                   "Loss of sync word alarm";
               }
               leaf otn-alarm-los {
                 type empty;
                 description
                   "Loss of signal alarm";
               }
               leaf otn-alarm-lof {
                 type empty;
                 description
                   "Loss of frame alarm";
               }
               leaf otn-alarm-lom {
                 type empty;
                 description
                   "Loss of multiframe alarm";
               }
               leaf otn-alarm-wavelength-lock {
                 type empty;
                 description
                   "Loss of Wavelength Lock alarm";
               }
               leaf otn-alarm-otu-ais {
                 type empty;
                 description
                   "OTU Alarm Indication Signal alarm";
               }
               leaf otn-alarm-otu-bdi {
                 type empty;
                 description
                   "OTU Background Block Error alarm";
               }
               leaf otn-alarm-otu-ttim {
                 type empty;
                 description
                   "OTU Trail Trace Identifier Mismatch alarm";
               }
               leaf otn-alarm-otu-iae {
                 type empty;
                 description
                   "OTU Incoming Alignment alarm";
               }
               leaf otn-alarm-otu-sd {
                 type empty;
                 description
                   "OTU Signal Degrade alarm";
               }
               leaf otn-alarm-otu-sf {
                 type empty;
                 description
                   "OTU Signal Fail alarm";
               }
               leaf otn-alarm-otu-biae {
                 type empty;
                 description
                   "OTU Backward Incoming Alignment alarm";
               }
               leaf otn-alarm-otu-tsf {
                 type empty;
                 description
                   "OTU Trail Signal Fail alarm";
               }
               leaf otn-alarm-otu-ssf {
                 type empty;
                 description
                   "OTU Server Signal Fail alarm";
               }
               leaf otn-alarm-otu-fec-excessive {
                 type empty;
                 description
                   "OTU FEC Excessive alarm";
               }
               leaf otn-alarm-otu-fec-degraded {
                 type empty;
                 description
                   "OTU FEC Degraded alarm";
               }
               leaf otn-alarm-otu-fe-fec-degraded {
                 type empty;
                 description
                   "OTU FE FEC Degraded/Excessive alarm";
               }
               leaf otn-alarm-otu-threshold-bbe {
                 type empty;
                 description
                   "OTU Background Block Error threshold alarm";
               }
               leaf otn-alarm-otu-threshold-es {
                 type empty;
                 description
                   "OTU Errored Seconds threshold alarm";
               }
               leaf otn-alarm-otu-threshold-ses {
                 type empty;
                 description
                   "OTU Severely Errored Seconds threshold alarm";
               }
               leaf otn-alarm-otu-threshold-uas {
                 type empty;
                 description
                   "OTU Unavailable Seconds threshold alarm";
               }
               leaf otn-alarm-odu-ais {
                 type empty;
                 description
                   "ODU  Alarm Indiaction Signal alarm";
               }
               leaf otn-alarm-odu-oci {
                 type empty;
                 description
                   "ODU Open Connection Indication alarm";
               }
               leaf otn-alarm-odu-lck {
                 type empty;
                 description
                   "ODU Locked alarm";
               }
               leaf otn-alarm-odu-bdi {
                 type empty;
                 description
                   "ODU Backward Defect Indication alarm";
               }
               leaf otn-alarm-odu-ttim {
                 type empty;
                 description
                   "ODU Trail Trace Identifier Mismatch alarm";
               }
               leaf otn-alarm-odu-sd {
                 type empty;
                 description
                   "ODU Signal Degrade alarm";
               }
               leaf otn-alarm-odu-sf {
                 type empty;
                 description
                   "ODU Signal Fail alarm";
               }
               leaf otn-alarm-odu-iae {
                 type empty;
                 description
                   "ODU Incoming Alignment alarm";
               }
               leaf otn-alarm-odu-ltc {
                 type empty;
                 description
                   "ODU Loss of Tandem Connection alarm";
               }
               leaf otn-alarm-odu-csf {
                 type empty;
                 description
                   "ODU Client Signal Fail alarm";
               }
               leaf otn-alarm-odu-tsf {
                 type empty;
                 description
                   "ODU Trail Signal Fail alarm";
               }
               leaf otn-alarm-odu-ssf {
                 type empty;
                 description
                   "ODU Server Signal Fail alarm";
               }
               leaf otn-alarm-odu-rx-aps-change {
                 type empty;
                 description
                   "ODU Rx Aps Change alarm";
               }
               leaf otn-alarm-odu-threshold-bbe {
                 type empty;
                 description
                   "ODU Background Block Error threshold alarm";
               }
               leaf otn-alarm-odu-threshold-es {
                 type empty;
                 description
                   "ODU Errored Seconds threshold alarm";
               }
               leaf otn-alarm-odu-threshold-ses {
                 type empty;
                 description
                   "ODU Severely Errored Seconds threshold alarm";
               }
               leaf otn-alarm-odu-threshold-uas {
                 type empty;
                 description
                   "ODU Unavailable Seconds threshold alarm";
               }
               leaf otn-alarm-opu-pmi {
                 type empty;
                 description
                   "OPU Payload Mismatch alarm";
               }
               leaf otn-alarm-pre-fec-sd {
                 type empty;
                 description
                   "Pre-FEC SD alarm";
               }
               leaf otn-alarm-fe-pre-fec-sd {
                 type empty;
                 description
                   "Far end pre-FEC SD alarm";
               }
               leaf optics-alarms-mod-fault {
                 type empty;
                 description
                   "Module Fault alarm";
               }
               leaf optics-alarms-lol {
                 type empty;
                 description
                   "Loss of Lock alarm";
               }
               leaf optics-alarms-los {
                 type empty;
                 description
                   "Loss of Signal alarms";
               }
               leaf optics-alarms-lof {
                 type empty;
                 description
                   "Loss of frame alarm";
               }
               leaf optics-alarms-lom {
                 type empty;
                 description
                   "Loss of multi-frame alarm";
               }
               leaf optics-alarms-otu-bdi {
                 type empty;
                 description
                   "Backward defect indiacation alarm";
               }
               leaf optics-alarms-rmsf {
                 type empty;
                 description
                   "Rx Modem sysnc fault alarm";
               }
               leaf optics-alarms-rmlol {
                 type empty;
                 description
                   "Rx Modem loss of lock alarm";
               }
               leaf optics-alarms-rloa {
                 type empty;
                 description
                   "Rx loss of alignment alarm";
               }
               leaf optics-alarms-mbclf {
                 type empty;
                 description
                   "Modulator Bias control loop fail alarm";
               }
               leaf optics-alarms-itlaf {
                 type empty;
                 description
                   "ITLA Fault alarm";
               }
               leaf optics-alarms-daccf {
                 type empty;
                 description
                   "DAC Calibration Fault alarm";
               }
               leaf optics-alarms-adccf {
                 type empty;
                 description
                   "ADC Calibration Fault alarm";
               }
               leaf optics-alarms-fec-degrade {
                 type empty;
                 description
                   "FEC Degrade alarm";
               }
               leaf optics-alarms-fec-excessive {
                 type empty;
                 description
                   "FEC Excessive alarm";
               }
               leaf optics-alarms-fe-fec-degrade {
                 type empty;
                 description
                   "Far-end FEC Degrade alarm";
               }
               leaf optics-alarms-fe-fec-excessive {
                 type empty;
                 description
                   "Far-end FEC Excessive alarm";
               }
               leaf ima-alarm-startup-fe {
                 type empty;
                 description
                   "IMA group startup far-end alarm";
               }
               leaf ima-alarm-config-abort {
                 type empty;
                 description
                   "IMA group config abort alarm";
               }
               leaf ima-alarm-config-abort-fe {
                 type empty;
                 description
                   "IMA group config abort far-end alarm";
               }
               leaf ima-alarm-insufficient-links {
                 type empty;
                 description
                   "IMA group insufficient links alarm";
               }
               leaf ima-alarm-insufficient-links-fe {
                 type empty;
                 description
                   "IMA group insufficient links far-end alarm";
               }
               leaf ima-alarm-blocked {
                 type empty;
                 description
                   "IMA group blocked alarm";
               }
               leaf ima-alarm-blocked-fe {
                 type empty;
                 description
                   "IMA group blocked far-end alarm";
               }
               leaf ima-alarm-timing-mismatch {
                 type empty;
                 description
                   "IMA group timing mismatch alarm";
               }
               leaf ima-alarm-version-mismatch {
                 type empty;
                 description
                   "IMA group version mismatch alarm";
               }
               leaf ima-alarm-lif {
                 type empty;
                 description
                   "IMA link loss of IMA frame alarm";
               }
               leaf ima-alarm-lods {
                 type empty;
                 description
                   "IMA link out of delay synchronization alarm";
               }
               leaf ima-alarm-rdi {
                 type empty;
                 description
                   "IMA link remote defect indicator alarm";
               }
               leaf ima-alarm-tx-misconnected {
                 type empty;
                 description
                   "IMA link tx misconnected alarm";
               }
               leaf ima-alarm-rx-misconnected {
                 type empty;
                 description
                   "IMA link rx misconnected alarm";
               }
               leaf ima-alarm-fault {
                 type empty;
                 description
                   "IMA link fault alarm";
               }
               leaf ima-alarm-tx-unusable-fe {
                 type empty;
                 description
                   "IMA link Tx unusable far-end alarm";
               }
               leaf ima-alarm-rx-unusable-fe {
                 type empty;
                 description
                   "IMA link Tx unusable far-end alarm";
               }
               leaf generic-value {
                 type int32;
                 description
                   "Hexadecimal value of unknown flag bits";
               }
             }
           }
           container active-defects {
             leaf type {
               type string;
               description
                 "Media type for associated interface alarms";
             }
             container interface-alarms {
               description
                 "Container tag for interface alarms";
               leaf alarm-not-present {
                 type empty;
                 description
                   "No alarm indicated";
               }
               leaf sonet-alarm-lol {
                 type empty;
                 description
                   "Loss of light alarm";
               }
               leaf sonet-alarm-pll {
                 type empty;
                 description
                   "PLL lock alarm";
               }
               leaf sonet-alarm-lof {
                 type empty;
                 description
                   "Loss of frame alarm";
               }
               leaf sonet-alarm-los {
                 type empty;
                 description
                   "Loss of signal alarm";
               }
               leaf sonet-alarm-sef {
                 type empty;
                 description
                   "Severely errored frame alarm";
               }
               leaf sonet-alarm-lais {
                 type empty;
                 description
                   "Line AIS alarm";
               }
               leaf sonet-alarm-pais {
                 type empty;
                 description
                   "Path AIS alarm";
               }
               leaf sonet-alarm-lop {
                 type empty;
                 description
                   "Loss of pointer alarm";
               }
               leaf sonet-alarm-berr-sd {
                 type empty;
                 description
                   "Bit error rate alarm, defect";
               }
               leaf sonet-alarm-berr-sf {
                 type empty;
                 description
                   "Bit error rate alarm, fault";
               }
               leaf sonet-alarm-lrdi {
                 type empty;
                 description
                   "Line remote defect indicator alarm";
               }
               leaf sonet-alarm-prdi {
                 type empty;
                 description
                   "Path remote defect indicator alarm";
               }
               leaf sonet-alarm-rei {
                 type empty;
                 description
                   "Path remote error indicator alarm";
               }
               leaf sonet-alarm-uneq {
                 type empty;
                 description
                   "Unequipped alarm";
               }
               leaf sonet-alarm-pmis {
                 type empty;
                 description
                   "Path payload level mismatch alarm";
               }
               leaf sonet-alarm-loc {
                 type empty;
                 description
                   "Loss of cell delineation alarm";
               }
               leaf sonet-alarm-vais {
                 type empty;
                 description
                   "VT AIS alarm";
               }
               leaf sonet-alarm-vlop {
                 type empty;
                 description
                   "VT loss of pointer alarm";
               }
               leaf sonet-alarm-vrdi {
                 type empty;
                 description
                   "VT remote defect indicator alarm";
               }
               leaf sonet-alarm-vuneq {
                 type empty;
                 description
                   "VT unequipped alarm";
               }
               leaf sonet-alarm-vmis {
                 type empty;
                 description
                   "VT label mismatch alarm";
               }
               leaf sonet-alarm-vloc {
                 type empty;
                 description
                   "VT loss of cell delineation alarm";
               }
               leaf sdh-alarm-lol {
                 type empty;
                 description
                   "Loss of light alarm";
               }
               leaf sdh-alarm-pll {
                 type empty;
                 description
                   "PLL lock alarm";
               }
               leaf sdh-alarm-lof {
                 type empty;
                 description
                   "Loss of frame alarm";
               }
               leaf sdh-alarm-los {
                 type empty;
                 description
                   "Loss of signal alarm";
               }
               leaf sdh-alarm-oof {
                 type empty;
                 description
                   "Out of frame alarm";
               }
               leaf sdh-alarm-msais {
                 type empty;
                 description
                   "Multiplex section AIS alarm";
               }
               leaf sdh-alarm-hpais {
                 type empty;
                 description
                   "High order path AIS alarm";
               }
               leaf sdh-alarm-lop {
                 type empty;
                 description
                   "Loss of pointer alarm";
               }
               leaf sdh-alarm-berr-sd {
                 type empty;
                 description
                   "Bit error rate alarm, defect";
               }
               leaf sdh-alarm-berr-sf {
                 type empty;
                 description
                   "Bit error rate alarm, fault";
               }
               leaf sdh-alarm-msferf {
                 type empty;
                 description
                   "Multiplex section far-end remote failure alarm";
               }
               leaf sdh-alarm-hpferf {
                 type empty;
                 description
                   "High order path far-end remote failure alarm";
               }
               leaf sdh-alarm-hpfebe {
                 type empty;
                 description
                   "High order path far-end block error alarm";
               }
               leaf sdh-alarm-hpuneq {
                 type empty;
                 description
                   "High order path unequipped alarm";
               }
               leaf sdh-alarm-hpplm {
                 type empty;
                 description
                   "High order path payload level mismatch alarm";
               }
               leaf sdh-alarm-loc {
                 type empty;
                 description
                   "Loss of cell delineation alarm";
               }
               leaf sdh-alarm-tuais {
                 type empty;
                 description
                   "TU AIS alarm";
               }
               leaf sdh-alarm-tulop {
                 type empty;
                 description
                   "TU loss of pointer alarm";
               }
               leaf sdh-alarm-turdi {
                 type empty;
                 description
                   "TU remote defect indicator alarm";
               }
               leaf sdh-alarm-tuuneq {
                 type empty;
                 description
                   "TU unequipped alarm";
               }
               leaf sdh-alarm-tumis {
                 type empty;
                 description
                   "TU label mismatch error";
               }
               leaf sdh-alarm-tuloc {
                 type empty;
                 description
                   "TU loss of cell delineation alarm";
               }
               leaf ds3-alarm-pll {
                 type empty;
                 description
                   "PLL lock alarm";
               }
               leaf ds3-alarm-ais {
                 type empty;
                 description
                   "AIS alarm";
               }
               leaf ds3-alarm-lof {
                 type empty;
                 description
                   "Loss of frame alarm";
               }
               leaf ds3-alarm-los {
                 type empty;
                 description
                   "Loss of signal alarm";
               }
               leaf ds3-alarm-lcv {
                 type empty;
                 description
                   "Line code violation alarm";
               }
               leaf ds3-alarm-exz {
                 type empty;
                 description
                   "Excessive zeros alarm";
               }
               leaf ds3-alarm-ferf {
                 type empty;
                 description
                   "Far-end receive failure alarm";
               }
               leaf ds3-alarm-ylw {
                 type empty;
                 description
                   "Yellow alarm";
               }
               leaf ds3-alarm-idle {
                 type empty;
                 description
                   "Idle alarm";
               }
               leaf ds1-alarm-ais {
                 type empty;
                 description
                   "AIS alarm";
               }
               leaf ds1-alarm-lof {
                 type empty;
                 description
                   "Loss of frame alarm";
               }
               leaf ds1-alarm-los {
                 type empty;
                 description
                   "Loss of signal alarm";
               }
               leaf ds1-alarm-ylw {
                 type empty;
                 description
                   "Yellow alarm";
               }
               leaf ds1-alarm-crc-major {
                 type empty;
                 description
                   "CRC errors crossed major threshold";
               }
               leaf ds1-alarm-crc-minor {
                 type empty;
                 description
                   "CRC errors crossed minor threshold";
               }
               leaf dsl-alarm-lof {
                 type empty;
                 description
                   "Loss of frame alarm";
               }
               leaf dsl-alarm-los {
                 type empty;
                 description
                   "Loss of signal alarm";
               }
               leaf dsl-alarm-lom {
                 type empty;
                 description
                   "Loss of multiframe alarm";
               }
               leaf dsl-alarm-locdi {
                 type empty;
                 description
                   "Loss of cell delineation alarm for interleaved channel";
               }
               leaf dsl-alarm-locdni {
                 type empty;
                 description
                   "Loss of cell delineation alarm for non-interleaved 
                   channel";
               }
               leaf dsl-alarm-lop {
                 type empty;
                 description
                   "Loss of power alarm";
               }
               leaf dsl-alarm-far-lof {
                 type empty;
                 description
                   "Far-end loss-of-frame alarm";
               }
               leaf dsl-alarm-far-los {
                 type empty;
                 description
                   "Far-end loss-of-signal alarm";
               }
               leaf dsl-alarm-far-locdi {
                 type empty;
                 description
                   "Far-end loss-of-cell-delineation alarm for interleaved 
                   channel";
               }
               leaf dsl-alarm-far-locdni {
                 type empty;
                 description
                   "Far-end loss-of-cell-delineation alarm for 
                   non-interleaved channel";
               }
               leaf fibrechannel-alarm-link-down {
                 type empty;
                 description
                   "Link alive failure";
               }
               leaf ethernet-alarm-link-down {
                 type empty;
                 description
                   "Link alive failure";
               }
               leaf ethernet-alarm-an-not-supported {
                 type empty;
                 description
                   "AN not supported";
               }
               leaf ethernet-alarm-link-local-fault {
                 type empty;
                 description
                   "Link local fault";
               }
               leaf ethernet-alarm-link-remote-fault {
                 type empty;
                 description
                   "Link remote fault";
               }
               leaf ethernet-alarm-link-local-degrade {
                 type empty;
                 description
                   "Link local degrade";
               }
               leaf ethernet-alarm-link-remote-degrade {
                 type empty;
                 description
                   "Link remote degrade";
               }
               leaf ethernet-alarm-lcdp {
                 type empty;
                 description
                   "Loss of code-group delineation";
               }
               leaf isdn-alarm-los {
                 type empty;
                 description
                   "Loss of signal alarm";
               }
               leaf isdn-alarm-lof {
                 type empty;
                 description
                   "Loss of frame alarm";
               }
               leaf shdsl-alarm-losd {
                 type empty;
                 description
                   "Loss of signal alarm";
               }
               leaf shdsl-alarm-losw {
                 type empty;
                 description
                   "Loss of sync word alarm";
               }
               leaf shdsl-alarm-line1-losd {
                 type empty;
                 description
                   "Loss of signal (line 1) alarm";
               }
               leaf shdsl-alarm-line1-losw {
                 type empty;
                 description
                   "Loss of sync word (line 1) alarm";
               }
               leaf shdsl-alarm-line2-losd {
                 type empty;
                 description
                   "Loss of signal (line 2) alarm";
               }
               leaf shdsl-alarm-line2-losw {
                 type empty;
                 description
                   "Loss of sync word (line 2) alarm";
               }
               leaf shdsl-efm-alarm-losd {
                 type empty;
                 description
                   "Loss of signal alarm";
               }
               leaf shdsl-efm-alarm-losw {
                 type empty;
                 description
                   "Loss of sync word alarm";
               }
               leaf otn-alarm-los {
                 type empty;
                 description
                   "Loss of signal alarm";
               }
               leaf otn-alarm-lof {
                 type empty;
                 description
                   "Loss of frame alarm";
               }
               leaf otn-alarm-lom {
                 type empty;
                 description
                   "Loss of multiframe alarm";
               }
               leaf otn-alarm-wavelength-lock {
                 type empty;
                 description
                   "Loss of Wavelength Lock alarm";
               }
               leaf otn-alarm-otu-ais {
                 type empty;
                 description
                   "OTU Alarm Indication Signal alarm";
               }
               leaf otn-alarm-otu-bdi {
                 type empty;
                 description
                   "OTU Background Block Error alarm";
               }
               leaf otn-alarm-otu-ttim {
                 type empty;
                 description
                   "OTU Trail Trace Identifier Mismatch alarm";
               }
               leaf otn-alarm-otu-iae {
                 type empty;
                 description
                   "OTU Incoming Alignment alarm";
               }
               leaf otn-alarm-otu-sd {
                 type empty;
                 description
                   "OTU Signal Degrade alarm";
               }
               leaf otn-alarm-otu-sf {
                 type empty;
                 description
                   "OTU Signal Fail alarm";
               }
               leaf otn-alarm-otu-biae {
                 type empty;
                 description
                   "OTU Backward Incoming Alignment alarm";
               }
               leaf otn-alarm-otu-tsf {
                 type empty;
                 description
                   "OTU Trail Signal Fail alarm";
               }
               leaf otn-alarm-otu-ssf {
                 type empty;
                 description
                   "OTU Server Signal Fail alarm";
               }
               leaf otn-alarm-otu-fec-excessive {
                 type empty;
                 description
                   "OTU FEC Excessive alarm";
               }
               leaf otn-alarm-otu-fec-degraded {
                 type empty;
                 description
                   "OTU FEC Degraded alarm";
               }
               leaf otn-alarm-otu-fe-fec-degraded {
                 type empty;
                 description
                   "OTU FE FEC Degraded/Excessive alarm";
               }
               leaf otn-alarm-otu-threshold-bbe {
                 type empty;
                 description
                   "OTU Background Block Error threshold alarm";
               }
               leaf otn-alarm-otu-threshold-es {
                 type empty;
                 description
                   "OTU Errored Seconds threshold alarm";
               }
               leaf otn-alarm-otu-threshold-ses {
                 type empty;
                 description
                   "OTU Severely Errored Seconds threshold alarm";
               }
               leaf otn-alarm-otu-threshold-uas {
                 type empty;
                 description
                   "OTU Unavailable Seconds threshold alarm";
               }
               leaf otn-alarm-odu-ais {
                 type empty;
                 description
                   "ODU  Alarm Indiaction Signal alarm";
               }
               leaf otn-alarm-odu-oci {
                 type empty;
                 description
                   "ODU Open Connection Indication alarm";
               }
               leaf otn-alarm-odu-lck {
                 type empty;
                 description
                   "ODU Locked alarm";
               }
               leaf otn-alarm-odu-bdi {
                 type empty;
                 description
                   "ODU Backward Defect Indication alarm";
               }
               leaf otn-alarm-odu-ttim {
                 type empty;
                 description
                   "ODU Trail Trace Identifier Mismatch alarm";
               }
               leaf otn-alarm-odu-sd {
                 type empty;
                 description
                   "ODU Signal Degrade alarm";
               }
               leaf otn-alarm-odu-sf {
                 type empty;
                 description
                   "ODU Signal Fail alarm";
               }
               leaf otn-alarm-odu-iae {
                 type empty;
                 description
                   "ODU Incoming Alignment alarm";
               }
               leaf otn-alarm-odu-ltc {
                 type empty;
                 description
                   "ODU Loss of Tandem Connection alarm";
               }
               leaf otn-alarm-odu-csf {
                 type empty;
                 description
                   "ODU Client Signal Fail alarm";
               }
               leaf otn-alarm-odu-tsf {
                 type empty;
                 description
                   "ODU Trail Signal Fail alarm";
               }
               leaf otn-alarm-odu-ssf {
                 type empty;
                 description
                   "ODU Server Signal Fail alarm";
               }
               leaf otn-alarm-odu-rx-aps-change {
                 type empty;
                 description
                   "ODU Rx Aps Change alarm";
               }
               leaf otn-alarm-odu-threshold-bbe {
                 type empty;
                 description
                   "ODU Background Block Error threshold alarm";
               }
               leaf otn-alarm-odu-threshold-es {
                 type empty;
                 description
                   "ODU Errored Seconds threshold alarm";
               }
               leaf otn-alarm-odu-threshold-ses {
                 type empty;
                 description
                   "ODU Severely Errored Seconds threshold alarm";
               }
               leaf otn-alarm-odu-threshold-uas {
                 type empty;
                 description
                   "ODU Unavailable Seconds threshold alarm";
               }
               leaf otn-alarm-opu-pmi {
                 type empty;
                 description
                   "OPU Payload Mismatch alarm";
               }
               leaf otn-alarm-pre-fec-sd {
                 type empty;
                 description
                   "Pre-FEC SD alarm";
               }
               leaf otn-alarm-fe-pre-fec-sd {
                 type empty;
                 description
                   "Far end pre-FEC SD alarm";
               }
               leaf optics-alarms-mod-fault {
                 type empty;
                 description
                   "Module Fault alarm";
               }
               leaf optics-alarms-lol {
                 type empty;
                 description
                   "Loss of Lock alarm";
               }
               leaf optics-alarms-los {
                 type empty;
                 description
                   "Loss of Signal alarms";
               }
               leaf optics-alarms-lof {
                 type empty;
                 description
                   "Loss of frame alarm";
               }
               leaf optics-alarms-lom {
                 type empty;
                 description
                   "Loss of multi-frame alarm";
               }
               leaf optics-alarms-otu-bdi {
                 type empty;
                 description
                   "Backward defect indiacation alarm";
               }
               leaf optics-alarms-rmsf {
                 type empty;
                 description
                   "Rx Modem sysnc fault alarm";
               }
               leaf optics-alarms-rmlol {
                 type empty;
                 description
                   "Rx Modem loss of lock alarm";
               }
               leaf optics-alarms-rloa {
                 type empty;
                 description
                   "Rx loss of alignment alarm";
               }
               leaf optics-alarms-mbclf {
                 type empty;
                 description
                   "Modulator Bias control loop fail alarm";
               }
               leaf optics-alarms-itlaf {
                 type empty;
                 description
                   "ITLA Fault alarm";
               }
               leaf optics-alarms-daccf {
                 type empty;
                 description
                   "DAC Calibration Fault alarm";
               }
               leaf optics-alarms-adccf {
                 type empty;
                 description
                   "ADC Calibration Fault alarm";
               }
               leaf optics-alarms-fec-degrade {
                 type empty;
                 description
                   "FEC Degrade alarm";
               }
               leaf optics-alarms-fec-excessive {
                 type empty;
                 description
                   "FEC Excessive alarm";
               }
               leaf optics-alarms-fe-fec-degrade {
                 type empty;
                 description
                   "Far-end FEC Degrade alarm";
               }
               leaf optics-alarms-fe-fec-excessive {
                 type empty;
                 description
                   "Far-end FEC Excessive alarm";
               }
               leaf ima-alarm-startup-fe {
                 type empty;
                 description
                   "IMA group startup far-end alarm";
               }
               leaf ima-alarm-config-abort {
                 type empty;
                 description
                   "IMA group config abort alarm";
               }
               leaf ima-alarm-config-abort-fe {
                 type empty;
                 description
                   "IMA group config abort far-end alarm";
               }
               leaf ima-alarm-insufficient-links {
                 type empty;
                 description
                   "IMA group insufficient links alarm";
               }
               leaf ima-alarm-insufficient-links-fe {
                 type empty;
                 description
                   "IMA group insufficient links far-end alarm";
               }
               leaf ima-alarm-blocked {
                 type empty;
                 description
                   "IMA group blocked alarm";
               }
               leaf ima-alarm-blocked-fe {
                 type empty;
                 description
                   "IMA group blocked far-end alarm";
               }
               leaf ima-alarm-timing-mismatch {
                 type empty;
                 description
                   "IMA group timing mismatch alarm";
               }
               leaf ima-alarm-version-mismatch {
                 type empty;
                 description
                   "IMA group version mismatch alarm";
               }
               leaf ima-alarm-lif {
                 type empty;
                 description
                   "IMA link loss of IMA frame alarm";
               }
               leaf ima-alarm-lods {
                 type empty;
                 description
                   "IMA link out of delay synchronization alarm";
               }
               leaf ima-alarm-rdi {
                 type empty;
                 description
                   "IMA link remote defect indicator alarm";
               }
               leaf ima-alarm-tx-misconnected {
                 type empty;
                 description
                   "IMA link tx misconnected alarm";
               }
               leaf ima-alarm-rx-misconnected {
                 type empty;
                 description
                   "IMA link rx misconnected alarm";
               }
               leaf ima-alarm-fault {
                 type empty;
                 description
                   "IMA link fault alarm";
               }
               leaf ima-alarm-tx-unusable-fe {
                 type empty;
                 description
                   "IMA link Tx unusable far-end alarm";
               }
               leaf ima-alarm-rx-unusable-fe {
                 type empty;
                 description
                   "IMA link Tx unusable far-end alarm";
               }
               leaf generic-value {
                 type int32;
                 description
                   "Hexadecimal value of unknown flag bits";
               }
             }
           }
           container sonet-errors {
             list media-alarm {
               leaf media-alarm-name {
                 type string;
               }
               leaf media-alarm-count {
                 type int32;
               }
             }
           }
           container sonet-physical-information {
             list media-alarm {
               leaf media-alarm-name {
                 type string;
               }
               leaf media-alarm-seconds {
                 type int32;
               }
               leaf media-alarm-count {
                 type int32;
               }
               leaf media-alarm-state {
                 type string;
               }
             }
           }
           container sonet-section-information {
             list media-alarm {
               leaf media-alarm-name {
                 type string;
               }
               leaf media-alarm-seconds {
                 type int32;
               }
               leaf media-alarm-count {
                 type int32;
               }
               leaf media-alarm-state {
                 type string;
               }
             }
           }
           container sonet-line-information {
             list media-alarm {
               leaf media-alarm-name {
                 type string;
               }
               leaf media-alarm-seconds {
                 type int32;
               }
               leaf media-alarm-count {
                 type int32;
               }
               leaf media-alarm-state {
                 type string;
               }
             }
           }
           container sonet-path-information {
             list media-alarm {
               leaf media-alarm-name {
                 type string;
               }
               leaf media-alarm-seconds {
                 type int32;
               }
               leaf media-alarm-count {
                 type int32;
               }
               leaf media-alarm-state {
                 type string;
               }
             }
           }
           container sonet-payload-pointer-information {
             leaf sonet-payload-pointer-curptr {
               type string;
               description
                 "Value of the SONET/SDH payload pointer, derived from the 
                 H1 and H2 overhead bytes";
             }
             leaf sonet-payload-pointer-ptrinc-count {
               type string;
               description
                 "Number of times the value of the SONET/SDH payload pointer
                 had positive justification";
             }
             leaf sonet-payload-pointer-ptrdec-count {
               type string;
               description
                 "Number of times the value of the SONET/SDH payload pointer
                 had negative justification";
             }
             leaf sonet-payload-pointer-newptr-ndf-count {
               type string;
               description
                 "Number of times a new payload pointer was created with the
                 New Data Found flag set";
             }
           }
           container sonet-vt-information {
             list media-alarm {
               leaf media-alarm-name {
                 type string;
               }
               leaf media-alarm-seconds {
                 type int32;
               }
               leaf media-alarm-count {
                 type int32;
               }
               leaf media-alarm-state {
                 type string;
               }
             }
           }
           container optics-diagnostics {
             description
               "Optics diagnostics";
             leaf output-power {
               type string;
               description
                 "Output power (milliwatts)";
             }
             leaf output-power-dbm {
               type string;
               description
                 "Output power (dBm)";
             }
             leaf input-power {
               type string;
               description
                 "Input power (milliwatts)";
             }
             leaf input-power-dbm {
               type string;
               description
                 "Input power (dBm)";
             }
             leaf per-wave-rx-optical-power {
               type string;
               description
                 "Per-wavelength receiver optical power (milliwatts)";
             }
             leaf per-wave-rx-optical-power-dbm {
               type string;
               description
                 "Per-wavelength receiver optical power (dBm)";
             }
             leaf lane-laser-frequency-error {
               type string;
               description
                 "Lane laser frequency error (MHz)";
             }
             leaf tec-current {
               type string;
               description
                 "Tec current";
             }
             leaf residual-isi {
               type string;
               description
                 "Residual ISI";
             }
             container optics-diagnostics-ot {
               description
                 "OT interface optics diagnostics";
               leaf module-temp-fault {
                 type string;
                 description
                   "Module temperature fault";
               }
               leaf specific-hw-fault {
                 type string;
                 description
                   "Specific HW fault";
               }
               leaf internal-power-fault {
                 type string;
                 description
                   "Internal power fault";
               }
               leaf post-therm-fault {
                 type string;
                 description
                   "Power thermal fault";
               }
               leaf post-fault {
                 type string;
                 description
                   "Post fault";
               }
               leaf command-error {
                 type string;
                 description
                   "Command error";
               }
               leaf rx-pll-lock {
                 type string;
                 description
                   "RX PLL lock";
               }
               leaf network-lane-los {
                 type string;
                 description
                   "Network Lane LOS";
               }
               leaf network-lane-lof {
                 type string;
                 description
                   "Network Lane LOF";
               }
               leaf network-lane-oof {
                 type string;
                 description
                   "Network Lane OOF";
               }
               leaf network-lane-lom {
                 type string;
                 description
                   "Network Lane LOM";
               }
               leaf network-lane-oom {
                 type string;
                 description
                   "Network Lane OOM";
               }
               leaf network-lane-otu-bdi {
                 type string;
                 description
                   "Network Lane OTU BDI";
               }
               leaf lane-rx-fifo-error {
                 type string;
                 description
                   "Lane RX FIFO error";
               }
               leaf tx-reference-clock-fault {
                 type string;
                 description
                   "TX reference clock fault";
               }
               leaf rx-modem-sync-fault {
                 type string;
                 description
                   "Rx modem sync fault";
               }
               leaf rx-modem-loss-of-lock {
                 type string;
                 description
                   "RX modem loss of lock";
               }
               leaf rx-loss-of-alignment {
                 type string;
                 description
                   "RX loss of alignment";
               }
               leaf rx-out-of-alignment {
                 type string;
                 description
                   "RX out of alignment";
               }
               leaf rx-timing-fault {
                 type string;
                 description
                   "Rx timing fault";
               }
               leaf link-msg-data-available {
                 type string;
                 description
                   "Link msg data available";
               }
               leaf modulator-bias-control-loop-fail {
                 type string;
                 description
                   "Modulator Bias Control Loop Fail";
               }
               leaf itla-fault {
                 type string;
                 description
                   "ITLA fault";
               }
               leaf dac-calib-fault {
                 type string;
                 description
                   "DAC calib fault";
               }
               leaf adc-calib-fault {
                 type string;
                 description
                   "ADC calib fault";
               }
               leaf prom-fault {
                 type string;
                 description
                   "PROM fault";
               }
               leaf tx-mod-bias-voa-ctrl-loop-high-alarm {
                 type string;
                 description
                   "TX mod bias VOA ctrl loop high alarm";
               }
               leaf tx-mod-bias-voa-ctrl-loop-low-alarm {
                 type string;
                 description
                   "TX mod bias VOA ctrl loop low alarm";
               }
               leaf rx-phase-control-loop-high-alarm {
                 type string;
                 description
                   "RX phase control loop high alarm";
               }
               leaf rx-phase-control-loop-low-alarm {
                 type string;
                 description
                   "RX phase control loop low alarm";
               }
               leaf rx-phase-control-loop-high-warning {
                 type string;
                 description
                   "RX phase control loop high warning";
               }
               leaf rx-phase-control-loop-low-warning {
                 type string;
                 description
                   "RX phase control loop low warning";
               }
               leaf oa-pump-bias-current-high-alarm {
                 type string;
                 description
                   "OA pump bias current high alarm";
               }
               leaf oa-pump-bias-current-low-alarm {
                 type string;
                 description
                   "OA pump bias current low alarm";
               }
               leaf oa-pump-bias-current-high-warning {
                 type string;
                 description
                   "OA pump bias current high warning";
               }
               leaf oa-pump-bias-current-low-warning {
                 type string;
                 description
                   "OA pump bias current low warning";
               }
               leaf tx-jitter-pll-lol-input-nw-lane {
                 type string;
                 description
                   "Tx jitter PLL LOL i/p nw lane";
               }
               leaf tx-out-of-alignment {
                 type string;
                 description
                   "TX out of alignment";
               }
               leaf tx-cmu-lock-fault {
                 type string;
                 description
                   "Tx CMU lock fault";
               }
               leaf adc-signal-below-threshold {
                 type string;
                 description
                   "ADC signal below threshold";
               }
               leaf tx-output-power-adjustment-fault {
                 type string;
                 description
                   "Tx output power adjustment fault";
               }
               leaf tx-output-mod-converge-fault {
                 type string;
                 description
                   "TX output mod converge fault";
               }
               leaf tx-laser-ready-fault {
                 type string;
                 description
                   "Tx laser ready fault";
               }
               leaf tx-laser-ready-off-fault {
                 type string;
                 description
                   "Tx laser ready off fault";
               }
               leaf tx-asic-ready-fault {
                 type string;
                 description
                   "Tx asic ready fault";
               }
               leaf tx-initialization-fault {
                 type string;
                 description
                   "Tx initialization fault";
               }
               leaf rx-demodulator-lock-fault {
                 type string;
                 description
                   "Rx demodulator lock fault";
               }
               leaf rx-dispersion-lock-fault {
                 type string;
                 description
                   "Rx dispersion lock fault";
               }
               leaf rx-adc-output-fault {
                 type string;
                 description
                   "Rx ADC output fault";
               }
               leaf rx-optical-input-fault {
                 type string;
                 description
                   "Rx optical input fault";
               }
               leaf rx-asic-ready-fault {
                 type string;
                 description
                   "Rx asic ready fault";
               }
               leaf rx-initialization-fault {
                 type string;
                 description
                   "Rx initialization fault";
               }
               leaf tx-mod-bias-high-alarm {
                 type string;
                 description
                   "TX modulator bias high alarm";
               }
               leaf tx-mod-bias-low-alarm {
                 type string;
                 description
                   "TX modulator bias low alarm";
               }
               leaf tx-mod-bias-high-warning {
                 type string;
                 description
                   "TX modulator bias high warning";
               }
               leaf tx-mod-bias-low-warning {
                 type string;
                 description
                   "TX modulator bias low warning";
               }
               leaf rx-pwr-high-alarm {
                 type string;
                 description
                   "RX power high alarm";
               }
               leaf rx-pwr-low-alarm {
                 type string;
                 description
                   "RX power low alarm";
               }
               leaf rx-pwr-high-warn {
                 type string;
                 description
                   "RX power high warning";
               }
               leaf rx-pwr-low-warn {
                 type string;
                 description
                   "RX power low warning";
               }
               leaf tx-laser-power-high-alarm {
                 type string;
                 description
                   "TX laser power high alarm";
               }
               leaf tx-laser-power-low-alarm {
                 type string;
                 description
                   "TX laser power low alarm";
               }
               leaf tx-laser-power-high-warn {
                 type string;
                 description
                   "TX laser power high warning";
               }
               leaf tx-laser-power-low-warn {
                 type string;
                 description
                   "TX laser power low warning";
               }
               leaf tx-bias-high-alarm {
                 type string;
                 description
                   "TX laser current high alarm";
               }
               leaf tx-bias-low-alarm {
                 type string;
                 description
                   "TX laser current low alarm";
               }
               leaf tx-bias-high-warn {
                 type string;
                 description
                   "TX laser current high warning";
               }
               leaf tx-bias-low-warn {
                 type string;
                 description
                   "TX laser current low warning";
               }
               leaf tx-laser-temp-high-alarm {
                 type string;
                 description
                   "TX laser temperature high alarm";
               }
               leaf tx-laser-temp-low-alarm {
                 type string;
                 description
                   "TX laser temperature low alarm";
               }
               leaf tx-laser-temp-high-warn {
                 type string;
                 description
                   "TX laser temperature high warning";
               }
               leaf tx-laser-temp-low-warn {
                 type string;
                 description
                   "TX laser temperature low warning";
               }
             }
             list optics-diagnostics-lane-values {
               key "lane-index";
               leaf lane-index {
                 type int32;
               }
               leaf laser-bias-current {
                 type string;
                 description
                   "Laser bias current (milliamperes)";
               }
               leaf laser-bias-current-not-available {
                 type string;
                 description
                   "Laser bias current measurement not available";
               }
               leaf laser-output-power {
                 type string;
                 description
                   "Laser output power (milliwatts)";
               }
               leaf laser-output-power-dbm {
                 type string;
                 description
                   "Laser output power (dBm)";
               }
               leaf output-power {
                 type string;
                 description
                   "Output power (milliwatts)";
               }
               leaf output-power-dbm {
                 type string;
                 description
                   "Output power (dBm)";
               }
               leaf laser-temperature {
                 type string;
                 description
                   "Laser temperature";
               }
               leaf laser-module-temperature {
                 type string;
                 description
                   "Module temperature";
               }
               leaf laser-tx-optical-power {
                 type string;
                 description
                   "Laser transmitter optical power (milliwatts)";
               }
               leaf laser-tx-optical-power-dbm {
                 type string;
                 description
                   "Laser transmitter optical power (dBm)";
               }
               leaf laser-rx-optical-power {
                 type string;
                 description
                   "Laser receiver optical power (milliwatts)";
               }
               leaf laser-rx-optical-power-dbm {
                 type string;
                 description
                   "Laser receiver optical power (dBm)";
               }
               leaf input-power {
                 type string;
                 description
                   "Input power (milliwatts)";
               }
               leaf input-power-dbm {
                 type string;
                 description
                   "Input power (dBm)";
               }
               leaf input-total-power {
                 type string;
                 description
                   "Input power (total) (milliwatts)";
               }
               leaf input-total-power-dbm {
                 type string;
                 description
                   "Input power (dBm)";
               }
               leaf per-wave-rx-optical-power {
                 type string;
                 description
                   "Per-wavelength receiver optical power (milliwatts)";
               }
               leaf per-wave-rx-optical-power-dbm {
                 type string;
                 description
                   "Per-wavelength receiver optical power (dBm)";
               }
               leaf lane-configured-cd {
                 type string;
                 description
                   "Lane configured chromatic dispersion (ps/nm)";
               }
               leaf lane-chromatic-dispersion {
                 type string;
                 description
                   "Lane chromatic dispersion (ps/nm)";
               }
               leaf lane-avg-chromatic-dispersion {
                 type string;
                 description
                   "Lane avg chromatic dispersion (ps/nm)";
               }
               leaf lane-min-chromatic-dispersion {
                 type string;
                 description
                   "Lane min chromatic dispersion (ps/nm)";
               }
               leaf lane-max-chromatic-dispersion {
                 type string;
                 description
                   "Lane max chromatic dispersion (ps/nm)";
               }
               leaf lane-differential-group-delay {
                 type string;
                 description
                   "Lane differential group delay (ps)";
               }
               leaf lane-avg-differential-group-delay {
                 type string;
                 description
                   "Lane avg differential group delay (ps)";
               }
               leaf lane-min-differential-group-delay {
                 type string;
                 description
                   "Lane min differential group delay (ps)";
               }
               leaf lane-max-differential-group-delay {
                 type string;
                 description
                   "Lane max differential group delay (ps)";
               }
               leaf lane-sopmd {
                 type string;
                 description
                   "Lane sopmd";
               }
               leaf lane-avg-sopmd {
                 type string;
                 description
                   "Lane avg sopmd";
               }
               leaf lane-min-sopmd {
                 type string;
                 description
                   "Lane min sopmd";
               }
               leaf lane-max-sopmd {
                 type string;
                 description
                   "Lane max sopmd";
               }
               leaf q-factor {
                 type string;
                 description
                   "Lane q-factor";
               }
               leaf q-factor-not-available {
                 type string;
                 description
                   "Lane q-factor not available";
               }
               leaf q-margin {
                 type string;
                 description
                   "Lane q-margin";
               }
               leaf q-margin-not-available {
                 type string;
                 description
                   "Lane q-margin not available";
               }
               leaf lane-state-of-polarization {
                 type string;
                 description
                   "Lane state of polarization (rad/s)";
               }
               leaf lane-avg-state-of-polarization {
                 type string;
                 description
                   "Lane avg state of polarization (rad/s)";
               }
               leaf lane-min-state-of-polarization {
                 type string;
                 description
                   "Lane min state of polarization (rad/s)";
               }
               leaf lane-max-state-of-polarization {
                 type string;
                 description
                   "Lane max state of polarization (rad/s)";
               }
               leaf lane-polarization-dependent-loss {
                 type string;
                 description
                   "Lane polarization dependent loss (dB)";
               }
               leaf lane-avg-polarization-dependent-loss {
                 type string;
                 description
                   "Lane avg polarization dependent loss (dB)";
               }
               leaf lane-min-polarization-dependent-loss {
                 type string;
                 description
                   "Lane min polarization dependent loss (dB)";
               }
               leaf lane-max-polarization-dependent-loss {
                 type string;
                 description
                   "Lane max polarization dependent loss (dB)";
               }
               leaf lane-q2-factor {
                 type string;
                 description
                   "Lane Q2 factor (dB)";
               }
               leaf lane-q-value {
                 type string;
                 description
                   "Lane q value (dB)";
               }
               leaf lane-avg-q-value {
                 type string;
                 description
                   "Lane avg q value (dB)";
               }
               leaf lane-min-q-value {
                 type string;
                 description
                   "Lane min q value (dB)";
               }
               leaf lane-max-q-value {
                 type string;
                 description
                   "Lane max q value (dB)";
               }
               leaf lane-carrier-frequency-offset {
                 type string;
                 description
                   "Lane carrier frequency offset (MHz)";
               }
               leaf lane-avg-carrier-frequency-offset {
                 type string;
                 description
                   "Lane avg carrier frequency offset (MHz)";
               }
               leaf lane-min-carrier-frequency-offset {
                 type string;
                 description
                   "Lane min carrier frequency offset (MHz)";
               }
               leaf lane-max-carrier-frequency-offset {
                 type string;
                 description
                   "Lane max carrier frequency offset (MHz)";
               }
               leaf lane-electrical-snr {
                 type string;
                 description
                   "Lane electrical SNR (dB)";
               }
               leaf lane-snr {
                 type string;
                 description
                   "Lane snr (dB)";
               }
               leaf lane-avg-snr {
                 type string;
                 description
                   "Lane avg snr (dB)";
               }
               leaf lane-min-snr {
                 type string;
                 description
                   "Lane min snr (dB)";
               }
               leaf lane-max-snr {
                 type string;
                 description
                   "Lane max snr (dB)";
               }
               leaf lane-rx-laser-bias {
                 type string;
                 description
                   "Lane rx laser bias (mA)";
               }
               leaf lane-rx-laser-power {
                 type string;
                 description
                   "Lane rx laser power (dBm)";
               }
               leaf lane-rx-laser-temp {
                 type string;
                 description
                   "Lane rx laser temp (C)";
               }
               leaf lane-tx-modulator-bias-x-i {
                 type string;
                 description
                   "Lane tx modulator bias x i (mV)";
               }
               leaf lane-tx-modulator-bias-x-q {
                 type string;
                 description
                   "Lane tx modulator bias x q (mV)";
               }
               leaf lane-tx-modulator-bias-y-i {
                 type string;
                 description
                   "Lane tx modulator bias y i (mV)";
               }
               leaf lane-tx-modulator-bias-y-q {
                 type string;
                 description
                   "Lane tx modulator bias y q (mV)";
               }
               leaf lane-tx-modulator-bias-x-phase {
                 type string;
                 description
                   "Lane tx modulator bias x phase (mV)";
               }
               leaf lane-tx-modulator-bias-y-phase {
                 type string;
                 description
                   "Lane tx modulator bias y phase (mV)";
               }
               leaf tx-input-equalization {
                 type string;
                 description
                   "Tx input equalization";
               }
               leaf rx-output-amplitude {
                 type string;
                 description
                   "Rx output amplitude";
               }
               leaf rx-output-pre-emphasis {
                 type string;
                 description
                   "Rx output pre epmhasis";
               }
               leaf lane-laser-frequency-error {
                 type string;
                 description
                   "Lane laser frequency error (MHz)";
               }
               leaf tec-current {
                 type string;
                 description
                   "Tec current";
               }
               leaf residual-isi {
                 type string;
                 description
                   "Residual ISI";
               }
               leaf pam-histogram {
                 type string;
                 description
                   "PAM histogram";
               }
               leaf laser-bias-current-high-alarm {
                 type string;
                 description
                   "Laser bias current high alarm";
               }
               leaf laser-bias-current-low-alarm {
                 type string;
                 description
                   "Laser bias current low alarm";
               }
               leaf laser-bias-current-high-warn {
                 type string;
                 description
                   "Laser bias current high warning";
               }
               leaf laser-bias-current-low-warn {
                 type string;
                 description
                   "Laser bias current low warning";
               }
               leaf laser-tx-power-high-alarm {
                 type string;
                 description
                   "Laser output power high alarm";
               }
               leaf laser-tx-power-low-alarm {
                 type string;
                 description
                   "Laser output power low alarm";
               }
               leaf laser-tx-power-high-warn {
                 type string;
                 description
                   "Laser output power high warning";
               }
               leaf laser-tx-power-low-warn {
                 type string;
                 description
                   "Laser output power low warning";
               }
               leaf tx-power-high-alarm {
                 type string;
                 description
                   "Tx power high alarm";
               }
               leaf tx-power-low-alarm {
                 type string;
                 description
                   "Tx power low alarm";
               }
               leaf tx-power-high-warn {
                 type string;
                 description
                   "Tx power high warning";
               }
               leaf tx-power-low-warn {
                 type string;
                 description
                   "Tx power low warning";
               }
               leaf laser-temp-high-alarm {
                 type string;
                 description
                   "Laser temperature high alarm";
               }
               leaf laser-temp-low-alarm {
                 type string;
                 description
                   "Laser temperature low alarm";
               }
               leaf laser-temp-high-warn {
                 type string;
                 description
                   "Laser temperature high warning";
               }
               leaf laser-temp-low-warn {
                 type string;
                 description
                   "Laser temperature low warning";
               }
               leaf laser-rx-power-high-alarm {
                 type string;
                 description
                   "Laser receiver power high alarm";
               }
               leaf laser-rx-power-low-alarm {
                 type string;
                 description
                   "Laser receiver power low alarm";
               }
               leaf laser-rx-power-high-warn {
                 type string;
                 description
                   "Laser receiver power high warning";
               }
               leaf laser-rx-power-low-warn {
                 type string;
                 description
                   "Laser receiver power low warning";
               }
               leaf rx-power-high-alarm {
                 type string;
                 description
                   "Receiver power high alarm";
               }
               leaf rx-power-low-alarm {
                 type string;
                 description
                   "Receiver power low alarm";
               }
               leaf rx-power-high-warn {
                 type string;
                 description
                   "Receiver power high warning";
               }
               leaf rx-power-low-warn {
                 type string;
                 description
                   "Receiver power low warning";
               }
               leaf tx-loss-of-signal-functionality-alarm {
                 type string;
                 description
                   "Tx loss of signal functionality alarm";
               }
               leaf rx-loss-of-signal-functionality-alarm {
                 type string;
                 description
                   "Rx loss of signal functionality alarm";
               }
               leaf tx-cdr-loss-of-lock-alarm {
                 type string;
                 description
                   "Tx CDR loss of lock alarm";
               }
               leaf tx-loss-of-signal-alarm {
                 type string;
                 description
                   "Transmitter loss of signal alarm";
               }
               leaf rx-loss-of-signal-alarm {
                 type string;
                 description
                   "Receiver loss of signal alarm";
               }
               leaf tx-laser-disabled-alarm {
                 type string;
                 description
                   "Tx laser disabled alarm";
               }
               leaf rx-cdr-loss-of-lock-alarm {
                 type string;
                 description
                   "Receiver CDR loss of lock alarm";
               }
               leaf tec-fault-alarm {
                 type string;
                 description
                   "TEC fault alarm";
               }
               leaf wavelength-unlocked-alarm {
                 type string;
                 description
                   "Wavelength unlocked alarm";
               }
               leaf apd-supply-fault-alarm {
                 type string;
                 description
                   "APD supply fault alarm";
               }
               leaf tx-channel-disabled-alarm {
                 type string;
                 description
                   "Tx channel disabled alarm";
               }
               leaf rx-channel-disabled-alarm {
                 type string;
                 description
                   "Rx channel disabled alarm";
               }
               leaf tx-output-disabled-alarm {
                 type string;
                 description
                   "Rx laser disabled alarm";
               }
               leaf rx-output-disabled-alarm {
                 type string;
                 description
                   "Rx laser disabled alarm";
               }
               leaf tx-squelch-disabled-alarm {
                 type string;
                 description
                   "Tx squelch disabled alarm";
               }
               leaf rx-squelch-disabled-alarm {
                 type string;
                 description
                   "Rx squelch disabled alarm";
               }
               leaf laser-end-of-life-alarm {
                 type string;
                 description
                   "Laser end-of-life alarm";
               }
               leaf lane-cd {
                 type string;
                 description
                   "Lane chromatic dispersion";
               }
               leaf lane-dgd {
                 type string;
                 description
                   "Lane differential group delay";
               }
               leaf lane-cfo {
                 type string;
                 description
                   "Lane carrier frequency offset";
               }
               leaf lane-pdl {
                 type string;
                 description
                   "Lane polarization dependent loss";
               }
               leaf lane-osnr {
                 type string;
                 description
                   "Optical signal-to-noise ratio(dB)";
               }
             }
           }
           list optics-chromatics {
             key "optics-chromatic-diagnostics-support";
             leaf optics-chromatic-diagnostics-support {
               type string;
               description
                 "Optics chromatic not supported for interface";
             }
             leaf opticstype {
               type string;
               description
                 "Type of optical module";
             }
             list optics-chromatic {
               key "supported-cd supported-mediaid";
               leaf supported-speed {
                 type string;
                 description
                   "Supported Speed";
               }
               leaf supported-cd {
                 type string;
                 description
                   "Supported Chromatic Dispersion";
               }
               leaf supported-distance {
                 type string;
                 description
                   "Supported Distance";
               }
               leaf supported-mediaid {
                 type string;
                 description
                   "Supported Mediaid";
               }
             }
           }
         }
       }
       container src-information {
         leaf src-chassis-name {
           type string;
           description
             "Source chassis name";
         }
         leaf src-fpc {
           type int32;
           description
             "Source FPC";
         }
         leaf-list src-pfe-id {
           type int32;
           description
             "Source PFE id";
         }
       }
       container macsec-statistics {
         description
           "MACSec Statistics ";
         leaf macsec-tx-sc-protected {
           type int32;
           description
             "Protected Secure Channel MACSec packets transmitted";
         }
         leaf macsec-tx-sc-encrypted {
           type int32;
           description
             "Encrypted Secure Channel MACSec packets transmitted";
         }
         leaf macsec-tx-sc-protectedbytes {
           type int32;
           description
             "Protected Secure Channel MACSec bytes transmitted";
         }
         leaf macsec-tx-sc-encryptedbytes {
           type int32;
           description
             "Encrypted Secure Channel MACSec bytes transmitted";
         }
         leaf macsec-rx-sc-ok {
           type int32;
           description
             "OK Secure Association MACSec packets received";
         }
         leaf macsec-rx-sc-validatedbytes {
           type int32;
           description
             "Validated Secure Association MACSec bytes received";
         }
         leaf macsec-rx-sc-decryptedbytes {
           type int32;
           description
             "Validated Secure Association MACSec bytes received";
         }
       }
       container peer-configuration-status {
         description
           "Nonmatching DCE end DLCIs";
         leaf peer-nonmatching-dlci {
           type int32;
           description
             "DCE end DLCIs that does not match the DTE";
         }
       }
       container lmi-statistics {
         description
           "LMI statistics for an interface";
         leaf lmi-statistics-dte-descriptor {
           type string;
           description
             "DTE interface statistics";
         }
         leaf lmi-enquiries-sent {
           type int32;
           description
             "Number of enquiry packets sent";
         }
         leaf lmi-full-enquiries-sent {
           type int32;
           description
             "Number of full enquiry packets sent";
         }
         leaf lmi-enquiry-responses-received {
           type int32;
           description
             "Number of enquiry response packets received";
         }
         leaf lmi-full-enquiry-responses-received {
           type int32;
           description
             "Number of full enquiry packets received";
         }
         leaf lmi-statistics-dce-descriptor {
           type string;
           description
             "DCE interface statistics";
         }
         leaf lmi-enquiries-received {
           type int32;
           description
             "Number of enquiry packets received";
         }
         leaf lmi-full-enquiries-received {
           type int32;
           description
             "Number of full enquiry packets received";
         }
         leaf lmi-enquiry-responses-sent {
           type int32;
           description
             "Number of enquiry response packets sent";
         }
         leaf lmi-full-enquiry-responses-sent {
           type int32;
           description
             "Number of full enquiry response packets sent";
         }
         leaf lmi-statistics-common-descriptor {
           type string;
           description
             "Statistics common to DTE and DCE";
         }
         leaf lmi-unknown-messages-received {
           type int32;
           description
             "Number of packets received that do not contain valid messages";
         }
         leaf lmi-asynchronous-updates-received {
           type int32;
           description
             "Number of ifstate change updates received";
         }
         leaf lmi-out-of-sequence {
           type int32;
           description
             "Number of packets received in unexpected sequence";
         }
         leaf lmi-keepalive-responses-timeout {
           type int32;
           description
             "Number of times, the timer for keepalive packets expired";
         }
       }
       container lsi-traffic-statistics {
         leaf input-bytes {
           type int32;
         }
         leaf input-bps {
           type int32;
         }
         leaf input-packets {
           type uint64;
         }
         leaf input-pps {
           type int32;
         }
       }
       container stp-traffic-statistics {
         leaf stp-input-bytes-dropped {
           type int32;
           description
             "Drop statistics due to stp state at ingress in bytes";
         }
         leaf stp-output-bytes-dropped {
           type int32;
           description
             "Drop statistics due to stp state at egress in bytes";
         }
         leaf stp-input-packets-dropped {
           type int32;
           description
             "Drop statistics due to stp state at ingress in packets";
         }
         leaf stp-output-packets-dropped {
           type int32;
           description
             "Drop statistics due to stp state at egress in packets";
         }
       }
       container ethernet-rpf-counter-stats {
         leaf ethernet-rpf-ipv4-rpf-bytes {
           type int32;
           description
             "Counter for ipv4 rpf byptes";
         }
         leaf ethernet-rpf-ipv4-rpf-packets {
           type int32;
           description
             "Counter for ipv4 rpf packets";
         }
         leaf ethernet-rpf-ipv6-rpf-bytes {
           type int32;
           description
             "Counter for ipv6 rpf byptes";
         }
         leaf ethernet-rpf-ipv6-rpf-packets {
           type int32;
           description
             "Counter for ipv6 rpf packets";
         }
       }
       container af-info {
         leaf af-bw {
           type string;
         }
         leaf af-gnf-id {
           type string;
         }
         leaf af-collapsed-fwd-mode {
           type string;
         }
       }
       container af-fe-info {
         list fe-info {
           leaf fe-num {
             type string;
           }
           leaf fe-bw {
             type string;
           }
           leaf fe-state {
             type string;
           }
         }
       }
       container af-fe-lb-stats-info {
         list fe-info {
           leaf fe-num {
             type string;
           }
           leaf fe-bw {
             type string;
           }
           leaf fe-state {
             type string;
           }
           leaf fe-tx-packets {
             type uint64;
           }
           leaf fe-tx-bytes {
             type uint64;
           }
         }
       }
       list af-fe-res-info {
         leaf fe-res-tx-packets {
           type uint64;
         }
         leaf fe-res-tx-bytes {
           type uint64;
         }
       }
       container af-fe-q-pkts {
         list fe-q-pkts-info {
           leaf fe-number {
             type string;
           }
           leaf fe-high-tx-packets {
             type uint64;
           }
           leaf fe-low-tx-packets {
             type uint64;
           }
         }
       }
       container af-fe-q-bytes {
         list fe-q-bytes-info {
           leaf fe-number {
             type string;
           }
           leaf fe-high-tx-bytes {
             type uint64;
           }
           leaf fe-low-tx-bytes {
             type uint64;
           }
         }
       }
       list af-fe-q-res-pkts {
         leaf fe-res-high-tx-packets {
           type uint64;
         }
         leaf fe-res-low-tx-packets {
           type uint64;
         }
       }
       list af-fe-q-res-bytes {
         leaf fe-res-high-tx-bytes {
           type uint64;
         }
         leaf fe-res-low-tx-bytes {
           type uint64;
         }
       }
       list af-collapsed-fwd-stats-mode-disp {
         leaf af-collapsed-fwd-mode-disp {
           type string;
         }
       }
       list af-collapsed-fwd-stats-pkts {
         leaf af-optimal-packets {
           type uint64;
         }
         leaf af-non-optimal-packets {
           type uint64;
         }
       }
       list af-collapsed-fwd-stats-bytes {
         leaf af-optimal-bytes {
           type uint64;
         }
         leaf af-non-optimal-bytes {
           type uint64;
         }
       }
       list queue-num-forwarding-class-name-map {
         key "queue-number";
         leaf queue-number {
           type uint32;
           description
             "Queue number";
         }
         leaf forwarding-class-name {
           type string;
           description
             "Forwarding class name associated with queue";
         }
       }
       container chassis-queue-counters {
         description
           "Chassis queue counter statistics";
         container interface-chassis-cos-summary {
           description
             "Packet Forwarding Engine chassis forwarding class and queue 
             information for an interface";
           leaf intf-cos-chassis-num-queues-supported {
             type int32;
             description
               "Number of Packet Forwarding Engine chassis queues the 
               interface supports";
           }
           leaf intf-cos-chassis-num-queues-in-use {
             type int32;
             description
               "Number of Packet Forwarding Engine chassis queues in use on 
               the interface";
           }
         }
         list queue {
           key "queue-number";
           description
             "Counters for a single queue";
           leaf queue-number {
             type uint32;
             description
               "Queue number";
           }
           leaf forwarding-class-name {
             type string;
             description
               "Forwarding class name associated with queue";
           }
           leaf queue-counters-queued-packets {
             type int32;
             description
               "Queued packet count";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-queued-packets-na {
             type string;
             description
               "Queued packets not available";
           }
           leaf queue-counters-queued-bytes-na {
             type string;
             description
               "Queued bytes not available";
           }
           leaf queue-counters-trans-packets {
             type int32;
             description
               "Total number of transmitted packets";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets-na {
             type string;
             description
               "Number of packets dropped due to tail drop not available";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of packets dropped at tail drop of the queue";
           }
           leaf queue-counters-tail-drop-bytes-rate {
             type int32;
             description
               "Number of packets dropped at tail drop of the queue";
           }
           leaf queue-counters-ecn-ce-packets {
             type int32;
             description
               "Total number of ECN CE packets";
           }
           leaf queue-counters-ecn-ce-packets-rate {
             type int32;
             description
               "Rate at which ECN CE packets are transmitted";
           }
           leaf queue-counters-ecn-ce-bytes {
             type int32;
             description
               "Total number of ECN CE bytes";
           }
           leaf queue-counters-ecn-ce-bytes-rate {
             type int32;
             description
               "Rate at which ECN CE bytes are transmitted";
           }
           leaf queue-counters-rate-limit-drop-packets-na {
             type string;
             description
               "Number of packets dropped due to rate-limit drop not 
               available";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes-na {
             type string;
             description
               "Number of bytes dropped due to tail drop not available";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets-na {
             type string;
             description
               "Number of packets dropped due to RED not available";
           }
           leaf queue-counters-red-packets {
             type int32;
             description
               "Number of packets dropped due to RED";
           }
           leaf queue-counters-red-packets-rate {
             type int32;
             description
               "Rate at which packets are dropped due to RED";
           }
           leaf queue-counters-red-packets-ln {
             type int32;
             description
               "Number of RED dropped low-loss, non-TCP packets";
           }
           leaf queue-counters-red-packets-rate-ln {
             type int32;
             description
               "RED drop rate for low-loss, non-TCP packets";
           }
           leaf queue-counters-red-packets-lt {
             type int32;
             description
               "Number of RED dropped of low-loss, TCP packets";
           }
           leaf queue-counters-red-packets-rate-lt {
             type int32;
             description
               "RED drop rate for low-loss, TCP packets";
           }
           leaf queue-counters-red-packets-hn {
             type int32;
             description
               "Number of RED dropped high-loss, non-TCP packets";
           }
           leaf queue-counters-red-packets-rate-hn {
             type int32;
             description
               "RED drop rate for high-loss, non-TCP packets";
           }
           leaf queue-counters-red-packets-ht {
             type int32;
             description
               "Number of RED dropped high-loss, TCP packets";
           }
           leaf queue-counters-red-packets-rate-ht {
             type int32;
             description
               "RED drop rate for high-loss, TCP packets";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-medium {
             type int32;
             description
               "Number of RED dropped medium-loss packets";
           }
           leaf queue-counters-red-packets-rate-medium {
             type int32;
             description
               "RED drop rate for medium-loss packets";
           }
           leaf queue-counters-red-packets-high {
             type int32;
             description
               "Number of RED dropped high-loss packets";
           }
           leaf queue-counters-red-packets-rate-high {
             type int32;
             description
               "RED drop rate for high-loss packets";
           }
           leaf queue-counters-red-bytes-na {
             type string;
             description
               "Number of bytes dropped due to RED not available";
           }
           leaf queue-counters-red-bytes {
             type int32;
             description
               "Number of bytes dropped due to RED";
           }
           leaf queue-counters-red-bytes-rate {
             type int32;
             description
               "Rate at which bytes are dropped due to RED";
           }
           leaf queue-counters-red-bytes-ln {
             type int32;
             description
               "Number of RED dropped low-loss, non-TCP bytes";
           }
           leaf queue-counters-red-bytes-rate-ln {
             type int32;
             description
               "RED drop rate for low-loss, non-TCP bytes";
           }
           leaf queue-counters-red-bytes-lt {
             type int32;
             description
               "Number of RED dropped low-loss, TCP bytes";
           }
           leaf queue-counters-red-bytes-rate-lt {
             type int32;
             description
               "RED drop rate for low-loss, TCP bytes";
           }
           leaf queue-counters-red-bytes-hn {
             type int32;
             description
               "Number of RED dropped high-loss, non-TCP bytes";
           }
           leaf queue-counters-red-bytes-rate-hn {
             type int32;
             description
               "RED drop rate for high-loss, non-TCP bytes";
           }
           leaf queue-counters-red-bytes-ht {
             type int32;
             description
               "Number of RED dropped high-loss, TCP bytes";
           }
           leaf queue-counters-red-bytes-rate-ht {
             type int32;
             description
               "RED drop rate for high-loss, TCP bytes";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-medium {
             type int32;
             description
               "Number of RED dropped medium-loss bytes";
           }
           leaf queue-counters-red-bytes-rate-medium {
             type int32;
             description
               "RED drop rate for medium-loss bytes";
           }
           leaf queue-counters-red-bytes-high {
             type int32;
             description
               "Number of RED dropped high-loss bytes";
           }
           leaf queue-counters-red-bytes-rate-high {
             type int32;
             description
               "RED drop rate for high-loss bytes";
           }
           leaf queue-counters-timestamp {
             type int32;
             description
               "Last packet enqueued timestamp";
           }
           leaf queue-counters-total-drop-packets {
             type int32;
             description
               "Number of total packets dropped at the queue";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
           leaf queue-counters-reserved-buffer-packets {
             type int32;
             description
               "Queues's usage of reserved buffer pool in pkts";
           }
           leaf queue-counters-reserved-buffer-bytes {
             type int32;
             description
               "Queues's usage of reserved buffer pool in bytes";
           }
           leaf queue-counters-shared-buffer-packets {
             type int32;
             description
               "Queues's usage of shared buffer pool in pkts";
           }
           leaf queue-counters-shared-buffer-bytes {
             type int32;
             description
               "Queues's usage of shared buffer pool in bytes";
           }
           leaf queue-counters-depth-average {
             type int32;
             description
               "Time averaged queue depth";
           }
           leaf queue-counters-depth-current {
             type int32;
             description
               "Current instantaneous queue depth";
           }
           leaf queue-counters-depth-peak {
             type int32;
             description
               "Peak queue depth";
           }
           leaf queue-counters-depth-max {
             type int32;
             description
               "Maximum queue depth attained";
           }
           leaf queue-counters-srx-reserved-buffer-bytes {
             type int32;
             description
               "Queues's usage of reserved buffer pool in bytes";
           }
           leaf queue-counters-srx-depth-current {
             type int32;
             description
               "Current instantaneous queue depth";
           }
         }
       }
       container ingress-queue-counters {
         description
           "Ingress queue counter statistics";
         list queue {
           key "queue-number";
           description
             "Counters for a single queue";
           leaf queue-number {
             type uint32;
             description
               "Queue number";
           }
           leaf forwarding-class-name {
             type string;
             description
               "Forwarding class name associated with queue";
           }
           leaf queue-counters-queued-packets {
             type int32;
             description
               "Queued packet count";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-queued-packets-na {
             type string;
             description
               "Queued packets not available";
           }
           leaf queue-counters-queued-bytes-na {
             type string;
             description
               "Queued bytes not available";
           }
           leaf queue-counters-trans-packets {
             type int32;
             description
               "Total number of transmitted packets";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets-na {
             type string;
             description
               "Number of packets dropped due to tail drop not available";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of packets dropped at tail drop of the queue";
           }
           leaf queue-counters-tail-drop-bytes-rate {
             type int32;
             description
               "Number of packets dropped at tail drop of the queue";
           }
           leaf queue-counters-ecn-ce-packets {
             type int32;
             description
               "Total number of ECN CE packets";
           }
           leaf queue-counters-ecn-ce-packets-rate {
             type int32;
             description
               "Rate at which ECN CE packets are transmitted";
           }
           leaf queue-counters-ecn-ce-bytes {
             type int32;
             description
               "Total number of ECN CE bytes";
           }
           leaf queue-counters-ecn-ce-bytes-rate {
             type int32;
             description
               "Rate at which ECN CE bytes are transmitted";
           }
           leaf queue-counters-rate-limit-drop-packets-na {
             type string;
             description
               "Number of packets dropped due to rate-limit drop not 
               available";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes-na {
             type string;
             description
               "Number of bytes dropped due to tail drop not available";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets-na {
             type string;
             description
               "Number of packets dropped due to RED not available";
           }
           leaf queue-counters-red-packets {
             type int32;
             description
               "Number of packets dropped due to RED";
           }
           leaf queue-counters-red-packets-rate {
             type int32;
             description
               "Rate at which packets are dropped due to RED";
           }
           leaf queue-counters-red-packets-ln {
             type int32;
             description
               "Number of RED dropped low-loss, non-TCP packets";
           }
           leaf queue-counters-red-packets-rate-ln {
             type int32;
             description
               "RED drop rate for low-loss, non-TCP packets";
           }
           leaf queue-counters-red-packets-lt {
             type int32;
             description
               "Number of RED dropped of low-loss, TCP packets";
           }
           leaf queue-counters-red-packets-rate-lt {
             type int32;
             description
               "RED drop rate for low-loss, TCP packets";
           }
           leaf queue-counters-red-packets-hn {
             type int32;
             description
               "Number of RED dropped high-loss, non-TCP packets";
           }
           leaf queue-counters-red-packets-rate-hn {
             type int32;
             description
               "RED drop rate for high-loss, non-TCP packets";
           }
           leaf queue-counters-red-packets-ht {
             type int32;
             description
               "Number of RED dropped high-loss, TCP packets";
           }
           leaf queue-counters-red-packets-rate-ht {
             type int32;
             description
               "RED drop rate for high-loss, TCP packets";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-medium {
             type int32;
             description
               "Number of RED dropped medium-loss packets";
           }
           leaf queue-counters-red-packets-rate-medium {
             type int32;
             description
               "RED drop rate for medium-loss packets";
           }
           leaf queue-counters-red-packets-high {
             type int32;
             description
               "Number of RED dropped high-loss packets";
           }
           leaf queue-counters-red-packets-rate-high {
             type int32;
             description
               "RED drop rate for high-loss packets";
           }
           leaf queue-counters-red-bytes-na {
             type string;
             description
               "Number of bytes dropped due to RED not available";
           }
           leaf queue-counters-red-bytes {
             type int32;
             description
               "Number of bytes dropped due to RED";
           }
           leaf queue-counters-red-bytes-rate {
             type int32;
             description
               "Rate at which bytes are dropped due to RED";
           }
           leaf queue-counters-red-bytes-ln {
             type int32;
             description
               "Number of RED dropped low-loss, non-TCP bytes";
           }
           leaf queue-counters-red-bytes-rate-ln {
             type int32;
             description
               "RED drop rate for low-loss, non-TCP bytes";
           }
           leaf queue-counters-red-bytes-lt {
             type int32;
             description
               "Number of RED dropped low-loss, TCP bytes";
           }
           leaf queue-counters-red-bytes-rate-lt {
             type int32;
             description
               "RED drop rate for low-loss, TCP bytes";
           }
           leaf queue-counters-red-bytes-hn {
             type int32;
             description
               "Number of RED dropped high-loss, non-TCP bytes";
           }
           leaf queue-counters-red-bytes-rate-hn {
             type int32;
             description
               "RED drop rate for high-loss, non-TCP bytes";
           }
           leaf queue-counters-red-bytes-ht {
             type int32;
             description
               "Number of RED dropped high-loss, TCP bytes";
           }
           leaf queue-counters-red-bytes-rate-ht {
             type int32;
             description
               "RED drop rate for high-loss, TCP bytes";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-medium {
             type int32;
             description
               "Number of RED dropped medium-loss bytes";
           }
           leaf queue-counters-red-bytes-rate-medium {
             type int32;
             description
               "RED drop rate for medium-loss bytes";
           }
           leaf queue-counters-red-bytes-high {
             type int32;
             description
               "Number of RED dropped high-loss bytes";
           }
           leaf queue-counters-red-bytes-rate-high {
             type int32;
             description
               "RED drop rate for high-loss bytes";
           }
           leaf queue-counters-timestamp {
             type int32;
             description
               "Last packet enqueued timestamp";
           }
           leaf queue-counters-total-drop-packets {
             type int32;
             description
               "Number of total packets dropped at the queue";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
           leaf queue-counters-reserved-buffer-packets {
             type int32;
             description
               "Queues's usage of reserved buffer pool in pkts";
           }
           leaf queue-counters-reserved-buffer-bytes {
             type int32;
             description
               "Queues's usage of reserved buffer pool in bytes";
           }
           leaf queue-counters-shared-buffer-packets {
             type int32;
             description
               "Queues's usage of shared buffer pool in pkts";
           }
           leaf queue-counters-shared-buffer-bytes {
             type int32;
             description
               "Queues's usage of shared buffer pool in bytes";
           }
           leaf queue-counters-depth-average {
             type int32;
             description
               "Time averaged queue depth";
           }
           leaf queue-counters-depth-current {
             type int32;
             description
               "Current instantaneous queue depth";
           }
           leaf queue-counters-depth-peak {
             type int32;
             description
               "Peak queue depth";
           }
           leaf queue-counters-depth-max {
             type int32;
             description
               "Maximum queue depth attained";
           }
           leaf queue-counters-srx-reserved-buffer-bytes {
             type int32;
             description
               "Queues's usage of reserved buffer pool in bytes";
           }
           leaf queue-counters-srx-depth-current {
             type int32;
             description
               "Current instantaneous queue depth";
           }
         }
         container interface-cos-summary {
           description
             "Summary of forwarding class and queue information on an 
             interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
           leaf intf-cos-burst-size-for-ifl {
             type int32;
             description
               "Burst size for the logical interface";
           }
         }
         container interface-cos-short-summary {
           description
             "Summary of queue information on an interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
         }
         list queue-num-forwarding-class-name-map {
           key "queue-number";
           leaf queue-number {
             type uint32;
             description
               "Queue number";
           }
           leaf forwarding-class-name {
             type string;
             description
               "Forwarding class name associated with queue";
           }
         }
       }
       container otn-oc-information {
         list media-alarm {
           leaf media-alarm-name {
             type string;
           }
           leaf media-alarm-seconds {
             type int32;
           }
           leaf media-alarm-count {
             type int32;
           }
           leaf media-alarm-state {
             type string;
           }
         }
       }
       container otn-otu-information {
         list media-alarm {
           leaf media-alarm-name {
             type string;
           }
           leaf media-alarm-seconds {
             type int32;
           }
           leaf media-alarm-count {
             type int32;
           }
           leaf media-alarm-state {
             type string;
           }
         }
       }
       container otn-odu-information {
         list media-alarm {
           leaf media-alarm-name {
             type string;
           }
           leaf media-alarm-seconds {
             type int32;
           }
           leaf media-alarm-count {
             type int32;
           }
           leaf media-alarm-state {
             type string;
           }
         }
       }
       container otn-ot-module-information {
         list media-alarm {
           leaf media-alarm-name {
             type string;
           }
           leaf media-alarm-seconds {
             type int32;
           }
           leaf media-alarm-count {
             type int32;
           }
           leaf media-alarm-state {
             type string;
           }
         }
       }
       list otn-odu-tcm-information {
         list media-alarm {
           leaf media-alarm-name {
             type string;
           }
           leaf media-alarm-seconds {
             type int32;
           }
           leaf media-alarm-count {
             type int32;
           }
           leaf media-alarm-state {
             type string;
           }
         }
       }
       container ima-state {
         leaf media-type {
           type string;
           description
             "Type of media this information is for";
         }
         leaf ima-state-line {
           type string;
           description
             "Line state of IMA link";
         }
         leaf ima-state-near-end {
           type string;
           description
             "Near-end states of IMA group/link";
         }
         leaf ima-state-far-end {
           type string;
           description
             "Far-end states of IMA group/link";
         }
       }
       container ima-group-information {
         description
           "IMA group alarms";
         list media-alarm {
           leaf media-alarm-name {
             type string;
           }
           leaf media-alarm-seconds {
             type int32;
           }
           leaf media-alarm-count {
             type int32;
           }
           leaf media-alarm-state {
             type string;
           }
         }
       }
       container ima-link-information {
         description
           "IMA link alarms";
         list media-alarm {
           leaf media-alarm-name {
             type string;
           }
           leaf media-alarm-seconds {
             type int32;
           }
           leaf media-alarm-count {
             type int32;
           }
           leaf media-alarm-state {
             type string;
           }
         }
       }
       list smart-sfp-channel-statistics {
         key "iwf-channel-num";
         description
           "Smart SFP channel IWF statistics";
         leaf iwf-channel-num {
           type uint32;
           description
             "Channel number for IWF stats";
         }
         leaf channel-not-applicable {
           type string;
           description
             "Channelization are not supported";
         }
         container smart-sfp-av-titan-iwf-statistics {
           leaf rx-packets {
             type uint32;
           }
           leaf tx-packets {
             type uint32;
           }
           leaf malformed-packets {
             type uint32;
           }
           leaf reordered-packets {
             type uint32;
           }
           leaf misordered-dropped-packets {
             type uint32;
           }
           leaf missing-packets {
             type uint32;
           }
           leaf played-out-packets {
             type uint32;
           }
           leaf jb-overrun {
             type uint32;
           }
           leaf jb-underrun {
             type uint32;
           }
         }
       }
       list smart-sfp-channel-defects {
         key "defect-channel-num";
         description
           "Smart SFP channel Defects";
         leaf defect-channel-num {
           type uint32;
           description
             "Channel number ";
         }
         leaf sfp-channel-defects {
           type string;
         }
         leaf channel-not-applicable {
           type string;
           description
             "Channelization are not supported";
         }
       }
       container ethernet-mac-pfc-statistics {
         description
           "Ethernet MAC Priority Flow control Statistics";
         leaf mac-pfc-dot1p {
           type int32;
         }
         leaf input-mac-pfc-frames {
           type int32;
         }
         leaf output-mac-pfc-frames {
           type int32;
         }
       }
       container ethernet-pfcwd-statistics {
         description
           "Ethernet MAC Priority Flow control Watchdog Statistics";
         leaf queue-number {
           type uint32;
           description
             "Queue number";
         }
         leaf detected {
           type int32;
         }
         leaf recovered {
           type int32;
         }
         leaf last-count {
           type int32;
         }
         leaf total-count {
           type int32;
         }
       }
       container satop-information {
         leaf ce-payload-size {
           type int32;
         }
         leaf ce-idle-pattern {
           type string;
         }
         leaf ce-octet-aligned {
           type string;
         }
         leaf ce-jitter-buffer-packets {
           type int32;
         }
         leaf ce-jitter-buffer-latency {
           type int32;
         }
         leaf ce-jitter-buffer-auto-adjust {
           type string;
         }
         leaf ce-excessive-packet-loss-rate-sample-period {
           type int32;
         }
         leaf ce-excessive-packet-loss-rate-threshold {
           type int32;
         }
       }
       container cesopsn-information {
         leaf ce-packetization-latency {
           type int32;
         }
         leaf ce-idle-pattern {
           type string;
         }
         leaf ce-jitter-buffer-packets {
           type int32;
         }
         leaf ce-jitter-buffer-latency {
           type int32;
         }
         leaf ce-jitter-buffer-auto-adjust {
           type string;
         }
         leaf ce-excessive-packet-loss-rate-sample-period {
           type int32;
         }
         leaf ce-excessive-packet-loss-rate-threshold {
           type int32;
         }
       }
       container ima-group-properties {
         leaf ima-version {
           type string;
           description
             "IMA specification version";
         }
         leaf ima-frame-length {
           type int32;
           description
             "IMA frame length";
         }
         leaf ima-differential-delay {
           type int32;
           description
             "IMA differential delay in milliseconds";
         }
         leaf ima-symmetry {
           type string;
           description
             "IMA operation symmetry mode";
         }
         leaf ima-transmit-clock {
           type string;
           description
             "IMA transmit clock mode";
         }
         leaf ima-tx-minimum-links {
           type int32;
           description
             "IMA transmit minimum links";
         }
         leaf ima-rx-minimum-links {
           type int32;
           description
             "IMA receive minimum links";
         }
         leaf ima-frame-sync-alpha {
           type int32;
           description
             "Consecutive invalid ICP cells for IMA frame synchronization";
         }
         leaf ima-frame-sync-beta {
           type int32;
           description
             "Consecutive errored ICP cells for IMA frame synchronization";
         }
         leaf ima-frame-sync-gamma {
           type int32;
           description
             "Consecutive valid ICP cells for IMA frame synchronization";
         }
         leaf ima-group-link-enumerator {
           type int32;
           description
             "Enumerator for link in this IMA group";
         }
         leaf ima-group-link-information {
           type string;
           description
             "Information for link in this IMA group";
         }
         leaf ima-test-period {
           type int32;
           description
             "IMA Test period";
         }
         leaf ima-test-elapsed {
           type int32;
           description
             "IMA Test elapsed time";
         }
         leaf ima-test-status {
           type string;
           description
             "IMA test procedure status";
         }
         leaf ima-test-pattern {
           type int32;
           description
             "IMA test tx pattern";
         }
         leaf ima-test-link {
           type string;
           description
             "IMA test procedure link";
         }
         leaf ima-test-result-pattern {
           type int32;
           description
             "IMA test rx pattern";
         }
         leaf ima-test-result-status {
           type string;
           description
             "IMA test result";
         }
         leaf ima-test-result-miscon {
           type int32;
           description
             "IMA test misconnected seconds";
         }
         leaf ima-test-result-mispat {
           type int32;
           description
             "IMA test mismatched pattern seconds";
         }
       }
       container ima-link-properties {
         leaf ima-group-id {
           type int32;
           description
             "IMA group ID";
         }
         leaf ima-link-direction {
           type string;
           description
             "IMA link direction";
         }
       }
       container cos-information {
         description
           "Information about class-of-service configuration";
         container cos-stream-information {
           description
             "Information about the traffic stream";
           leaf cos-direction {
             type string;
             description
               "Direction of the traffic stream";
           }
           list cos-queue-configuration {
             key "cos-queue-number";
             leaf cos-queue-number {
               type int32;
               description
                 "Queue number";
             }
             leaf cos-queue-forwarding-class {
               type string;
             }
             leaf cos-queue-bandwidth-remainder {
               type string;
             }
             leaf cos-queue-bandwidth {
               type int32;
             }
             leaf cos-queue-bandwidth-bps-remainder {
               type string;
             }
             leaf cos-queue-bandwidth-bps {
               type uint64;
             }
             leaf cos-queue-buffer-remainder {
               type string;
             }
             leaf cos-queue-buffer {
               type int32;
             }
             leaf cos-queue-buffer-bytes {
               type int32;
             }
             leaf cos-queue-priority {
               type string;
             }
             leaf cos-queue-limit {
               type string;
             }
           }
         }
       }
       container physical-interface-cos-information {
         description
           "Physical interface class-of-service parameters";
         leaf physical-interface-cos-hw-max-queues {
           type int32;
           description
             "Maximum number of class-of-service queues supported by the 
             hardware";
         }
         leaf physical-interface-cos-use-max-queues {
           type int32;
           description
             "Maximum number of usable class-of-service queues";
         }
         leaf physical-interface-schedulers {
           type int32;
           description
             "Schedulers allocated to this interface";
         }
         leaf physical-interface-bypass-queueing-chip {
           type string;
           description
             "Bypass queueing chip enabled on this interface";
         }
         container physical-interface-red-buffer-occupancy {
           description
             "Type of buffer occupancy information used for performing 
             random early drop on the interface";
           leaf instant-usage-weight-exponent {
             type int32;
             description
               "Weight used for instant buffer usage information for 
               computing buffer occupancy expressed as a negative exponent 
               of 2";
           }
         }
       }
       container precl-statistics {
         description
           "Preclassifier Statistics ";
         container precl-information {
           description
             "Preclassifier Statistics";
           list precl-per-class-statistics {
             leaf precl-traffic-class {
               type string;
               description
                 "Traffic class";
             }
             leaf precl-rx-packets {
               type int32;
               description
                 "Packets received by the preclassifier";
             }
             leaf precl-tx-packets {
               type int32;
               description
                 "Packets transmitted by the preclassifier";
             }
             leaf precl-dropped-packets {
               type int32;
               description
                 "Packets dropped by the preclassifier";
             }
           }
         }
       }
       container mlfr-uni-nni-traffic-statistics {
         container bundle {
           container multilink-frames {
             description
               "Link-pic bound frame statistics for multilink bundles and 
               classes";
             leaf input-frames {
               type int32;
             }
             leaf input-fps {
               type int32;
             }
             leaf input-bytes {
               type int32;
             }
             leaf input-bps {
               type int32;
             }
             leaf output-frames {
               type int32;
             }
             leaf output-fps {
               type int32;
             }
             leaf output-bytes {
               type int32;
             }
             leaf output-bps {
               type int32;
             }
           }
           container network-frames {
             description
               "Internet/RE bound frame statistics for multilink bundles and
               classes";
             leaf input-frames {
               type int32;
             }
             leaf input-fps {
               type int32;
             }
             leaf input-bytes {
               type int32;
             }
             leaf input-bps {
               type int32;
             }
             leaf output-frames {
               type int32;
             }
             leaf output-fps {
               type int32;
             }
             leaf output-bytes {
               type int32;
             }
             leaf output-bps {
               type int32;
             }
           }
         }
         container mlfr-uni-nni-link-information {
           leaf active-bundle-links {
             type int32;
             description
               "Number of active bundle links in this multilink Frame Relay 
               UNI NNI bundle instance";
           }
           leaf removed-bundle-links {
             type int32;
             description
               "Number of bundle links that are removed from service in this
               multilink Frame Relay UNI NNI bundle instance";
           }
           leaf disabled-bundle-links {
             type int32;
             description
               "Number of bundle links that are not allowed to transmit in 
               this multilink Frame Relay UNI NNI bundle instance";
           }
         }
         list mlfr-uni-nni-link {
           key "name";
           leaf name {
             type string;
             description
               "Name of this item";
           }
           leaf down {
             type empty;
             description
               "Link is down";
           }
           leaf link-uptime {
             type string;
             description
               "Total uptime for the member link";
           }
           leaf input-frames {
             type int32;
           }
           leaf input-fps {
             type int32;
           }
           leaf input-bytes {
             type int32;
           }
           leaf input-bps {
             type int32;
           }
           leaf output-frames {
             type int32;
           }
           leaf output-fps {
             type int32;
           }
           leaf output-bytes {
             type int32;
           }
           leaf output-bps {
             type int32;
           }
           leaf current-differential-delay {
             type int32;
             description
               "Current differential delay of this bundle link";
           }
           leaf recent-high-differential-delay {
             type int32;
             description
               "Recent highest differential delay of this bundle link (in 
               every 256 measurements)";
           }
           leaf over-red-differential {
             type int32;
             description
               "Number of times over red differential delay";
           }
           leaf over-yellow-differential {
             type int32;
             description
               "Number of times over yellow differential delay";
           }
           leaf lip-header-string {
             type string;
             description
               "Header string of the LIP display";
           }
           leaf rcv-lip-addlink {
             type int32;
             description
               "Number of LIP ADD_LINKs received";
           }
           leaf rcv-lip-link-ack {
             type int32;
             description
               "Number of LIP ADD_LINK_ACKs received";
           }
           leaf rcv-lip-link-rej {
             type int32;
             description
               "Number of LIP ADD_LINK_REJs received";
           }
           leaf rcv-lip-hello {
             type int32;
             description
               "Number of LIP HELLOs received";
           }
           leaf rcv-lip-hello-ack {
             type int32;
             description
               "Number of LIP HELLO_ACKs received";
           }
           leaf rcv-lip-link-rem {
             type int32;
             description
               "Number of LIP LINK_REMOVEs received";
           }
           leaf rcv-lip-rem-ack {
             type int32;
             description
               "Number of LIP LINK_REMOVE_ACKs received";
           }
           leaf xmt-lip-addlink {
             type int32;
             description
               "Number of LIP ADD_LINKs transmitted";
           }
           leaf xmt-lip-link-ack {
             type int32;
             description
               "Number of LIP LINK_ACKs transmitted";
           }
           leaf xmt-lip-link-rej {
             type int32;
             description
               "Number of LIP LINK_REJs transmitted";
           }
           leaf xmt-lip-hello {
             type int32;
             description
               "Number of LIP HELLOs transmitted";
           }
           leaf xmt-lip-hello-ack {
             type int32;
             description
               "Number of LIP HELLO_ACKs transmitted";
           }
           leaf xmt-lip-link-rem {
             type int32;
             description
               "Number of LIP LINK_REMOVEs transmitted";
           }
           leaf xmt-lip-rem-ack {
             type int32;
             description
               "Number of LIP LINK_REMOVE_ACKs transmitted";
           }
         }
       }
       container lag-traffic-statistics {
         container lag-adaptive-statistics {
           leaf adaptive-adjusts {
             type int32;
           }
           leaf adaptive-scans {
             type int32;
           }
           leaf adaptive-updates {
             type int32;
           }
         }
         container lag-multicast-statistics {
           leaf lag-multicast-statistics-header {
             type empty;
           }
           container lag-ipv4-multicast-statistics {
             leaf input-packets {
               type uint64;
             }
             leaf input-pps {
               type int32;
             }
             leaf input-bytes {
               type int32;
             }
             leaf input-bps {
               type int32;
             }
             leaf output-packets {
               type uint64;
             }
             leaf output-pps {
               type int32;
             }
             leaf output-bytes {
               type int32;
             }
             leaf output-bps {
               type int32;
             }
           }
           container lag-ipv6-multicast-statistics {
             leaf input-packets {
               type uint64;
             }
             leaf input-pps {
               type int32;
             }
             leaf input-bytes {
               type int32;
             }
             leaf input-bps {
               type int32;
             }
             leaf output-packets {
               type uint64;
             }
             leaf output-pps {
               type int32;
             }
             leaf output-bytes {
               type int32;
             }
             leaf output-bps {
               type int32;
             }
           }
         }
         list if-distribution-list-information {
         }
         container ifd-lag-traffic-statistics {
         }
       }
       container ifd-lag-traffic-statistics {
         list ifd-lag-members-list {
           key "name";
           leaf name {
             type string;
             description
               "Name of this item";
           }
           leaf down {
             type empty;
             description
               "Link is down";
           }
           leaf input-packets {
             type uint64;
           }
           leaf input-pps {
             type int32;
           }
           leaf input-bytes {
             type int32;
           }
           leaf input-bps {
             type int32;
           }
           leaf output-packets {
             type uint64;
           }
           leaf output-pps {
             type int32;
           }
           leaf output-bytes {
             type int32;
           }
           leaf output-bps {
             type int32;
           }
         }
       }
       container interval-information {
         list interval {
           description
             "Statistics for a single interval";
           leaf range {
             type string;
             description
               "Time range for this interval";
           }
           list media-alarm {
             leaf media-alarm-name {
               type string;
             }
             leaf media-alarm-count {
               type int32;
             }
           }
         }
       }
       container transport-interval-information {
         list transport-interval {
           description
             "Statistics for a single interval";
           list transport-pm-ber {
             leaf transport-pm-ber-thr-max {
               type string;
             }
             leaf transport-pm-ber-tca-max-en {
               type string;
             }
             leaf transport-pm-ber-tca-max {
               type string;
             }
             leaf transport-pm-ber-name {
               type string;
             }
             leaf transport-pm-ber-min {
               type string;
             }
             leaf transport-pm-ber-max {
               type string;
             }
             leaf transport-pm-ber-avg {
               type string;
             }
             leaf transport-pm-ber-thr-min {
               type string;
             }
             leaf transport-pm-ber-tca-min-en {
               type string;
             }
             leaf transport-pm-ber-tca-min {
               type string;
             }
           }
           list transport-pm-ber-cur {
             leaf transport-pm-ber-cur-thr-max {
               type string;
             }
             leaf transport-pm-ber-cur-tca-max-en {
               type string;
             }
             leaf transport-pm-ber-cur-tca-max {
               type string;
             }
             leaf transport-pm-ber-cur-name {
               type string;
             }
             leaf transport-pm-ber-cur-cur {
               type string;
             }
             leaf transport-pm-ber-cur-min {
               type string;
             }
             leaf transport-pm-ber-cur-max {
               type string;
             }
             leaf transport-pm-ber-cur-avg {
               type string;
             }
             leaf transport-pm-ber-cur-thr-min {
               type string;
             }
             leaf transport-pm-ber-cur-tca-min-en {
               type string;
             }
             leaf transport-pm-ber-cur-tca-min {
               type string;
             }
           }
           container transport-range {
             leaf transport-range-info {
               type string;
             }
             leaf transport-interval-len-info {
               type string;
             }
             leaf transport-range-suspect-flag {
               type string;
             }
             leaf transport-range-reason {
               type string;
             }
           }
           container transport-lane {
             leaf lane {
               type string;
             }
           }
           list transport-pm {
             leaf transport-pm-name {
               type string;
             }
             leaf transport-pm-count {
               type int32;
             }
             leaf transport-pm-thresh {
               type int32;
             }
             leaf transport-pm-tca-enabled {
               type string;
             }
             leaf transport-pm-tca-raised {
               type string;
             }
           }
           list transport-optics {
             leaf transport-optics-name {
               type string;
             }
             leaf transport-optics-unit {
               type string;
             }
             leaf transport-optics-min {
               type int32;
             }
             leaf transport-optics-max {
               type int32;
             }
             leaf transport-optics-avg {
               type int32;
             }
             leaf transport-optics-thr-min {
               type int32;
             }
             leaf transport-optics-thr-max {
               type int32;
             }
             leaf transport-optics-tca-min-en {
               type string;
             }
             leaf transport-optics-tca-max-en {
               type string;
             }
             leaf transport-optics-tca-min {
               type string;
             }
             leaf transport-optics-tca-max {
               type string;
             }
           }
           list transport-optics-cur {
             leaf transport-optics-cur-name {
               type string;
             }
             leaf transport-optics-cur-unit {
               type string;
             }
             leaf transport-optics-cur-cur {
               type int32;
             }
             leaf transport-optics-cur-min {
               type int32;
             }
             leaf transport-optics-cur-max {
               type int32;
             }
             leaf transport-optics-cur-avg {
               type int32;
             }
             leaf transport-optics-cur-thr-min {
               type int32;
             }
             leaf transport-optics-cur-thr-max {
               type int32;
             }
             leaf transport-optics-cur-tca-min-en {
               type string;
             }
             leaf transport-optics-cur-tca-max-en {
               type string;
             }
             leaf transport-optics-cur-tca-min {
               type string;
             }
             leaf transport-optics-cur-tca-max {
               type string;
             }
           }
         }
       }
       leaf interface-name {
         type jt:interface-device;
       }
       leaf logical-interface-name {
         type string;
       }
     }
     list logical-interface {
       key "name";
       description
         "Information about a single logical interface";
       leaf name {
         type string;
         description
           "Name of this item";
       }
       leaf local-index {
         type int32;
         description
           "Local kernel index for this interface";
       }
       leaf snmp-index {
         type int32;
         description
           "SNMP ifIndex for this interface";
       }
       leaf hardware-token {
         type int32;
         description
           "Hardware token for layer 3 ifl";
       }
       leaf generation {
         type string;
         description
           "Generation number used to distinguish between successive 
           instances of this interface";
       }
       leaf description {
         type string;
         description
           "Description of this interface";
       }
       leaf multilink-flapped {
         type string;
         description
           "Time when the interface last flapped";
       }
       leaf logical-interface-bandwidth {
         type string;
         description
           "Bandwidth of this logical interface";
       }
       leaf link-address {
         type string;
         description
           "Link address on this logical interface";
       }
       leaf unmatched-ifl {
         type string;
       }
       leaf encapsulation {
         type string;
         description
           "Encapsulation on the logical interface";
       }
       leaf dont-fragment {
         type string;
         description
           "Dont fragment on the logical interface";
       }
       leaf dont-decrement-ttl {
         type string;
         description
           "Dont decrement TTL";
       }
       leaf propagate-dscp {
         type string;
         description
           "Propagate DSCP field";
       }
       leaf propagate-ecn {
         type string;
         description
           "Propagate ECN field";
       }
       leaf esi-value {
         type string;
         description
           "Ethernet segment identifier for this interface";
       }
       leaf esi-mode {
         type string;
         description
           "Ethernet segment mode for this interface";
       }
       leaf evpn-multihomed-status {
         type string;
       }
       leaf virtual-gateway-esi-value {
         type string;
         description
           "Ethernet segment identifier for this interface";
       }
       leaf virtual-gateway-esi-mode {
         type string;
         description
           "Ethernet segment mode for this interface";
       }
       leaf interface-set-name {
         type string;
         description
           "Interface set on the logical interface";
       }
       leaf copy-tos-to-outer-ip-header {
         type string;
         description
           "Flag that enables copying of the value in the ToS field of the 
           IP packet's payload header to the delivery header in the generic
           routingencapsulation packet";
       }
       leaf copy-tos-to-outer-ip-header-transit {
         type string;
         description
           "Flag that enables copying of the value in the ToS field of the 
           IP packet's payload header to the delivery header in the generic
           routing encapsulation transit packet";
       }
       leaf force-control-packets-on-transit-path {
         type string;
         description
           "Flag that enables forcing control traffic to follow transit path
           encapsulation packet";
       }
       leaf gre-keepalive-configured {
         type string;
         description
           "Gre Keepalives enabled on the logical interface";
       }
       leaf gre-keepalive-adj-state {
         type string;
         description
           "Gre Keepalives enabled on the logical interface";
       }
       leaf demux-table-type {
         type string;
         description
           "Demux table enabled on the logical interface";
       }
       leaf redundant-logical-interface-name {
         type string;
         description
           "Name of the redundant logical interface";
       }
       leaf tenant-name {
         type string;
         description
           "Tenant name assigned to logical interface";
       }
       leaf lcp-state {
         type string;
         description
           "State of the Line Control Protocol";
       }
       leaf chap-state {
         type string;
         description
           "State of the Challenge Handshake Authentication Protocol";
       }
       leaf pap-state {
         type string;
         description
           "State of the Password Authentication Protocol";
       }
       leaf logical-interface-mac {
         type string;
         description
           "MAC on the logical interface";
       }
       leaf logical-interface-vgw-v4-mac {
         type string;
         description
           "MAC on the logical interface";
       }
       leaf logical-interface-vgw-v6-mac {
         type string;
         description
           "MAC on the logical interface";
       }
       leaf logical-interface-zone-name {
         type string;
         description
           "Zone name for this interface";
       }
       leaf subunit {
         type int32;
         description
           "Subunit for this interface";
       }
       leaf dialer-time-to-disconnect {
         type string;
         description
           "Time for dialer to disconnect due to idle timeout";
       }
       container if-config-flags {
         leaf iff-none {
           type empty;
         }
         leaf iff-hardware-down {
           type empty;
         }
         leaf iff-down {
           type empty;
         }
         leaf iff-up {
           type empty;
         }
         leaf iff-admin-down {
           type empty;
         }
         leaf iff-admin-up {
           type empty;
         }
         leaf iff-link-down {
           type empty;
         }
         leaf iff-device-down {
           type empty;
         }
         leaf iff-point-to-point {
           type empty;
         }
         leaf iff-point-to-multipoint {
           type empty;
         }
         leaf plp-to-clp {
           type empty;
         }
         leaf iff-multiaccess {
           type empty;
         }
         leaf iff-change {
           type empty;
         }
         leaf iff-inverse-arp {
           type empty;
         }
         leaf iff-no-multicast {
           type empty;
         }
         leaf iff-multicast {
           type empty;
         }
         leaf iff-promiscuous {
           type empty;
         }
         leaf iff-all-multicast {
           type empty;
         }
         leaf iff-snmp-traps {
           type empty;
         }
         leaf iff-no-forwarding-viable {
           type empty;
         }
         leaf iff-macsec {
           type empty;
         }
         leaf iff-secure {
           type empty;
         }
         leaf iff-rx-passive {
           type empty;
         }
         leaf iff-tx-passive {
           type empty;
         }
         leaf iff-ccc-down {
           type empty;
         }
         leaf iff-clear-df {
           type empty;
         }
         leaf iff-tunnel-reassembly {
           type empty;
         }
         leaf iff-acfc {
           type empty;
         }
         leaf iff-pfc {
           type empty;
         }
         leaf iff-rdd {
           type empty;
         }
         leaf iff-looped {
           type empty;
         }
         leaf iff-framing-conflict {
           type empty;
         }
         leaf internal-flags {
           type string;
           description
             "Hexadecimal value of internal flag bits";
         }
       }
       container layer2-input-policer-information {
         description
           "Information about Layer 2 input policer for interface";
         leaf layer2-input-policer {
           type string;
           description
             "Name of the Layer 2 input policer";
         }
       }
       container layer2-output-policer-information {
         description
           "Information about Layer 2 output policer for interface";
         leaf layer2-output-policer {
           type string;
           description
             "Name of the Layer 2 output policer";
         }
       }
       container atm-input-policer-information {
         description
           "Information about atm input policer for interface";
         leaf atm-input-policer {
           type string;
           description
             "Name of the atm input policer";
         }
       }
       container pppoe-information {
         description
           "PPPoE information";
         list pppoe-interface {
           leaf state {
             type string;
             description
               "State";
           }
           leaf session-id {
             type string;
             description
               "Session ID";
           }
           leaf ac-name-session {
             type string;
             description
               "Session AC name";
           }
           leaf remote-mac {
             type string;
             description
               "Remote MAC address";
           }
           leaf ac-name-config {
             type string;
             description
               "Configured AC name";
           }
           leaf service-name {
             type string;
             description
               "Service name";
           }
           leaf auto-reconnect {
             type string;
             description
               "Autoreconnect timeout";
           }
           leaf idle-timeout {
             type string;
             description
               "Idle timeout";
           }
           leaf underlying-interface-name {
             type string;
             description
               "Underlying interface name";
           }
           leaf underlying-interface-index {
             type string;
             description
               "Underlying interface index";
           }
           leaf padg-credits {
             type int32;
             description
               "PADG transmit credits";
           }
           leaf pppoe-credit-scale-factor {
             type string;
             description
               "Scaling factor";
           }
           leaf ignore-eol-tag {
             type string;
             description
               "Ignore End-of-List TAG";
           }
           leaf ppp-max-payload-tag {
             type int32;
             description
               "PPP-Max-Payload TAG";
           }
           leaf interface-name {
             type string;
             description
               "Interface name";
           }
           leaf interface-index {
             type string;
             description
               "Index";
           }
           leaf aci-iflset-name {
             type string;
             description
               "ACI Interface Set name";
           }
           leaf aci-iflset-index {
             type string;
             description
               "ACI Interface Set index";
           }
           leaf ifl-type {
             type string;
             description
               "Type";
           }
           leaf session-uptime {
             type string;
             description
               "Duration for which the session has been up";
           }
           leaf dynamic-profile {
             type string;
             description
               "Dynamic Profile name";
           }
           leaf pppoe-credits {
             type string;
             description
               "Forwarding credit balances";
           }
           leaf dynamic-interface-bandwidth {
             type string;
             description
               "Dynamic interface bandwidth";
           }
           leaf agent-circuit-id {
             type string;
             description
               "Agent Circuit ID";
           }
           leaf agent-remote-id {
             type string;
             description
               "Agent Remote ID";
           }
           leaf padm-motm {
             type string;
             description
               "PADM Message of the Moment tag";
           }
           leaf padm-hurl {
             type string;
             description
               "PADM HTTP URL tag";
           }
           leaf pppoe-relay-session-id {
             type string;
             description
               "PPPoE Relay Session ID";
           }
         }
       }
       container pppoe-underlying-information {
         description
           "PPPoE Underlying information";
         list pppoe-underlying-interface {
           leaf dynamic-profile {
             type string;
             description
               "Dynamic Profile name";
           }
           leaf service-name-table {
             type string;
             description
               "Name of Service Name Table";
           }
           leaf max-sessions {
             type int32;
             description
               "Maximum number of PPPoE sessions";
           }
           leaf max-sessions-vsa-ignore {
             type string;
             description
               "Ignore max-sessions VSA";
           }
           leaf duplicate-protection {
             type string;
             description
               "Duplicate protection mode";
           }
           leaf short-cycle-protection {
             type string;
             description
               "Short cycle protection mode";
           }
           leaf direct-connect {
             type string;
             description
               "Direct connect mode";
           }
           leaf ac-name {
             type string;
             description
               "Access Concentrator name";
           }
           leaf underlying-interface-name {
             type string;
             description
               "Underlying interface name";
           }
           leaf underlying-interface-index {
             type string;
             description
               "Underlying interface index";
           }
           leaf encapsulation-type-identifier {
             type string;
             description
               "Encapsulation type identifier";
           }
           leaf state {
             type string;
             description
               "State";
           }
           leaf active-sessions {
             type int32;
             description
               "Number of active PPPoE sessions";
           }
           leaf aci-autosensing {
             type string;
             description
               "ACI VLAN Autosensing mode";
           }
           leaf line-identity-autosensing {
             type string;
             description
               "Line Identity Autosensing mode";
           }
         }
       }
       container aci-vlan-information {
         leaf dynamic-profile {
           type string;
           description
             "Dynamic Profile name";
         }
       }
       container line-identity-information {
         leaf dynamic-profile {
           type string;
           description
             "Dynamic Profile name";
         }
         leaf circuit-id {
           type string;
           description
             "Aci vlan attribute";
         }
         leaf remote-id {
           type string;
           description
             "Aci vlan attribute";
         }
         leaf accept-no-ids {
           type string;
           description
             "Aci vlan attribute";
         }
       }
       container demux-information {
         description
           "Demux information";
         container demux-interface {
           leaf demux-underlying-interface-name {
             type string;
             description
               "Underlying interface name";
           }
           leaf demux-underlying-interface-index {
             type string;
             description
               "Underlying interface index";
           }
           leaf demux-inet-prefix-type {
             type string;
             description
               "Prefix type";
           }
           leaf demux-inet-prefix-count {
             type string;
             description
               "IPv4 Prefix count";
           }
           leaf demux-inet-prefix {
             type string;
             description
               "IPv4 Prefix";
           }
           leaf demux-inet6-prefix-type {
             type string;
             description
               "Prefix type";
           }
           leaf demux-inet6-prefix-count {
             type string;
             description
               "IPv6 Prefix count";
           }
           leaf demux-inet6-prefix {
             type string;
             description
               "IPv6 Prefix";
           }
         }
       }
       container dual-ad-icl-color-information {
         container dual-ad-icl-color-info {
           description
             "Dual-AD ICL Color Information";
           leaf dual-ad-icl-color-type {
             type uint32;
             description
               "Dual-AD ICL Color Type";
           }
           leaf dual-ad-icl-color {
             type uint32;
             description
               "Dual-AD ICL Color";
           }
         }
       }
       container dialer-information {
         description
           "Dialer information";
         leaf dialer-time-to-disconnect {
           type string;
           description
             "Time for dialer to disconnect due to idle timeout";
         }
         container dialer-interface {
           list dial-string-list {
             leaf dial-string {
               type string;
               description
                 "Dial string";
             }
           }
           list sub-interface-list {
             leaf sub-interface-name {
               type string;
               description
                 "Subordinate interface name";
             }
           }
           list watch-list {
             leaf watch-route {
               type string;
               description
                 "Watch route";
             }
           }
         }
       }
       container shared-interface-information {
         description
           "Shared interface information";
         container shared-interface-logical-interface {
           description
             "Shared interface logical interface";
           leaf peer-interface-name {
             type string;
             description
               "Peer interface name";
           }
           leaf interface-shared-with {
             type string;
             description
               "Logical interface owner";
           }
           leaf rx-fe {
             type string;
             description
               "Rx tunnel token forwarding element";
           }
           leaf rx-nhid {
             type string;
             description
               "Rx tunnel token next hop index";
           }
           leaf tx-fe {
             type string;
             description
               "Tx tunnel token forwarding element";
           }
           leaf tx-nhid {
             type string;
             description
               "Tx tunnel token next hop index";
           }
         }
       }
       container mac-database {
         list mac-record {
           leaf mac-address {
             type jt:mac-addr;
           }
           leaf receive-frames {
             type int32;
           }
           leaf receive-bytes {
             type int32;
           }
           leaf transmit-frames {
             type int32;
           }
           leaf transmit-bytes {
             type int32;
           }
         }
       }
       container policer-overhead {
         description
           "Policer overhead information";
         leaf ingress-policer-overhead {
           type int32;
           description
             "Ingress policer overhead information";
         }
         leaf egress-policer-overhead {
           type int32;
           description
             "Egress policer overhead information";
         }
       }
       container queue-counters {
         description
           "Queue counter statistics";
         leaf queue-counters-error-message {
           type string;
           description
             "Queue statistics not available for this interface";
         }
         container interface-cos-short-summary {
           description
             "Summary of queue information on an interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
         }
         list queue {
           key "queue-number";
           description
             "Counters for a single queue";
           leaf queue-number {
             type uint32;
             description
               "Queue number";
           }
           leaf queue-counters-queued-packets {
             type int32;
             description
               "Queued packet count";
           }
           leaf queue-counters-trans-packets {
             type int32;
             description
               "Total number of transmitted packets";
           }
           leaf queue-counters-total-drop-packets {
             type int32;
             description
               "Number of total packets dropped at the queue";
           }
           leaf forwarding-class-name {
             type string;
             description
               "Forwarding class name associated with queue";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-queued-packets-na {
             type string;
             description
               "Queued packets not available";
           }
           leaf queue-counters-queued-bytes-na {
             type string;
             description
               "Queued bytes not available";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets-na {
             type string;
             description
               "Number of packets dropped due to tail drop not available";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of packets dropped at tail drop of the queue";
           }
           leaf queue-counters-tail-drop-bytes-rate {
             type int32;
             description
               "Number of packets dropped at tail drop of the queue";
           }
           leaf queue-counters-ecn-ce-packets {
             type int32;
             description
               "Total number of ECN CE packets";
           }
           leaf queue-counters-ecn-ce-packets-rate {
             type int32;
             description
               "Rate at which ECN CE packets are transmitted";
           }
           leaf queue-counters-ecn-ce-bytes {
             type int32;
             description
               "Total number of ECN CE bytes";
           }
           leaf queue-counters-ecn-ce-bytes-rate {
             type int32;
             description
               "Rate at which ECN CE bytes are transmitted";
           }
           leaf queue-counters-rate-limit-drop-packets-na {
             type string;
             description
               "Number of packets dropped due to rate-limit drop not 
               available";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes-na {
             type string;
             description
               "Number of bytes dropped due to tail drop not available";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets-na {
             type string;
             description
               "Number of packets dropped due to RED not available";
           }
           leaf queue-counters-red-packets {
             type int32;
             description
               "Number of packets dropped due to RED";
           }
           leaf queue-counters-red-packets-rate {
             type int32;
             description
               "Rate at which packets are dropped due to RED";
           }
           leaf queue-counters-red-packets-ln {
             type int32;
             description
               "Number of RED dropped low-loss, non-TCP packets";
           }
           leaf queue-counters-red-packets-rate-ln {
             type int32;
             description
               "RED drop rate for low-loss, non-TCP packets";
           }
           leaf queue-counters-red-packets-lt {
             type int32;
             description
               "Number of RED dropped of low-loss, TCP packets";
           }
           leaf queue-counters-red-packets-rate-lt {
             type int32;
             description
               "RED drop rate for low-loss, TCP packets";
           }
           leaf queue-counters-red-packets-hn {
             type int32;
             description
               "Number of RED dropped high-loss, non-TCP packets";
           }
           leaf queue-counters-red-packets-rate-hn {
             type int32;
             description
               "RED drop rate for high-loss, non-TCP packets";
           }
           leaf queue-counters-red-packets-ht {
             type int32;
             description
               "Number of RED dropped high-loss, TCP packets";
           }
           leaf queue-counters-red-packets-rate-ht {
             type int32;
             description
               "RED drop rate for high-loss, TCP packets";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-medium {
             type int32;
             description
               "Number of RED dropped medium-loss packets";
           }
           leaf queue-counters-red-packets-rate-medium {
             type int32;
             description
               "RED drop rate for medium-loss packets";
           }
           leaf queue-counters-red-packets-high {
             type int32;
             description
               "Number of RED dropped high-loss packets";
           }
           leaf queue-counters-red-packets-rate-high {
             type int32;
             description
               "RED drop rate for high-loss packets";
           }
           leaf queue-counters-red-bytes-na {
             type string;
             description
               "Number of bytes dropped due to RED not available";
           }
           leaf queue-counters-red-bytes {
             type int32;
             description
               "Number of bytes dropped due to RED";
           }
           leaf queue-counters-red-bytes-rate {
             type int32;
             description
               "Rate at which bytes are dropped due to RED";
           }
           leaf queue-counters-red-bytes-ln {
             type int32;
             description
               "Number of RED dropped low-loss, non-TCP bytes";
           }
           leaf queue-counters-red-bytes-rate-ln {
             type int32;
             description
               "RED drop rate for low-loss, non-TCP bytes";
           }
           leaf queue-counters-red-bytes-lt {
             type int32;
             description
               "Number of RED dropped low-loss, TCP bytes";
           }
           leaf queue-counters-red-bytes-rate-lt {
             type int32;
             description
               "RED drop rate for low-loss, TCP bytes";
           }
           leaf queue-counters-red-bytes-hn {
             type int32;
             description
               "Number of RED dropped high-loss, non-TCP bytes";
           }
           leaf queue-counters-red-bytes-rate-hn {
             type int32;
             description
               "RED drop rate for high-loss, non-TCP bytes";
           }
           leaf queue-counters-red-bytes-ht {
             type int32;
             description
               "Number of RED dropped high-loss, TCP bytes";
           }
           leaf queue-counters-red-bytes-rate-ht {
             type int32;
             description
               "RED drop rate for high-loss, TCP bytes";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-medium {
             type int32;
             description
               "Number of RED dropped medium-loss bytes";
           }
           leaf queue-counters-red-bytes-rate-medium {
             type int32;
             description
               "RED drop rate for medium-loss bytes";
           }
           leaf queue-counters-red-bytes-high {
             type int32;
             description
               "Number of RED dropped high-loss bytes";
           }
           leaf queue-counters-red-bytes-rate-high {
             type int32;
             description
               "RED drop rate for high-loss bytes";
           }
           leaf queue-counters-timestamp {
             type int32;
             description
               "Last packet enqueued timestamp";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
           leaf queue-counters-reserved-buffer-packets {
             type int32;
             description
               "Queues's usage of reserved buffer pool in pkts";
           }
           leaf queue-counters-reserved-buffer-bytes {
             type int32;
             description
               "Queues's usage of reserved buffer pool in bytes";
           }
           leaf queue-counters-shared-buffer-packets {
             type int32;
             description
               "Queues's usage of shared buffer pool in pkts";
           }
           leaf queue-counters-shared-buffer-bytes {
             type int32;
             description
               "Queues's usage of shared buffer pool in bytes";
           }
           leaf queue-counters-depth-average {
             type int32;
             description
               "Time averaged queue depth";
           }
           leaf queue-counters-depth-current {
             type int32;
             description
               "Current instantaneous queue depth";
           }
           leaf queue-counters-depth-peak {
             type int32;
             description
               "Peak queue depth";
           }
           leaf queue-counters-depth-max {
             type int32;
             description
               "Maximum queue depth attained";
           }
           leaf queue-counters-srx-reserved-buffer-bytes {
             type int32;
             description
               "Queues's usage of reserved buffer pool in bytes";
           }
           leaf queue-counters-srx-depth-current {
             type int32;
             description
               "Current instantaneous queue depth";
           }
         }
         container interface-cos-summary {
           description
             "Summary of forwarding class and queue information on an 
             interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
           leaf intf-cos-burst-size-for-ifl {
             type int32;
             description
               "Burst size for the logical interface";
           }
         }
       }
       container voq-counters {
         description
           "VOQ counter statistics";
         leaf voq-counters-error-message {
           type string;
           description
             "VOQ statistics not available for this interface";
         }
         container voq {
           description
             "Counters for a single voq";
           container fpc {
             description
               "Counters for a single FPC";
             leaf fpc-no {
               type int32;
               description
                 "FPC number";
             }
             container pfe {
               description
                 "Counters for a single PFE";
               leaf-list pfe-no {
                 type int32;
                 description
                   "PFE number";
               }
               leaf voq-counters-tail-drop-packets {
                 type int32;
                 description
                   "Tail DROP packet count";
               }
               leaf voq-counters-tail-drop-packets-rate {
                 type int32;
                 description
                   "Rate at which tail packets are dropped";
               }
               leaf voq-counters-tail-drop-bytes {
                 type int32;
                 description
                   "Tail DROP bytes count";
               }
               leaf voq-counters-tail-drop-bytes-rate {
                 type int32;
                 description
                   "Rate at which tail bytes are dropped";
               }
               leaf voq-counters-drop-packets {
                 type int32;
                 description
                   "DROP packet count";
               }
               leaf voq-counters-drop-packets-rate {
                 type int32;
                 description
                   "Rate at which packets are dropped";
               }
               leaf voq-counters-drop-bytes {
                 type int32;
                 description
                   "DROP bytes count";
               }
               leaf voq-counters-drop-bytes-rate {
                 type int32;
                 description
                   "Rate at which bytes are dropped";
               }
               leaf voq-counters-queued-packets {
                 type int32;
                 description
                   "QUEUED packets count";
               }
               leaf voq-counters-queued-packets-rate {
                 type int32;
                 description
                   "Rate at which packets are queued";
               }
               leaf voq-counters-queued-bytes {
                 type int32;
                 description
                   "QUEUED bytes count";
               }
               leaf voq-counters-queued-bytes-rate {
                 type int32;
                 description
                   "Rate at which bytes are queued";
               }
               leaf voq-counters-transmitted-packets {
                 type int32;
                 description
                   "Transmitted packets count";
               }
               leaf voq-counters-transmitted-packets-rate {
                 type int32;
                 description
                   "Rate at which packets are transmitted";
               }
               leaf voq-counters-transmitted-bytes {
                 type int32;
                 description
                   "Transmitted bytes count";
               }
               leaf voq-counters-transmitted-bytes-rate {
                 type int32;
                 description
                   "Rate at which bytes are transmitted";
               }
               leaf voq-counters-queue-depth-bytes-current {
                 type int32;
                 description
                   "Current queue length";
               }
               leaf voq-counters-queue-depth-bytes-peak {
                 type int32;
                 description
                   "Peak queue length";
               }
               leaf voq-counters-queue-depth-bytes-average {
                 type int32;
                 description
                   "Average queue length";
               }
             }
           }
           leaf queue-number {
             type uint32;
             description
               "Queue number";
           }
           leaf forwarding-class-name {
             type string;
             description
               "Forwarding class name associated with queue";
           }
           leaf restricted-forwarding-class-name {
             type string;
           }
         }
       }
       container ingress-queue-counters {
         description
           "Ingress queue counter statistics";
         list queue {
           key "queue-number";
           description
             "Counters for a single queue";
           leaf queue-number {
             type uint32;
             description
               "Queue number";
           }
           leaf forwarding-class-name {
             type string;
             description
               "Forwarding class name associated with queue";
           }
           leaf queue-counters-queued-packets {
             type int32;
             description
               "Queued packet count";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-queued-packets-na {
             type string;
             description
               "Queued packets not available";
           }
           leaf queue-counters-queued-bytes-na {
             type string;
             description
               "Queued bytes not available";
           }
           leaf queue-counters-trans-packets {
             type int32;
             description
               "Total number of transmitted packets";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets-na {
             type string;
             description
               "Number of packets dropped due to tail drop not available";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of packets dropped at tail drop of the queue";
           }
           leaf queue-counters-tail-drop-bytes-rate {
             type int32;
             description
               "Number of packets dropped at tail drop of the queue";
           }
           leaf queue-counters-ecn-ce-packets {
             type int32;
             description
               "Total number of ECN CE packets";
           }
           leaf queue-counters-ecn-ce-packets-rate {
             type int32;
             description
               "Rate at which ECN CE packets are transmitted";
           }
           leaf queue-counters-ecn-ce-bytes {
             type int32;
             description
               "Total number of ECN CE bytes";
           }
           leaf queue-counters-ecn-ce-bytes-rate {
             type int32;
             description
               "Rate at which ECN CE bytes are transmitted";
           }
           leaf queue-counters-rate-limit-drop-packets-na {
             type string;
             description
               "Number of packets dropped due to rate-limit drop not 
               available";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes-na {
             type string;
             description
               "Number of bytes dropped due to tail drop not available";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets-na {
             type string;
             description
               "Number of packets dropped due to RED not available";
           }
           leaf queue-counters-red-packets {
             type int32;
             description
               "Number of packets dropped due to RED";
           }
           leaf queue-counters-red-packets-rate {
             type int32;
             description
               "Rate at which packets are dropped due to RED";
           }
           leaf queue-counters-red-packets-ln {
             type int32;
             description
               "Number of RED dropped low-loss, non-TCP packets";
           }
           leaf queue-counters-red-packets-rate-ln {
             type int32;
             description
               "RED drop rate for low-loss, non-TCP packets";
           }
           leaf queue-counters-red-packets-lt {
             type int32;
             description
               "Number of RED dropped of low-loss, TCP packets";
           }
           leaf queue-counters-red-packets-rate-lt {
             type int32;
             description
               "RED drop rate for low-loss, TCP packets";
           }
           leaf queue-counters-red-packets-hn {
             type int32;
             description
               "Number of RED dropped high-loss, non-TCP packets";
           }
           leaf queue-counters-red-packets-rate-hn {
             type int32;
             description
               "RED drop rate for high-loss, non-TCP packets";
           }
           leaf queue-counters-red-packets-ht {
             type int32;
             description
               "Number of RED dropped high-loss, TCP packets";
           }
           leaf queue-counters-red-packets-rate-ht {
             type int32;
             description
               "RED drop rate for high-loss, TCP packets";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-medium {
             type int32;
             description
               "Number of RED dropped medium-loss packets";
           }
           leaf queue-counters-red-packets-rate-medium {
             type int32;
             description
               "RED drop rate for medium-loss packets";
           }
           leaf queue-counters-red-packets-high {
             type int32;
             description
               "Number of RED dropped high-loss packets";
           }
           leaf queue-counters-red-packets-rate-high {
             type int32;
             description
               "RED drop rate for high-loss packets";
           }
           leaf queue-counters-red-bytes-na {
             type string;
             description
               "Number of bytes dropped due to RED not available";
           }
           leaf queue-counters-red-bytes {
             type int32;
             description
               "Number of bytes dropped due to RED";
           }
           leaf queue-counters-red-bytes-rate {
             type int32;
             description
               "Rate at which bytes are dropped due to RED";
           }
           leaf queue-counters-red-bytes-ln {
             type int32;
             description
               "Number of RED dropped low-loss, non-TCP bytes";
           }
           leaf queue-counters-red-bytes-rate-ln {
             type int32;
             description
               "RED drop rate for low-loss, non-TCP bytes";
           }
           leaf queue-counters-red-bytes-lt {
             type int32;
             description
               "Number of RED dropped low-loss, TCP bytes";
           }
           leaf queue-counters-red-bytes-rate-lt {
             type int32;
             description
               "RED drop rate for low-loss, TCP bytes";
           }
           leaf queue-counters-red-bytes-hn {
             type int32;
             description
               "Number of RED dropped high-loss, non-TCP bytes";
           }
           leaf queue-counters-red-bytes-rate-hn {
             type int32;
             description
               "RED drop rate for high-loss, non-TCP bytes";
           }
           leaf queue-counters-red-bytes-ht {
             type int32;
             description
               "Number of RED dropped high-loss, TCP bytes";
           }
           leaf queue-counters-red-bytes-rate-ht {
             type int32;
             description
               "RED drop rate for high-loss, TCP bytes";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-medium {
             type int32;
             description
               "Number of RED dropped medium-loss bytes";
           }
           leaf queue-counters-red-bytes-rate-medium {
             type int32;
             description
               "RED drop rate for medium-loss bytes";
           }
           leaf queue-counters-red-bytes-high {
             type int32;
             description
               "Number of RED dropped high-loss bytes";
           }
           leaf queue-counters-red-bytes-rate-high {
             type int32;
             description
               "RED drop rate for high-loss bytes";
           }
           leaf queue-counters-timestamp {
             type int32;
             description
               "Last packet enqueued timestamp";
           }
           leaf queue-counters-total-drop-packets {
             type int32;
             description
               "Number of total packets dropped at the queue";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
           leaf queue-counters-reserved-buffer-packets {
             type int32;
             description
               "Queues's usage of reserved buffer pool in pkts";
           }
           leaf queue-counters-reserved-buffer-bytes {
             type int32;
             description
               "Queues's usage of reserved buffer pool in bytes";
           }
           leaf queue-counters-shared-buffer-packets {
             type int32;
             description
               "Queues's usage of shared buffer pool in pkts";
           }
           leaf queue-counters-shared-buffer-bytes {
             type int32;
             description
               "Queues's usage of shared buffer pool in bytes";
           }
           leaf queue-counters-depth-average {
             type int32;
             description
               "Time averaged queue depth";
           }
           leaf queue-counters-depth-current {
             type int32;
             description
               "Current instantaneous queue depth";
           }
           leaf queue-counters-depth-peak {
             type int32;
             description
               "Peak queue depth";
           }
           leaf queue-counters-depth-max {
             type int32;
             description
               "Maximum queue depth attained";
           }
           leaf queue-counters-srx-reserved-buffer-bytes {
             type int32;
             description
               "Queues's usage of reserved buffer pool in bytes";
           }
           leaf queue-counters-srx-depth-current {
             type int32;
             description
               "Current instantaneous queue depth";
           }
         }
         container interface-cos-summary {
           description
             "Summary of forwarding class and queue information on an 
             interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
           leaf intf-cos-burst-size-for-ifl {
             type int32;
             description
               "Burst size for the logical interface";
           }
         }
         container interface-cos-short-summary {
           description
             "Summary of queue information on an interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
         }
         list queue-num-forwarding-class-name-map {
           key "queue-number";
           leaf queue-number {
             type uint32;
             description
               "Queue number";
           }
           leaf forwarding-class-name {
             type string;
             description
               "Forwarding class name associated with queue";
           }
         }
       }
       container forwarding-class-counters {
         description
           "Forwarding-class counter statistics";
         leaf forwarding-class-counters-error-message {
           type string;
           description
             "Forwarding-class statistics not available for this interface";
         }
         container ipv4-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container ipv6-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container mpls-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container layer2-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container other-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container protocol-aggregate-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container forwarding-class-statistics {
           container protocol-aggregate-forwarding-class-counters {
           }
           container ipv4-forwarding-class-counters {
           }
           container ipv6-forwarding-class-counters {
           }
           container mpls-forwarding-class-counters {
           }
           container layer2-forwarding-class-counters {
           }
           container other-forwarding-class-counters {
           }
         }
         container forwarding-class-accounting-parameters {
           leaf forwarding-class-accounting-for-protocol {
             type string;
           }
           leaf forwarding-class-accounting-for-traffic-direction {
             type string;
           }
           leaf forwarding-class-accounting-for-traffic-type {
             type string;
           }
           leaf forwarding-class-accounting-overhead-bytes {
             type uint32;
           }
         }
         container per-forwarding-class-counters {
           leaf fc_name_header {
             type string;
           }
           leaf forwarding-class-name {
             type string;
             description
               "Forwarding class name associated with queue";
           }
           leaf fc-input-bytes {
             type int32;
           }
           leaf fc-input-bytes-rate {
             type int32;
             description
               "Input bytes rate";
           }
           leaf fc-output-bytes {
             type int32;
           }
           leaf fc-output-bytes-rate {
             type int32;
             description
               "Output bytes rate";
           }
           leaf fc-input-packets {
             type int32;
           }
           leaf fc-input-packets-rate {
             type int32;
             description
               "Input packets rate";
           }
           leaf fc-output-packets {
             type int32;
           }
           leaf fc-output-packets-rate {
             type int32;
             description
               "Output packets rate";
           }
           leaf input-unicast-bytes {
             type int32;
           }
           leaf output-unicast-bytes {
             type int32;
           }
           leaf input-unicast-packets {
             type int32;
           }
           leaf output-unicast-packets {
             type int32;
           }
           leaf input-multicast-bytes {
             type int32;
           }
           leaf output-multicast-bytes {
             type int32;
           }
           leaf input-multicast-packets {
             type int32;
           }
           leaf output-multicast-packets {
             type int32;
           }
         }
       }
       container multilink-bundle-link-information {
         leaf multilink-active-bundle-links {
           type int32;
           description
             "Number of active bundle links in this multilink bundle 
             instance";
         }
         leaf multilink-removed-bundle-links {
           type int32;
           description
             "Number of bundle links that are removed from service in this 
             multilink bundle instance";
         }
         leaf multilink-disabled-bundle-links {
           type int32;
           description
             "Number of bundle links that are not allowed to transmit in 
             this multilink bundle instance";
         }
       }
       container multilink-bundle-options {
         leaf mrru {
           type int32;
         }
         leaf remote-mrru {
           type int32;
           description
             "Remote max received reconstructed unit";
         }
         leaf drop-timeout {
           type int32;
         }
         leaf mlppp-inner-ppp-pfc {
           type string;
           description
             "MLPPP inner PPP protocol field compression";
         }
         leaf sequence-number-format {
           type string;
         }
         leaf fragment-threshold {
           type int32;
         }
         leaf minimum-links {
           type int32;
         }
         leaf interleave-fragments {
           type string;
         }
         leaf multilink-classes {
           type int32;
           description
             "Number of multilink classes";
         }
         leaf link-layer-overhead {
           type string;
           description
             "Link layer overhead";
         }
       }
       container multilink-bundle-errors {
         description
           "Multilink bundle errors";
         leaf packet-drops {
           type int32;
           description
             "Number of packets dropped";
         }
         leaf packet-drop-bytes {
           type int32;
           description
             "Number of bytes in dropped packets";
         }
         leaf fragment-drops {
           type int32;
           description
             "Number of fragments dropped";
         }
         leaf fragment-drop-bytes {
           type int32;
           description
             "Number of bytes in dropped fragments";
         }
         leaf mrru-exceeded {
           type int32;
           description
             "Number of assembled packets that exceeded MRRU";
         }
         leaf processing-errors {
           type int32;
           description
             "Number of errors encountered in assembling packets";
         }
       }
       container multilink-traffic-statistics {
         container bundle {
           container multilink-frames {
             description
               "Link-pic bound frame statistics for multilink bundles and 
               classes";
             leaf input-frames {
               type int32;
             }
             leaf input-fps {
               type int32;
             }
             leaf input-bytes {
               type int32;
             }
             leaf input-bps {
               type int32;
             }
             leaf output-frames {
               type int32;
             }
             leaf output-fps {
               type int32;
             }
             leaf output-bytes {
               type int32;
             }
             leaf output-bps {
               type int32;
             }
           }
           container network-frames {
             description
               "Internet/RE bound frame statistics for multilink bundles and
               classes";
             leaf input-frames {
               type int32;
             }
             leaf input-fps {
               type int32;
             }
             leaf input-bytes {
               type int32;
             }
             leaf input-bps {
               type int32;
             }
             leaf output-frames {
               type int32;
             }
             leaf output-fps {
               type int32;
             }
             leaf output-bytes {
               type int32;
             }
             leaf output-bps {
               type int32;
             }
           }
           container network-v6-frames {
             description
               "Transit IPV6 statistics for multilink bundles";
             leaf inputv6-packets {
               type int32;
             }
             leaf inputv6-bytes {
               type int32;
             }
             leaf outputv6-packets {
               type int32;
             }
             leaf outputv6-bytes {
               type int32;
             }
           }
         }
         container class {
           description
             "Multilink class traffic statistics";
           container class-info {
             description
               "Multilink class information";
             leaf multilink-class-id {
               type int32;
               description
                 "Multilink class ID";
             }
           }
           container multilink-frames {
             description
               "Link-pic bound frame statistics for multilink bundles and 
               classes";
             leaf input-frames {
               type int32;
             }
             leaf input-fps {
               type int32;
             }
             leaf input-bytes {
               type int32;
             }
             leaf input-bps {
               type int32;
             }
             leaf output-frames {
               type int32;
             }
             leaf output-fps {
               type int32;
             }
             leaf output-bytes {
               type int32;
             }
             leaf output-bps {
               type int32;
             }
           }
           container network-frames {
             description
               "Internet/RE bound frame statistics for multilink bundles and
               classes";
             leaf input-frames {
               type int32;
             }
             leaf input-fps {
               type int32;
             }
             leaf input-bytes {
               type int32;
             }
             leaf input-bps {
               type int32;
             }
             leaf output-frames {
               type int32;
             }
             leaf output-fps {
               type int32;
             }
             leaf output-bytes {
               type int32;
             }
             leaf output-bps {
               type int32;
             }
           }
         }
         list link {
           key "name";
           leaf name {
             type string;
             description
               "Name of this item";
           }
           leaf down {
             type empty;
             description
               "Link is down";
           }
           leaf link-uptime {
             type string;
             description
               "Total uptime for the member link";
           }
           leaf input-frames {
             type int32;
           }
           leaf input-fps {
             type int32;
           }
           leaf input-bytes {
             type int32;
           }
           leaf input-bps {
             type int32;
           }
           leaf output-frames {
             type int32;
           }
           leaf output-fps {
             type int32;
           }
           leaf output-bytes {
             type int32;
           }
           leaf output-bps {
             type int32;
           }
         }
         container multilink-detail-statistics {
           container bundle-detail {
             container fragments {
               description
                 "Fragment statistics for multilink bundles and classes";
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
             container non-fragments {
               description
                 "Non-fragment statistics for multilink bundles and classes";
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
             container lfi {
               description
                 "LFI frame statistics for multilink bundles and classes";
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
           }
           container class-detail {
             container class-info {
               description
                 "Multilink class information";
               leaf multilink-class-id {
                 type int32;
                 description
                   "Multilink class ID";
               }
             }
             container fragments {
               description
                 "Fragment statistics for multilink bundles and classes";
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
             container non-fragments {
               description
                 "Non-fragment statistics for multilink bundles and classes";
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
           }
         }
         container crtp {
           container crtp-sessions {
             leaf input-frames {
               type int32;
             }
             leaf output-frames {
               type int32;
             }
           }
           list crtp-statistics {
             key "name";
             leaf name {
               type string;
               description
                 "Name of this item";
             }
             leaf input-frames {
               type int32;
             }
             leaf input-fps {
               type int32;
             }
             leaf input-bytes {
               type int32;
             }
             leaf input-bps {
               type int32;
             }
             leaf output-frames {
               type int32;
             }
             leaf output-fps {
               type int32;
             }
             leaf output-bytes {
               type int32;
             }
             leaf output-bps {
               type int32;
             }
           }
         }
       }
       container statistics-account-overhead {
         description
           "Statistics account overhead information";
         leaf ingress-account-overhead {
           type int32;
           description
             "Ingress Statistics account overhead information";
         }
         leaf egress-account-overhead {
           type int32;
           description
             "Egress Statistics account overhead information";
         }
       }
       container traffic-statistics {
         leaf input-bps {
           type int32;
         }
         leaf input-pps {
           type int32;
         }
         leaf output-bps {
           type int32;
         }
         leaf output-pps {
           type int32;
         }
         leaf input-packets {
           type uint64;
         }
         leaf output-packets {
           type uint64;
         }
         container ipv4-traffic-statistics {
           leaf input-bps {
             type int32;
           }
           leaf output-bps {
             type int32;
           }
           leaf input-pps {
             type int32;
           }
           leaf output-pps {
             type int32;
           }
           leaf input-bytes {
             type int32;
           }
           leaf output-bytes {
             type int32;
           }
           leaf input-packets {
             type uint64;
           }
           leaf output-packets {
             type uint64;
           }
         }
         leaf input-bytes {
           type int32;
         }
         leaf output-bytes {
           type int32;
         }
         container ipv6-transit-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-traffic-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-total-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
       }
       container multicast-statistics {
         description
           "Multicast statistics for interface";
         leaf multicast-statistics-header {
           type empty;
         }
         container ipv4-multicast-statistics {
           description
             "IPV4 multicast statistics for interface";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-multicast-statistics {
           description
             "IPV6 multicast statistics for interface";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
       }
       container ingress-traffic-statistics {
         description
           "Traffic statistics at ingress before entering Packet Forwarding 
           Engine";
         leaf input-bps {
           type int32;
         }
         leaf input-pps {
           type int32;
         }
         leaf input-drop-bps {
           type int32;
           description
             "Drop rate at ingress in bits per second ";
         }
         leaf input-drop-pps {
           type int32;
           description
             "Drop rate at ingress in packets per second ";
         }
         leaf input-bytes {
           type int32;
         }
         leaf input-packets {
           type uint64;
         }
         leaf input-drop-bytes {
           type int32;
           description
             "Drop statistics at ingress in bytes";
         }
         leaf input-drop-packets {
           type int32;
           description
             "Drop statistics at ingress in packets";
         }
       }
       container local-traffic-statistics {
         description
           "Statistics for locally originated traffic";
         leaf input-bytes {
           type int32;
         }
         leaf input-bps {
           type int32;
         }
         leaf output-bytes {
           type int32;
         }
         leaf output-bps {
           type int32;
         }
         leaf input-packets {
           type uint64;
         }
         leaf input-pps {
           type int32;
         }
         leaf output-packets {
           type uint64;
         }
         leaf output-pps {
           type int32;
         }
         container ipv4-local-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-local-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
       }
       container transit-traffic-statistics {
         description
           "Statistics for traffic passing through the Packet Forwarding 
           Engine";
         leaf input-bytes {
           type int32;
         }
         leaf input-bps {
           type int32;
         }
         leaf output-bytes {
           type int32;
         }
         leaf output-bps {
           type int32;
         }
         leaf input-packets {
           type uint64;
         }
         leaf input-pps {
           type int32;
         }
         leaf output-packets {
           type uint64;
         }
         leaf output-pps {
           type int32;
         }
         container ipv4-transit-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-transit-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-total-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
       }
       container layer3-statistics {
         container l3-ipv4-unicast-statistics {
           description
             "Statistics for traffic passing through the packet forwarding 
             engine";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container l3-ipv4-multicast-statistics {
           description
             "Statistics for traffic passing through the packet forwarding 
             engine";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container l3-ipv6-unicast-statistics {
           description
             "Statistics for traffic passing through the packet forwarding 
             engine";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container l3-ipv6-multicast-statistics {
           description
             "Statistics for traffic passing through the packet forwarding 
             engine";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
       }
       container keepalive-config {
         description
           "Configured keepalive settings on this interface";
         leaf keepalive-interval {
           type int32;
         }
         leaf keepalive-up-count {
           type int32;
         }
         leaf keepalive-down-count {
           type int32;
         }
       }
       container keepalive-statistics {
         description
           "Keepalive statistics for this interface";
         leaf keepalive-lmi-descriptor {
           type string;
         }
         leaf keepalive-input-count {
           type int32;
         }
         leaf keepalive-input-time {
           type string;
         }
         leaf keepalive-output-count {
           type int32;
         }
         leaf keepalive-output-time {
           type string;
         }
       }
       container ppp-flags {
         leaf iff-ppp-flags-acfc {
           type empty;
         }
         leaf iff-ppp-flags-pfc {
           type empty;
         }
       }
       list ncp-information {
         description
           "Network Control Protocol information";
         leaf ncp-protocol {
           type string;
           description
             "Network protocol for this NCP instance";
         }
         leaf ncp-state {
           type string;
           description
             "State of this NCP instance";
         }
       }
       container virtual-circuit-information {
         description
           "Operational information and statistics for a virtual circuit";
         leaf vpi {
           type int32;
           description
             "Virtual path identifier";
         }
         leaf vci {
           type int32;
           description
             "Virtual circuit identifier";
         }
         leaf psn-tag {
           type string;
           description
             "VPI/VCI swapping configuration";
         }
         leaf psn-vpi {
           type int32;
           description
             "PSN virtual path identifier";
         }
         leaf psn-vci {
           type int32;
           description
             "PSN virtual circuit identifier";
         }
         leaf trunk {
           type int32;
           description
             "ATM trunk identifier";
         }
         leaf dlci {
           type int32;
         }
         leaf swapping {
           type string;
           description
             "VPI/VCI swapping configuration";
         }
         leaf trunk-bandwidth {
           type int32;
           description
             "ATM trunk bandwidth";
         }
         leaf atm-tm-cbr {
           type empty;
           description
             "Constant bit rate";
         }
         leaf atm-tm-vbr {
           type empty;
           description
             "Variable bit rate";
         }
         leaf atm-tm-rtvbr {
           type empty;
           description
             "Real-time variable bit rate";
         }
         leaf peak {
           type int32;
         }
         leaf sustained {
           type int32;
         }
         leaf burst {
           type int32;
         }
         leaf cdvt {
           type int32;
         }
         leaf queue-limit {
           type int32;
         }
         leaf down-time {
           type int32;
           description
             "Total down time for this circuit";
         }
         leaf last-down-time {
           type int32;
           description
             "Time elapsed since circuit last went down";
         }
         leaf ifvc-epd {
           type int32;
           description
             "Early packet discard threshold";
         }
         leaf ifvc-weight {
           type int32;
           description
             "Transmit weight";
         }
         leaf ifvc-epd-plp0 {
           type int32;
           description
             "Early packet discard threshold for PLP 0";
         }
         leaf ifvc-epd-plp1 {
           type int32;
           description
             "Early packet discard threshold for PLP 1";
         }
         container vci-range {
           description
             "ATM VCI range";
           leaf vpi {
             type int32;
             description
               "Virtual path identifier";
           }
           leaf start-vci {
             type int32;
             description
               "ATM VCI range's start value";
           }
           leaf end-vci {
             type int32;
             description
               "ATM VCI range's end value";
           }
         }
         container ifvc-flags {
           leaf ifvc-down {
             type empty;
           }
           leaf ifvc-none {
             type empty;
           }
           leaf ifvc-active {
             type empty;
           }
           leaf ifvc-closed {
             type empty;
           }
           leaf ifvc-inverse-arp {
             type empty;
           }
           leaf ifvc-ilmi {
             type empty;
           }
           leaf ifvc-oam {
             type empty;
           }
           leaf ifvc-shaping {
             type empty;
           }
           leaf ifvc-passiveoam {
             type empty;
           }
           leaf ifvc-multicast {
             type empty;
           }
           leaf ifvc-ccc-down {
             type empty;
           }
           leaf ifvc-configured {
             type empty;
             description
               "DCE-end is configured";
           }
           leaf ifvc-unconfigured {
             type empty;
             description
               "DCE-end is unconfigured";
           }
           leaf generic-value {
             type int32;
             description
               "Hexadecimal value of unknown flag bits";
           }
         }
         container ifvc-multipoint-destination {
           leaf multipoint-address {
             type string;
             description
               "Protocol address of the remote side of this connection";
           }
         }
         container oam-parameters {
           leaf period {
             type int32;
           }
           leaf up-count {
             type int32;
           }
           leaf down-count {
             type int32;
           }
         }
         container oam-statistics {
           description
             "Container tag for OAM statistics";
           leaf oam-total-received-count {
             type int32;
           }
           leaf oam-total-transmitted-count {
             type int32;
           }
           leaf oam-total-received-count-4 {
             type int32;
           }
           leaf oam-total-transmitted-count-4 {
             type int32;
           }
           leaf oam-loopback-received-count {
             type int32;
           }
           leaf oam-loopback-transmitted-count {
             type int32;
           }
           leaf oam-loopback-received-last {
             type string;
           }
           leaf oam-loopback-transmitted-last {
             type string;
           }
           leaf oam-rdi-received-count {
             type int32;
           }
           leaf oam-rdi-transmitted-count {
             type int32;
           }
           leaf oam-rdi-received-last {
             type string;
           }
           leaf oam-rdi-transmitted-last {
             type string;
           }
           leaf oam-ais-received-count {
             type int32;
           }
           leaf oam-ais-transmitted-count {
             type int32;
           }
           leaf oam-ais-received-last {
             type string;
           }
           leaf oam-ais-transmitted-last {
             type string;
           }
         }
         container traffic-statistics {
           leaf input-bps {
             type int32;
           }
           leaf input-pps {
             type int32;
           }
           leaf output-bps {
             type int32;
           }
           leaf output-pps {
             type int32;
           }
           leaf input-packets {
             type uint64;
           }
           leaf output-packets {
             type uint64;
           }
           container ipv4-traffic-statistics {
             leaf input-bps {
               type int32;
             }
             leaf output-bps {
               type int32;
             }
             leaf input-pps {
               type int32;
             }
             leaf output-pps {
               type int32;
             }
             leaf input-bytes {
               type int32;
             }
             leaf output-bytes {
               type int32;
             }
             leaf input-packets {
               type uint64;
             }
             leaf output-packets {
               type uint64;
             }
           }
           leaf input-bytes {
             type int32;
           }
           leaf output-bytes {
             type int32;
           }
           container ipv6-transit-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-traffic-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-total-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
         }
         container atm-policer-statistics {
           leaf non-conform-clp0-cells {
             type int32;
             description
               "UPC non-conforming ATM CLP0 cell";
           }
           leaf non-conform-clp1-cells {
             type int32;
             description
               "UPC non-conforming ATM CLP1 cell";
           }
           leaf tagged-cells {
             type int32;
             description
               "UPC tagged cell";
           }
         }
         container atm-statistics {
           leaf vc-queue-drops {
             type int32;
           }
         }
         container atm-cos-information {
           leaf vc-cos-mode {
             type string;
             description
               "Virtual circuit CoS scheduling mode";
           }
           list atm-cos-queue {
             container atm-cos-queue-parameters {
               leaf cos-forwarding-class-name {
                 type string;
                 description
                   "Forwarding class name associated with queue";
               }
               leaf cos-queue-number {
                 type int32;
                 description
                   "Queue number";
               }
               leaf scheduling-priority {
                 type string;
                 description
                   "Scheduling priority";
               }
               leaf transmit-weight-cells {
                 type int32;
                 description
                   "Weight to apply to scheduling as number of cells";
               }
               leaf transmit-weight-percent {
                 type int32;
                 description
                   "Weight to apply to scheduling as fill percentage";
               }
               leaf epd-threshold {
                 type int32;
                 description
                   "Early packet drop threshold";
               }
               leaf epd-threshold-plp0 {
                 type int32;
                 description
                   "Early packet drop threshold for PLP 0";
               }
               leaf epd-threshold-plp1 {
                 type int32;
                 description
                   "Early packet drop threshold for PLP 1";
               }
               container linear-red-drop-profile {
                 leaf queue-depth {
                   type int32;
                   description
                     "Maximum queue depth";
                 }
                 leaf low-red {
                   type int32;
                   description
                     "Fill level percentage when linear RED is applied for 
                     low PLP";
                 }
                 leaf high-red {
                   type int32;
                   description
                     "Fill level percentage when linear RED is applied for 
                     high PLP";
                 }
                 leaf max-low-red {
                   type int32;
                   description
                     "Fill level percentage with 100% packet drop for low 
                     PLP";
                 }
                 leaf max-high-red {
                   type int32;
                   description
                     "Fill level percentage with 100% packet drop for high 
                     PLP";
                 }
               }
             }
             container atm-cos-queue-statistics {
               leaf atm-output-bytes {
                 type int32;
               }
               leaf atm-output-packets {
                 type int32;
               }
               leaf atm-packet-drops {
                 type int32;
               }
             }
             container atm-cos-plp-statistics {
               leaf atm-plp0-output-bytes {
                 type int32;
               }
               leaf atm-plp1-output-bytes {
                 type int32;
               }
               leaf atm-plp0-output-packets {
                 type int32;
               }
               leaf atm-plp1-output-packets {
                 type int32;
               }
               leaf atm-plp0-byte-drops {
                 type int32;
               }
               leaf atm-plp1-byte-drops {
                 type int32;
               }
               leaf atm-plp0-packet-drops {
                 type int32;
               }
               leaf atm-plp1-packet-drops {
                 type int32;
               }
             }
           }
         }
         container in-arp-statistics {
           description
             "Container tag for ARP statistics";
           leaf received-count {
             type int32;
             description
               "Number of ARPs received";
           }
           leaf transmitted-count {
             type int32;
             description
               "Number of ARPs sent";
           }
           leaf denied-count {
             type int32;
             description
               "Number of ARPs denied";
           }
           leaf operation-not-supported-count {
             type int32;
             description
               "Number of ARPs with operation not supported";
           }
           leaf bad-packet-length-count {
             type int32;
             description
               "Number of ARPs with bad packet length";
           }
           leaf bad-protocol-count {
             type int32;
             description
               "Number of ARPs with bad protocol";
           }
           leaf bad-protocol-length-count {
             type int32;
             description
               "Number of ARPs with bad protocol length";
           }
           leaf bad-hardware-length-count {
             type int32;
             description
               "Number of ARPs with bad hardware length";
           }
           leaf dropped-count {
             type int32;
             description
               "Number of ARPs dropped";
           }
           leaf last-received {
             type string;
             description
               "Time an ARP was last received";
           }
           leaf last-transmitted {
             type string;
             description
               "Time an ARP was last sent";
           }
         }
         container dlci-statistics {
           description
             "DLCI statistics for an interface";
           leaf dlci-active {
             type int32;
             description
               "Number of DLCIs in active state";
           }
           leaf dlci-inactive {
             type int32;
             description
               "Number of DLCIs in inactive state";
           }
         }
       }
       list filter-information {
         leaf-list filter-input {
           type string;
           description
             "Name of the input filter";
         }
         leaf-list filter-input-precedence {
           type uint32;
           description
             "Precedence of the input filter";
         }
         leaf-list filter-output {
           type string;
           description
             "Name of the output filter";
         }
         leaf-list filter-output-precedence {
           type uint32;
           description
             "Precedence of the output filter";
         }
       }
       container allowed-host-inbound-traffic {
         description
           "List of allowed system services and protocols";
         leaf inbound-all-protocols {
           type empty;
           description
             "All protocols";
         }
         leaf inbound-any-service {
           type empty;
           description
             "Any service";
         }
         leaf inbound-bootp {
           type empty;
           description
             "Bootp and dhcp relay-agent service";
         }
         leaf inbound-bfd {
           type empty;
           description
             "Bidirectional Forwarding Detection";
         }
         leaf inbound-bgp {
           type empty;
           description
             "Border Gateway Protocol";
         }
         leaf inbound-dns {
           type empty;
           description
             "DNS and DNS-proxy service";
         }
         leaf inbound-dvmrp {
           type empty;
           description
             "Distance Vector Multicast Routing Protocol";
         }
         leaf inbound-igmp {
           type empty;
           description
             "Internet Group Management Protocol";
         }
         leaf inbound-ldp {
           type empty;
           description
             "Label Distribution Protocol";
         }
         leaf inbound-msdp {
           type empty;
           description
             "Multicast Source Discovery Protocol";
         }
         leaf inbound-nhrp {
           type empty;
           description
             "Next Hop Resolution Protocol";
         }
         leaf inbound-ospf {
           type empty;
           description
             "Open Shortest Path First";
         }
         leaf inbound-ospf3 {
           type empty;
           description
             "Open Shortest Path First version 3";
         }
         leaf inbound-pgm {
           type empty;
           description
             "Pragmatic General Multicast";
         }
         leaf inbound-pim {
           type empty;
           description
             "Protocol Independent Multicast";
         }
         leaf inbound-rip {
           type empty;
           description
             "Routing Information Protocol";
         }
         leaf inbound-ripng {
           type empty;
           description
             "Routing Information Protocol next generation";
         }
         leaf inbound-router-discovery {
           type empty;
           description
             "Router Discovery";
         }
         leaf inbound-rsvp {
           type empty;
           description
             "Resource Reservation Protocol";
         }
         leaf inbound-sap {
           type empty;
           description
             "Session Announcement Protocol";
         }
         leaf inbound-vrrp {
           type empty;
           description
             "Virtual Router Redundancy Protocol";
         }
         leaf inbound-all-services {
           type empty;
           description
             "All system services";
         }
         leaf inbound-dhcp {
           type empty;
           description
             "Dynamic Host Configuration Protocol";
         }
         leaf inbound-finger {
           type empty;
           description
             "Finger service";
         }
         leaf inbound-ftp {
           type empty;
           description
             "File Transfer Protocol";
         }
         leaf inbound-tftp {
           type empty;
           description
             "Trivial File Transfer Protocol";
         }
         leaf ident-reset {
           type empty;
           description
             "Send back TCP RST to IDENT request for port 113";
         }
         leaf inbound-http {
           type empty;
           description
             "Web management service using HTTP";
         }
         leaf inbound-https {
           type empty;
           description
             "Web management service using HTTP secured by SSL";
         }
         leaf inbound-ike {
           type empty;
           description
             "Internet Key Exchange";
         }
         leaf inbound-netconf {
           type empty;
           description
             "NETCONF service";
         }
         leaf inbound-ping {
           type empty;
           description
             "Internet Control Message Protocol echo requests";
         }
         leaf inbound-reverse-telnet {
           type empty;
           description
             "Reverse telnet service";
         }
         leaf inbound-reverse-ssh {
           type empty;
           description
             "Reverse SSH service";
         }
         leaf inbound-rlogin {
           type empty;
           description
             "Rlogin service";
         }
         leaf inbound-rpm {
           type empty;
           description
             "Real-time performance monitoring";
         }
         leaf inbound-rsh {
           type empty;
           description
             "Rsh service";
         }
         leaf inbound-snmp {
           type empty;
           description
             "Simple Network Management Protocol service";
         }
         leaf inbound-snmp-trap {
           type empty;
           description
             "Simple Network Management Protocol traps";
         }
         leaf inbound-ssh {
           type empty;
           description
             "SSH service";
         }
         leaf inbound-telnet {
           type empty;
           description
             "Telnet service";
         }
         leaf inbound-traceroute {
           type empty;
           description
             "Traceroute service";
         }
         leaf inbound-xnm-clear-text {
           type empty;
           description
             "JUNOScript API for unencrypted traffic over TCP";
         }
         leaf inbound-xnm-ssl {
           type empty;
           description
             "JUNOScript API service over SSL";
         }
         leaf inbound-lsping {
           type empty;
           description
             "Label Switched Path ping service";
         }
         leaf inbound-lsselfping {
           type empty;
           description
             "Label Switched Path self ping service";
         }
         leaf inbound-ntp {
           type empty;
           description
             "Network Time Protocol service";
         }
         leaf inbound-sip {
           type empty;
           description
             "Session Initiation Protocol service";
         }
         leaf inbound-dhcpv6 {
           type empty;
           description
             "Dynamic Host Configuration Protocol for IPv6 service";
         }
         leaf inbound-r2cp {
           type empty;
           description
             "Radio Router Control Protocol service";
         }
         leaf inbound-webapi-clear-text {
           type empty;
           description
             "Webapi service using http";
         }
         leaf inbound-webapi-ssl {
           type empty;
           description
             "Webapi service using HTTP secured by SSL";
         }
         leaf inbound-tcp-encap {
           type empty;
           description
             "Tcp encapsulation service";
         }
         leaf inbound-sdwan-appqoe {
           type empty;
           description
             "Sdwan Appqoe service";
         }
         leaf inbound-high-availability {
           type empty;
           description
             "High Availability  service";
         }
       }
       list address-family {
         key "address-family-name";
         leaf compression-device-name {
           type string;
           description
             "Name of the link service device";
         }
         leaf address-family-name {
           type string;
         }
         leaf multilink-bundle-name {
           type string;
           description
             "Name of the multilink bundle for this address family";
         }
         leaf as-bundle-name {
           type string;
           description
             "Name of the aggregated SONET bundle for this address family";
         }
         leaf ae-bundle-name {
           type string;
           description
             "Name of the aggregated Ethernet bundle";
         }
         leaf es-sa-name {
           type string;
           description
             "Name of the IPSec security association for this address family";
         }
         leaf mtu {
           type string;
           description
             "MTU size on this interface";
         }
         leaf maximum-labels {
           type uint32;
           description
             "Maximum labels on MPLS iffamily";
         }
         leaf generation {
           type string;
           description
             "Generation number used to distinguish between successive 
             instances of this interface";
         }
         leaf route-table {
           type int32;
         }
         leaf vpls-mesh-group {
           type string;
         }
         leaf es-sa-fail-count {
           type int32;
           description
             "Number of failures for IPSec security association for this 
             family";
         }
         leaf es-sa-xmt-seq-num {
           type int32;
           description
             "Transmit sequence number of IPSec security association family";
         }
         leaf es-sa-recv-seq-num {
           type int32;
           description
             "Receive sequence number of IPSec security association family";
         }
         leaf evpn-multihomed-status {
           type string;
         }
         leaf evpn-mh-esi-sh-label {
           type string;
         }
         leaf iff-next-hop {
           type int32;
           description
             "Interface family next-hop";
         }
         leaf iff-vpls-status {
           type string;
           description
             "Interface family vpls status";
         }
         leaf max-local-cache {
           type uint32;
           description
             "Max local nh cache size";
         }
         leaf new-hold-limit {
           type uint32;
           description
             "Max limit on new unresolved nh";
         }
         leaf intf-curr-cnt {
           type uint32;
           description
             "Current nh total cache size on this interface";
         }
         leaf intf-unresolved-cnt {
           type uint32;
           description
             "Current new unresolved nh cache size on this interface";
         }
         leaf intf-dropcnt {
           type uint32;
           description
             "Current interface nh drop count";
         }
         leaf intf-hold-nh-dropcnt {
           type uint32;
           description
             "Current interface Hold NextHop drop count by RED";
         }
         leaf ft-iff-dest-port {
           type uint32;
           description
             "Destination UDP port to be used for this family";
         }
         leaf mlppp-service-interface {
           type string;
           description
             "Name of the multilink service interface for this address 
             family";
         }
         leaf mlppp-service-dev-pool {
           type string;
           description
             "Name of the multilink service device pool for this address 
             family";
         }
         leaf mlppp-dynamic-profile {
           type string;
           description
             "Name of the multilink dynamic profile for this address family";
         }
         leaf arp-respond-any-local-address {
           type string;
           description
             "Respond to ARP requests for any local address";
         }
         container address-family-flags {
           leaf ifff-none {
             type empty;
           }
           leaf ifff-primary {
             type empty;
           }
           leaf ifff-redirects {
             type empty;
           }
           leaf ifff-no-redirects {
             type empty;
           }
           leaf ifff-no-neighbor-learn {
             type empty;
           }
           leaf ifff-targeted-broadcast {
             type empty;
           }
           leaf ifff-sendbcast-pkt-to-re {
             type empty;
           }
           leaf ifff-hard-down {
             type empty;
           }
           leaf ifff-down {
             type empty;
           }
           leaf ifff-up {
             type empty;
           }
           leaf ifff-func1 {
             type empty;
           }
           leaf ifff-func2 {
             type empty;
           }
           leaf ifff-is-primary {
             type empty;
           }
           leaf ifff-recv-options {
             type empty;
           }
           leaf ifff-recv-ttl-exceeded {
             type empty;
           }
           leaf ifff-dst-class-usage {
             type empty;
           }
           leaf ifff-src-class-input {
             type empty;
           }
           leaf ifff-src-class-output {
             type empty;
           }
           leaf ifff-mtu-user-conf {
             type empty;
           }
           leaf ifff-mac-validate-strict {
             type empty;
           }
           leaf ifff-mac-validate-loose {
             type empty;
           }
           leaf ifff-rpf-check {
             type empty;
           }
           leaf ifff-rpf-loose-mode {
             type empty;
           }
           leaf ifff-sample-input {
             type empty;
           }
           leaf ifff-sample-output {
             type empty;
           }
           leaf ifff-no-asynch-notification {
             type empty;
           }
           leaf ifff-negotiate-address {
             type empty;
           }
           leaf ifff-port-mode-trunk {
             type empty;
           }
           leaf ifff-inter-switch-link {
             type empty;
           }
           leaf ifff-mtu-protocol-adj {
             type empty;
           }
           leaf ifff-unnumbered {
             type empty;
           }
           leaf ifff-tcc-mpls {
             type empty;
           }
           leaf ifff-tcc-inet {
             type empty;
           }
           leaf ifff-tcc-inet6 {
             type empty;
           }
           leaf ifff-tcc-iso {
             type empty;
           }
           leaf ifff-port-mode-isid-trunk {
             type empty;
           }
           leaf iff-clear-df {
             type empty;
           }
           leaf ifff-tunnel-loopback {
             type empty;
           }
           leaf ifff-class-based-filtering-scu {
             type empty;
           }
           leaf ifff-class-based-filtering-dcu {
             type empty;
           }
           leaf internal-flags {
             type string;
             description
               "Hexadecimal value of internal flag bits";
           }
           leaf generic-value {
             type int32;
             description
               "Hexadecimal value of unknown flag bits";
           }
         }
         list address-family-unnumbered {
           key "unnumbered-family-donor-interface-name";
           description
             "Information about an unnumbered address family";
           leaf unnumbered-family-donor-interface-name {
             type string;
             description
               "Donor interface name";
           }
           leaf unnumbered-family-donor-interface-index {
             type string;
             description
               "Donor interface index";
           }
           leaf unnumbered-family-preferred-source-address {
             type string;
             description
               "Unnumbered interface preferred source address";
           }
         }
         container pppoe-underlying-information {
           description
             "PPPoE Underlying information";
           list pppoe-underlying-interface {
             leaf dynamic-profile {
               type string;
               description
                 "Dynamic Profile name";
             }
             leaf service-name-table {
               type string;
               description
                 "Name of Service Name Table";
             }
             leaf max-sessions {
               type int32;
               description
                 "Maximum number of PPPoE sessions";
             }
             leaf max-sessions-vsa-ignore {
               type string;
               description
                 "Ignore max-sessions VSA";
             }
             leaf duplicate-protection {
               type string;
               description
                 "Duplicate protection mode";
             }
             leaf short-cycle-protection {
               type string;
               description
                 "Short cycle protection mode";
             }
             leaf direct-connect {
               type string;
               description
                 "Direct connect mode";
             }
             leaf ac-name {
               type string;
               description
                 "Access Concentrator name";
             }
             leaf underlying-interface-name {
               type string;
               description
                 "Underlying interface name";
             }
             leaf underlying-interface-index {
               type string;
               description
                 "Underlying interface index";
             }
             leaf encapsulation-type-identifier {
               type string;
               description
                 "Encapsulation type identifier";
             }
             leaf state {
               type string;
               description
                 "State";
             }
             leaf active-sessions {
               type int32;
               description
                 "Number of active PPPoE sessions";
             }
             leaf aci-autosensing {
               type string;
               description
                 "ACI VLAN Autosensing mode";
             }
             leaf line-identity-autosensing {
               type string;
               description
                 "Line Identity Autosensing mode";
             }
           }
         }
         list filter-information {
           leaf-list filter-input {
             type string;
             description
               "Name of the input filter";
           }
           leaf-list filter-input-precedence {
             type uint32;
             description
               "Precedence of the input filter";
           }
           leaf-list filter-output {
             type string;
             description
               "Name of the output filter";
           }
           leaf-list filter-output-precedence {
             type uint32;
             description
               "Precedence of the output filter";
           }
         }
         list policer-information {
           description
             "Interface policer information";
           leaf policer-input {
             type string;
             description
               "Name of the input policer";
           }
           leaf policer-output {
             type string;
             description
               "Name of the output policer";
           }
         }
         list interface-address {
           key "ifa-local";
           leaf-list interface-address.heading {
             type string;
           }
           leaf ifa-destination {
             type string;
             description
               "Protocol address of the remote side of this connection";
           }
           leaf ifa-local {
             type string;
             description
               "Protocol address on this interface";
           }
           leaf ifa-broadcast {
             type string;
             description
               "Network broadcast address";
           }
           leaf ifa-primary-dns {
             type string;
             description
               "Primary DNS server address";
           }
           leaf ifa-primary-nbns {
             type string;
             description
               "Primary Netbios Name server address";
           }
           leaf ifa-secondary-dns {
             type string;
             description
               "Secondary DNS server address";
           }
           leaf ifa-secondary-nbns {
             type string;
             description
               "Secondary Netbios Name server address";
           }
           leaf ifa-address-pool {
             type string;
             description
               "Address pool name";
           }
           leaf generation {
             type string;
             description
               "Generation number used to distinguish between successive 
               instances of this interface";
           }
           container ifa-flags {
             leaf ifaf-none {
               type empty;
             }
             leaf ifaf-primary {
               type empty;
             }
             leaf ifaf-preferred {
               type empty;
             }
             leaf ifaf-master-only {
               type empty;
             }
             leaf ifaf-down {
               type empty;
             }
             leaf ifaf-kernel {
               type empty;
             }
             leaf ifaf-current-default {
               type empty;
             }
             leaf ifaf-current-preferred {
               type empty;
             }
             leaf ifaf-current-primary {
               type empty;
             }
             leaf ifaf-duplicate {
               type empty;
             }
             leaf ifaf-webauth-http {
               type empty;
             }
             leaf generic-value {
               type int32;
               description
                 "Hexadecimal value of unknown flag bits";
             }
             leaf internal-flags {
               type string;
               description
                 "Hexadecimal value of internal flag bits";
             }
           }
           container in6-addr-flags {
             leaf ifaf-none {
               type empty;
             }
             leaf in6-anycast {
               type empty;
             }
             leaf in6-tentative {
               type empty;
             }
             leaf in6-duplicate {
               type empty;
             }
             leaf in6-detached {
               type empty;
             }
             leaf in6-deprecated {
               type empty;
             }
             leaf in6-nodad {
               type empty;
             }
             leaf in6-temporary {
               type empty;
             }
             leaf in6-autoconf {
               type empty;
             }
             leaf in6-nopfxmgmt {
               type empty;
             }
           }
         }
         container mac-validate-statistics {
           description
             "SRC MAC validate statistics";
           leaf mac-validate-packets {
             type int32;
             description
               "Number of packets that have failed the mac-validate check";
           }
           leaf mac-validate-bytes {
             type int32;
             description
               "Number of bytes that have failed the mac-validate check";
           }
         }
         container route-rpf-statistics {
           description
             "Unicast reverse-path forwarding (RPF) statistics";
           leaf route-rpf-packets {
             type int32;
             description
               "Number of packets that have failed the RPF check";
           }
           leaf route-rpf-bytes {
             type int32;
             description
               "Number of bytes that have failed the RPF check";
           }
         }
         container destination-class-statistics {
           description
             "Destination class usage (DCU) statistics";
           list destination-class {
             description
               "DCU statistics for a single class";
             leaf dcu-class-name {
               type string;
               description
                 "Name of DCU class";
             }
             leaf dcu-class-packets {
               type int32;
               description
                 "Number of packets counted by DCU for this class";
             }
             leaf dcu-class-bytes {
               type int32;
               description
                 "Number of bytes counted by DCU for this class";
             }
             leaf dcu-class-pps {
               type int32;
               description
                 "Packet-per-seconds counted by DCU for this class";
             }
             leaf dcu-class-bps {
               type int32;
               description
                 "Bit-per-seconds counted by DCU for this class";
             }
           }
         }
         container source-class-statistics {
           description
             "Source class usage (SCU) statistics";
           list source-class {
             description
               "SCU statistics for a single class";
             leaf scu-class-name {
               type string;
               description
                 "Name of SCU class";
             }
             leaf scu-class-packets {
               type int32;
               description
                 "Number of packets counted by SCU for this class";
             }
             leaf scu-class-bytes {
               type int32;
               description
                 "Number of bytes counted by SCU for this class";
             }
             leaf scu-class-pps {
               type int32;
               description
                 "Packet-per-seconds counted by SCU for this class";
             }
             leaf scu-class-bps {
               type int32;
               description
                 "Bit-per-seconds counted by SCU for this class";
             }
           }
         }
         list local-bias-information {
           leaf local-bias-vtep-ifl-name {
             type string;
             description
               "Interface name";
           }
           leaf local-bias-vtep-ifl-index {
             type uint32;
             description
               "Interface index";
           }
           leaf local-bias-vtep-address {
             type string;
             description
               "Protocol address of the connection";
           }
         }
       }
       list bridge-iff-properties {
         description
           "Information about Ethernet-switching address family";
       }
       container l2circuit-info {
         leaf out-of-sequence {
           type int32;
         }
         leaf denied-packets {
           type int32;
         }
         leaf cell-bundle-size {
           type int32;
         }
         leaf cell-bundle-timeout {
           type int32;
         }
         leaf cell-timeout-count {
           type int32;
         }
       }
       container irb-domain {
         leaf irb-routing-instance {
           type string;
           description
             "Name of the Routing Instance";
         }
         leaf irb-bridge {
           type string;
           description
             "Name of the Bridging Domain";
         }
       }
       container media-information {
         description
           "Information about media alarms";
         leaf media-type {
           type string;
           description
             "Type of media this information is for";
         }
         list media-alarm {
           leaf media-alarm-name {
             type string;
           }
           leaf media-alarm-count {
             type int32;
           }
           leaf media-alarm-seconds {
             type int32;
           }
           leaf media-alarm-state {
             type string;
           }
           leaf ce-counter-name {
             type string;
             description
               "Circuit Emulation counter information";
           }
           leaf ce-counter-packets {
             type int32;
             description
               "Circuit Emulation number of packets";
           }
           leaf ce-counter-bytes {
             type int32;
             description
               "Circuit Emulation number of bytes";
           }
           leaf ce-counter-count {
             type int32;
             description
               "Circuit Emulation number of event occurrences";
           }
         }
         leaf ds1-timeslots {
           type string;
         }
         leaf ds1-line-encoding {
           type string;
         }
         leaf ds1-byte-encoding {
           type string;
         }
         leaf ds1-data-inversion {
           type string;
         }
         leaf idle-cycle-flag {
           type string;
         }
         leaf start-end-flag {
           type string;
         }
         leaf ds0-byte-encoding {
           type string;
         }
         leaf ds0-data-inversion {
           type string;
         }
         leaf e3-data-inversion {
           type string;
         }
         leaf ds1-buildout {
           type string;
           description
             "Number of feet";
         }
       }
       container vtep-info {
         leaf vtep-type {
           type string;
           description
             "Type of VXLAN endpoint";
         }
         leaf vtep-address {
           type string;
           description
             "Protocol address of the connection";
         }
         leaf vtep-l2-routing-instance {
           type string;
           description
             "Name of the layer-2 routing instance";
         }
         leaf vtep-l3-routing-instance {
           type string;
           description
             "Name of the layer-3 routing instance";
         }
         leaf primary-vtep-address {
           type string;
           description
             "Primary Protocol address of the connection";
         }
         leaf vtep-token-count {
           type int32;
           description
             "VTEP additional tokens";
         }
         leaf-list vtep-token-array {
           type string;
           description
             "VTEP token array";
         }
       }
       container ft-info {
         leaf ft-dest-port {
           type int32;
           description
             "Destnation UDP port used in encap";
         }
         leaf ft-src-port-min {
           type int32;
           description
             "Source UDP port start range used in encap";
         }
         leaf ft-src-port-max {
           type int32;
           description
             "Source UDP port end range used in encap";
         }
         leaf ft-vnid {
           type int32;
           description
             "VNI value used in encap";
         }
         leaf ft-src-addr {
           type string;
           description
             "Source address used for encap";
         }
         leaf ft-dst-addr {
           type string;
           description
             "Destination address used for encap";
         }
         leaf ft-name {
           type string;
           description
             "Test interface name";
         }
         leaf ft-vlan-id {
           type int32;
           description
             "Vlan id of corresponding test interface";
         }
         leaf ft-mac {
           type string;
           description
             "Mac address";
         }
       }
       container rbeb-info {
         leaf rbeb-address {
           type string;
           description
             "Protocol address of the connection";
         }
         leaf rbeb-l2-routing-instance {
           type string;
           description
             "Name of the layer-2 routing instance";
         }
       }
       container macsec-statistics {
         description
           "MACSec Statistics ";
         leaf macsec-tx-sc-protected {
           type int32;
           description
             "Protected Secure Channel MACSec packets transmitted";
         }
         leaf macsec-tx-sc-encrypted {
           type int32;
           description
             "Encrypted Secure Channel MACSec packets transmitted";
         }
         leaf macsec-tx-sc-protectedbytes {
           type int32;
           description
             "Protected Secure Channel MACSec bytes transmitted";
         }
         leaf macsec-tx-sc-encryptedbytes {
           type int32;
           description
             "Encrypted Secure Channel MACSec bytes transmitted";
         }
         leaf macsec-rx-sc-ok {
           type int32;
           description
             "OK Secure Association MACSec packets received";
         }
         leaf macsec-rx-sc-validatedbytes {
           type int32;
           description
             "Validated Secure Association MACSec bytes received";
         }
         leaf macsec-rx-sc-decryptedbytes {
           type int32;
           description
             "Validated Secure Association MACSec bytes received";
         }
       }
       container security-input-flow-statistics {
         description
           "Flow input statistics for the interface";
         leaf flow-input-self-packets {
           type int32;
           description
             "Input Self packets";
         }
         leaf flow-input-icmp-packets {
           type int32;
           description
             "Input ICMP packets";
         }
         leaf flow-input-vpn-packets {
           type int32;
           description
             "Input VPN packets";
         }
         leaf flow-input-multicast-packets {
           type int32;
           description
             "Input multicast packets";
         }
         leaf flow-input-policy-bytes {
           type int32;
           description
             "Input policy bytes";
         }
         leaf flow-input-connections {
           type int32;
           description
             "Input connections";
         }
       }
       container security-output-flow-statistics {
         description
           "Flow output statistics for the interface";
         leaf flow-output-multicast-packets {
           type int32;
           description
             "Output multicast packets";
         }
         leaf flow-output-policy-bytes {
           type int32;
           description
             "Output bytes permitted by policy";
         }
       }
       container security-error-flow-statistics {
         description
           "Flow error statistics for the interface";
         leaf flow-error-policy-denied {
           type int32;
           description
             "Policy denied";
         }
         leaf flow-error-no-gate-parent {
           type int32;
           description
             "No parent for gate";
         }
         leaf flow-error-syn-protection {
           type int32;
           description
             "Syn-attack protection";
         }
         leaf flow-error-incoming-nat {
           type int32;
           description
             "Incoming NAT errors";
         }
         leaf flow-error-no-tunnel {
           type int32;
           description
             "No tunnel found";
         }
         leaf flow-error-no-more-session {
           type int32;
           description
             "No more sessions";
         }
         leaf flow-error-invalid-zone {
           type int32;
           description
             "Invalid zone received packet";
         }
         leaf flow-error-user-authentication {
           type int32;
           description
             "User authentication errors";
         }
         leaf flow-error-multiple-auth {
           type int32;
           description
             "Multiple user authentications";
         }
         leaf flow-error-multiple-incoming-nat {
           type int32;
           description
             "Multiple incoming NAT";
         }
         leaf flow-error-address-spoofing {
           type int32;
           description
             "Address spoofing";
         }
         leaf flow-error-null-zone {
           type int32;
           description
             "No zone or NULL zone binding";
         }
         leaf flow-error-no-nat-gate {
           type int32;
           description
             "No NAT gate";
         }
         leaf flow-error-no-minor-session {
           type int32;
           description
             "No minor session";
         }
         leaf flow-error-no-session-gate {
           type int32;
           description
             "No session for a gate";
         }
         leaf flow-error-seq-outside-window {
           type int32;
           description
             "TCP sequence number out of window";
         }
         leaf flow-error-no-route-present {
           type int32;
           description
             "No route present";
         }
         leaf flow-error-authentication-failed {
           type int32;
           description
             "Authentication failed";
         }
         leaf flow-error-security-association-missing {
           type int32;
           description
             "Security association not active";
         }
         leaf flow-error-no-sa-for-spi {
           type int32;
           description
             "No SA for incoming SPI";
         }
         leaf flow-error-no-interest-self-packet {
           type int32;
           description
             "No one interested in self packets";
         }
       }
       container multilink-bundle-status {
         description
           "Multilink bundle status";
         leaf rx-sequence-number {
           type string;
           description
             "Received sequence number";
         }
         leaf tx-sequence-number {
           type string;
           description
             "Transmitted sequence number";
         }
         leaf packet-drops {
           type int32;
           description
             "Number of packets dropped";
         }
         leaf packet-drop-bytes {
           type int32;
           description
             "Number of bytes in dropped packets";
         }
         leaf fragment-drops {
           type int32;
           description
             "Number of fragments dropped";
         }
         leaf fragment-drop-bytes {
           type int32;
           description
             "Number of bytes in dropped fragments";
         }
         leaf mrru-exceeded {
           type int32;
           description
             "Number of assembled packets that exceeded MRRU";
         }
         leaf processing-errors {
           type int32;
           description
             "Number of errors encountered in assembling packets";
         }
         leaf fragment-timeout {
           type int32;
           description
             "Fragments timed out during assembly";
         }
         leaf sequence-number-missing {
           type int32;
           description
             "Gap detected in sequence numbers";
         }
         leaf out-of-order-sequence-number {
           type int32;
           description
             "Fragments with an out-of-order sequence number";
         }
         leaf out-of-range-sequence-number {
           type int32;
           description
             "Fragments with an out-of-range sequence number";
         }
         leaf packet-buffer-overflow {
           type int32;
           description
             "Number of times the packet data buffer overflowed";
         }
         leaf fragment-buffer-overflow {
           type int32;
           description
             "Number of times the fragment data buffer overflowed";
         }
       }
       container multilink-bundle-class {
         description
           "Multilink class status";
         leaf multilink-class-id {
           type int32;
           description
             "Multilink class ID";
         }
         leaf rx-sequence-number {
           type string;
           description
             "Received sequence number";
         }
         leaf tx-sequence-number {
           type string;
           description
             "Transmitted sequence number";
         }
         leaf packet-drops {
           type int32;
           description
             "Number of packets dropped";
         }
         leaf packet-drop-bytes {
           type int32;
           description
             "Number of bytes in dropped packets";
         }
         leaf fragment-drops {
           type int32;
           description
             "Number of fragments dropped";
         }
         leaf fragment-drop-bytes {
           type int32;
           description
             "Number of bytes in dropped fragments";
         }
         leaf mrru-exceeded {
           type int32;
           description
             "Number of assembled packets that exceeded MRRU";
         }
         leaf processing-errors {
           type int32;
           description
             "Number of errors encountered in assembling packets";
         }
         leaf fragment-timeout {
           type int32;
           description
             "Fragments timed out during assembly";
         }
         leaf sequence-number-missing {
           type int32;
           description
             "Gap detected in sequence numbers";
         }
         leaf out-of-order-sequence-number {
           type int32;
           description
             "Fragments with an out-of-order sequence number";
         }
         leaf out-of-range-sequence-number {
           type int32;
           description
             "Fragments with an out-of-range sequence number";
         }
         leaf packet-buffer-overflow {
           type int32;
           description
             "Number of times the packet data buffer overflowed";
         }
         leaf fragment-buffer-overflow {
           type int32;
           description
             "Number of times the fragment data buffer overflowed";
         }
         leaf multilink-class-drop-timeout {
           type int32;
           description
             "Drop timeout for multilink class (milliseconds)";
         }
       }
       container lag-traffic-statistics {
         container lag-bundle {
           leaf input-packets {
             type uint64;
           }
           leaf input-pps {
             type int32;
           }
           leaf input-bytes {
             type int32;
           }
           leaf input-bps {
             type int32;
           }
           leaf output-packets {
             type uint64;
           }
           leaf output-pps {
             type int32;
           }
           leaf output-bytes {
             type int32;
           }
           leaf output-bps {
             type int32;
           }
         }
         container lag-adaptive-statistics {
           leaf adaptive-adjusts {
             type int32;
           }
           leaf adaptive-scans {
             type int32;
           }
           leaf adaptive-updates {
             type int32;
           }
         }
         container lag-multicast-statistics {
           leaf lag-multicast-statistics-header {
             type empty;
           }
           container lag-ipv4-multicast-statistics {
             leaf input-packets {
               type uint64;
             }
             leaf input-pps {
               type int32;
             }
             leaf input-bytes {
               type int32;
             }
             leaf input-bps {
               type int32;
             }
             leaf output-packets {
               type uint64;
             }
             leaf output-pps {
               type int32;
             }
             leaf output-bytes {
               type int32;
             }
             leaf output-bps {
               type int32;
             }
           }
           container lag-ipv6-multicast-statistics {
             leaf input-packets {
               type uint64;
             }
             leaf input-pps {
               type int32;
             }
             leaf input-bytes {
               type int32;
             }
             leaf input-bps {
               type int32;
             }
             leaf output-packets {
               type uint64;
             }
             leaf output-pps {
               type int32;
             }
             leaf output-bytes {
               type int32;
             }
             leaf output-bps {
               type int32;
             }
           }
         }
         container aggregate-member-info {
           leaf aggregate-member-count {
             type uint32;
           }
         }
         list lag-link {
           key "name";
           leaf name {
             type string;
             description
               "Name of this item";
           }
           leaf down {
             type empty;
             description
               "Link is down";
           }
           leaf input-packets {
             type uint64;
           }
           leaf input-pps {
             type int32;
           }
           leaf input-bytes {
             type int32;
           }
           leaf input-bps {
             type int32;
           }
           leaf output-packets {
             type uint64;
           }
           leaf output-pps {
             type int32;
           }
           leaf output-bytes {
             type int32;
           }
           leaf output-bps {
             type int32;
           }
         }
         list lag-bfd-view {
           key "name";
           leaf name {
             type string;
             description
               "Name of this item";
           }
           leaf link-usability {
             type string;
           }
         }
         list lag-targeting-summary {
           leaf targeting-intf-name {
             type string;
           }
           leaf targeting-intf-type {
             type string;
           }
           leaf targeting-intf-link-state {
             type string;
           }
         }
         list lag-marker {
           key "name";
           leaf name {
             type string;
             description
               "Name of this item";
           }
           leaf marker-rx-packets {
             type string;
           }
           leaf marker-response-tx-packets {
             type string;
           }
           leaf lacp-rx-packets {
             type string;
             description
               "Number of LACP packets received";
           }
           leaf lacp-tx-packets {
             type string;
             description
               "Number of LACP packets transmitted";
           }
           leaf unknown-rx-packets {
             type string;
             description
               "Number of unknown type packets received";
           }
           leaf illegal-rx-packets {
             type string;
             description
               "Number of ill formed packets received";
           }
         }
         list lag-lacp-statistics {
           key "name";
           leaf name {
             type string;
             description
               "Name of this item";
           }
           leaf lacp-rx-packets {
             type string;
             description
               "Number of LACP packets received";
           }
           leaf lacp-tx-packets {
             type string;
             description
               "Number of LACP packets transmitted";
           }
           leaf unknown-rx-packets {
             type string;
             description
               "Number of unknown type packets received";
           }
           leaf illegal-rx-packets {
             type string;
             description
               "Number of ill formed packets received";
           }
         }
         list if-distribution-list-information {
           leaf list-type {
             type string;
           }
           leaf list-status {
             type string;
           }
           list if-list {
             leaf if-child-name {
               type string;
             }
             leaf if-status {
               type string;
             }
           }
         }
         list lag-link-protection-subgrp {
           key "name";
           leaf name {
             type string;
             description
               "Name of this item";
           }
           leaf lag-link-protection-subgrp-name {
             type string;
           }
           leaf lag-link-protection-subgrp-state {
             type string;
           }
         }
         list lag-lacp-info {
           key "name";
           description
             "LACP information";
           leaf name {
             type string;
             description
               "Name of this item";
           }
           leaf lacp-role {
             type string;
             description
               "Whether it is an actor or partner";
           }
           leaf lacp-sys-priority {
             type string;
             description
               "System priority";
           }
           leaf lacp-system-id {
             type string;
             description
               "LACP system identifier";
           }
           leaf lacp-port-priority {
             type string;
             description
               "Priority of the port";
           }
           leaf lacp-port-number {
             type string;
             description
               "Port number";
           }
           leaf lacp-port-key {
             type string;
             description
               "Operational key of the port";
           }
         }
         list lag-lacp-state {
           key "name";
           description
             "LACP protocol state information";
           leaf name {
             type string;
             description
               "Name of this item";
           }
           leaf lacp-role {
             type string;
             description
               "Whether it is an actor or partner";
           }
           leaf lacp-expired {
             type string;
             description
               "State of the receive lacp machine is EXPIRED?";
           }
           leaf lacp-defaulted {
             type string;
             description
               "State of the receive lacp machine is DEFAULTED?";
           }
           leaf lacp-distributing {
             type string;
             description
               "State of the mux lacp machine is DISTRIBUTING?";
           }
           leaf lacp-collecting {
             type string;
             description
               "State of the mux lacp machine is COLLECTING?";
           }
           leaf lacp-synchronization {
             type string;
             description
               "Actor view of partner information is in sync";
           }
           leaf lacp-aggregation {
             type string;
             description
               "Actor view of partner information is in sync";
           }
           leaf lacp-timeout {
             type string;
             description
               "Configured as either fast or slow periodic";
           }
           leaf lacp-activity {
             type string;
             description
               "Configured as either active or passive";
           }
         }
         list lag-lacp-protocol {
           key "name";
           description
             "LACP protocol information";
           leaf name {
             type string;
             description
               "Name of this item";
           }
           leaf lacp-receive-state {
             type string;
             description
               "State of the receive lacp machine";
           }
           leaf lacp-transmit-state {
             type string;
             description
               "State of the transmit lacp machine";
           }
           leaf lacp-mux-state {
             type string;
             description
               "State of the mux lacp machine";
           }
         }
         list lag-lacp-bfd {
           key "name";
           description
             "BFD protocol information";
           leaf name {
             type string;
             description
               "Name of this item";
           }
           leaf lacp-bfd-state {
             type string;
             description
               "State of the BFD session";
           }
         }
         list lacp-hold-up-information {
           key "name";
           description
             "LACP hold-up information";
           leaf name {
             type string;
             description
               "Name of this item";
           }
           leaf status {
             type string;
           }
           leaf restart-count {
             type int32;
           }
           leaf time-to-expire {
             type int32;
           }
           leaf start-time {
             type string;
           }
         }
         container ifd-lag-traffic-statistics {
           list ifd-lag-members-list {
             key "name";
             leaf name {
               type string;
               description
                 "Name of this item";
             }
             leaf down {
               type empty;
               description
                 "Link is down";
             }
             leaf input-packets {
               type uint64;
             }
             leaf input-pps {
               type int32;
             }
             leaf input-bytes {
               type int32;
             }
             leaf input-bps {
               type int32;
             }
             leaf output-packets {
               type uint64;
             }
             leaf output-pps {
               type int32;
             }
             leaf output-bytes {
               type int32;
             }
             leaf output-bps {
               type int32;
             }
           }
         }
       }
       container ifd-lag-traffic-statistics {
       }
       container layer2-input-policer-statistics {
         description
           "Layer 2 input policer statistics for interface";
         leaf policer-low-bytes {
           type int32;
           description
             "Number of loss priority low bytes";
         }
         leaf policer-low-frames {
           type int32;
           description
             "Number of loss priority low frames";
         }
         leaf policer-low-rate {
           type int32;
           description
             "Rate of loss priority low pkts";
         }
         leaf policer-medium-high-bytes {
           type int32;
           description
             "Number of loss priority medium high bytes";
         }
         leaf policer-medium-high-frames {
           type int32;
           description
             "Number of loss priority medium high frames";
         }
         leaf policer-medium-high-rate {
           type int32;
           description
             "Rate of loss priority medium high rate";
         }
         leaf policer-high-bytes {
           type int32;
           description
             "Number of loss priority high bytes";
         }
         leaf policer-high-frames {
           type int32;
           description
             "Number of loss priority high frames";
         }
         leaf policer-high-rate {
           type int32;
           description
             "Rate of loss priority high rate";
         }
         leaf policer-dropped-bytes {
           type int32;
           description
             "Number of dropped bytes";
         }
         leaf policer-dropped-frames {
           type int32;
           description
             "Number of dropped frames";
         }
         leaf policer-dropped-rate {
           type int32;
           description
             "Number of dropped rate";
         }
         leaf policer-medium-low-frames {
           type int32;
           description
             "Number of loss priority medium low frames";
         }
         leaf policer-medium-low-bytes {
           type int32;
           description
             "Number of loss priority medium low bytes";
         }
         leaf policer-medium-low-rate {
           type int32;
           description
             "Rate of loss priority medium low pkts";
         }
       }
       container layer2-output-policer-statistics {
         description
           "Layer 2 output policer statistics for interface";
         leaf policer-low-bytes {
           type int32;
           description
             "Number of loss priority low bytes";
         }
         leaf policer-low-frames {
           type int32;
           description
             "Number of loss priority low frames";
         }
         leaf policer-low-rate {
           type int32;
           description
             "Rate of loss priority low pkts";
         }
         leaf policer-medium-high-bytes {
           type int32;
           description
             "Number of loss priority medium high bytes";
         }
         leaf policer-medium-high-frames {
           type int32;
           description
             "Number of loss priority medium high frames";
         }
         leaf policer-medium-high-rate {
           type int32;
           description
             "Rate of loss priority medium high rate";
         }
         leaf policer-high-bytes {
           type int32;
           description
             "Number of loss priority high bytes";
         }
         leaf policer-high-frames {
           type int32;
           description
             "Number of loss priority high frames";
         }
         leaf policer-high-rate {
           type int32;
           description
             "Rate of loss priority high rate";
         }
         leaf policer-dropped-bytes {
           type int32;
           description
             "Number of dropped bytes";
         }
         leaf policer-dropped-frames {
           type int32;
           description
             "Number of dropped frames";
         }
         leaf policer-dropped-rate {
           type int32;
           description
             "Number of dropped rate";
         }
         leaf policer-medium-low-frames {
           type int32;
           description
             "Number of loss priority medium low frames";
         }
         leaf policer-medium-low-bytes {
           type int32;
           description
             "Number of loss priority medium low bytes";
         }
         leaf policer-medium-low-rate {
           type int32;
           description
             "Rate of loss priority medium low pkts";
         }
       }
       container atm-input-policer-statistics {
         description
           "ATM input Policer Statistics for interface";
         leaf atm-policer-traffic-count-cells {
           type int32;
           description
             "Stats for counted ATM Cells";
         }
         leaf atm-policer-traffic-discard-cells {
           type int32;
           description
             "Stats for discarded ATM Cells";
         }
         leaf atm-policer-traffic-discard-tag-cells {
           type int32;
           description
             "Stats for discard-tag ATM Cells";
         }
       }
       container mac-policer-information {
         leaf mac-address {
           type jt:mac-addr;
         }
         leaf mac-entry-type {
           type string;
         }
         leaf receive-bytes {
           type int32;
         }
         leaf transmit-bytes {
           type int32;
         }
         leaf receive-frames {
           type int32;
         }
         leaf transmit-frames {
           type int32;
         }
         container ether-policer-list {
           list ether-policer-record {
             leaf policer-type {
               type string;
             }
             leaf out-of-spec-frames {
               type int32;
             }
             leaf out-of-spec-bytes {
               type int32;
             }
           }
         }
       }
       container ppp-parameters {
         description
           "PPP parameters";
         leaf lcp-restart-timer {
           type int32;
           description
             "LCP restart timer (milliseconds)";
         }
         leaf ncp-restart-timer {
           type int32;
           description
             "NCP restart timer (milliseconds)";
         }
         leaf termination-requests {
           type string;
           description
             "Whether PPP termination requests are sent";
         }
         leaf loopback-clear-timer {
           type int32;
           description
             "PPP loopback clear timer (seconds)";
         }
       }
       leaf admin-status {
         type string;
         description
           "Desired state of the interface";
       }
       leaf oper-status {
         type string;
         description
           "Current operational state of the interface";
       }
       leaf vrfname {
         type string;
         description
           "Routing instance name";
       }
       leaf zonename {
         type string;
         description
           "Zone name";
       }
     }
     container controller {
       leaf name {
         type string;
         description
           "Name of this item";
       }
       leaf admin-status {
         type string;
         description
           "Desired state of the interface";
       }
       leaf oper-status {
         type string;
         description
           "Current operational state of the interface";
       }
     }
     list interface-set {
       key "name";
       leaf name {
         type string;
         description
           "Name of this item";
       }
       container traffic-statistics {
         leaf input-bps {
           type int32;
         }
         leaf input-pps {
           type int32;
         }
         leaf output-bps {
           type int32;
         }
         leaf output-pps {
           type int32;
         }
         leaf input-packets {
           type uint64;
         }
         leaf output-packets {
           type uint64;
         }
         container ipv4-traffic-statistics {
           leaf input-bps {
             type int32;
           }
           leaf output-bps {
             type int32;
           }
           leaf input-pps {
             type int32;
           }
           leaf output-pps {
             type int32;
           }
           leaf input-bytes {
             type int32;
           }
           leaf output-bytes {
             type int32;
           }
           leaf input-packets {
             type uint64;
           }
           leaf output-packets {
             type uint64;
           }
         }
         leaf input-bytes {
           type int32;
         }
         leaf output-bytes {
           type int32;
         }
         container ipv6-transit-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-traffic-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-total-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
       }
       container interface-set-queue-information {
         container queue-counters {
           description
             "Queue counter statistics";
           leaf queue-counters-error-message {
             type string;
             description
               "Queue statistics not available for this interface";
           }
           container interface-cos-short-summary {
             description
               "Summary of queue information on an interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           list queue {
             key "queue-number";
             description
               "Counters for a single queue";
             leaf queue-number {
               type uint32;
               description
                 "Queue number";
             }
             leaf queue-counters-queued-packets {
               type int32;
               description
                 "Queued packet count";
             }
             leaf queue-counters-trans-packets {
               type int32;
               description
                 "Total number of transmitted packets";
             }
             leaf queue-counters-total-drop-packets {
               type int32;
               description
                 "Number of total packets dropped at the queue";
             }
             leaf forwarding-class-name {
               type string;
               description
                 "Forwarding class name associated with queue";
             }
             leaf queue-counters-queued-packets-rate {
               type int32;
               description
                 "Rate at which packets are queued";
             }
             leaf queue-counters-queued-bytes {
               type int32;
               description
                 "Queued bytes count";
             }
             leaf queue-counters-queued-bytes-rate {
               type int32;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets-rate {
               type int32;
               description
                 "Rate at which packets are transmitted";
             }
             leaf queue-counters-trans-bytes {
               type int32;
               description
                 "Total number of transmitted bytes";
             }
             leaf queue-counters-trans-bytes-rate {
               type int32;
               description
                 "Rate at which bytes are transmitted";
             }
             leaf queue-counters-tail-drop-packets-na {
               type string;
               description
                 "Number of packets dropped due to tail drop not available";
             }
             leaf queue-counters-tail-drop-packets {
               type int32;
               description
                 "Number of packets dropped at the tail of the queue";
             }
             leaf queue-counters-tail-drop-packets-rate {
               type int32;
               description
                 "Rate at which packets are dropped at tail of queue";
             }
             leaf queue-counters-tail-drop-bytes {
               type int32;
               description
                 "Number of packets dropped at tail drop of the queue";
             }
             leaf queue-counters-tail-drop-bytes-rate {
               type int32;
               description
                 "Number of packets dropped at tail drop of the queue";
             }
             leaf queue-counters-ecn-ce-packets {
               type int32;
               description
                 "Total number of ECN CE packets";
             }
             leaf queue-counters-ecn-ce-packets-rate {
               type int32;
               description
                 "Rate at which ECN CE packets are transmitted";
             }
             leaf queue-counters-ecn-ce-bytes {
               type int32;
               description
                 "Total number of ECN CE bytes";
             }
             leaf queue-counters-ecn-ce-bytes-rate {
               type int32;
               description
                 "Rate at which ECN CE bytes are transmitted";
             }
             leaf queue-counters-rate-limit-drop-packets-na {
               type string;
               description
                 "Number of packets dropped due to rate-limit drop not 
                 available";
             }
             leaf queue-counters-rate-limit-drop-packets {
               type int32;
               description
                 "Number of packets dropped by rate-limit for the queue";
             }
             leaf queue-counters-rate-limit-drop-packets-rate {
               type int32;
               description
                 "Rate at which packets are dropped by rate-limit for the 
                 queue";
             }
             leaf queue-counters-rate-limit-drop-bytes-na {
               type string;
               description
                 "Number of bytes dropped due to tail drop not available";
             }
             leaf queue-counters-rate-limit-drop-bytes {
               type int32;
               description
                 "Number of bytes dropped at the tail of the queue";
             }
             leaf queue-counters-rate-limit-drop-bytes-rate {
               type int32;
               description
                 "Rate at which bytes are dropped at the tail of the queue";
             }
             leaf queue-counters-red-packets-na {
               type string;
               description
                 "Number of packets dropped due to RED not available";
             }
             leaf queue-counters-red-packets {
               type int32;
               description
                 "Number of packets dropped due to RED";
             }
             leaf queue-counters-red-packets-rate {
               type int32;
               description
                 "Rate at which packets are dropped due to RED";
             }
             leaf queue-counters-red-packets-ln {
               type int32;
               description
                 "Number of RED dropped low-loss, non-TCP packets";
             }
             leaf queue-counters-red-packets-rate-ln {
               type int32;
               description
                 "RED drop rate for low-loss, non-TCP packets";
             }
             leaf queue-counters-red-packets-lt {
               type int32;
               description
                 "Number of RED dropped of low-loss, TCP packets";
             }
             leaf queue-counters-red-packets-rate-lt {
               type int32;
               description
                 "RED drop rate for low-loss, TCP packets";
             }
             leaf queue-counters-red-packets-hn {
               type int32;
               description
                 "Number of RED dropped high-loss, non-TCP packets";
             }
             leaf queue-counters-red-packets-rate-hn {
               type int32;
               description
                 "RED drop rate for high-loss, non-TCP packets";
             }
             leaf queue-counters-red-packets-ht {
               type int32;
               description
                 "Number of RED dropped high-loss, TCP packets";
             }
             leaf queue-counters-red-packets-rate-ht {
               type int32;
               description
                 "RED drop rate for high-loss, TCP packets";
             }
             leaf queue-counters-red-packets-low {
               type int32;
               description
                 "Number of RED dropped low-loss packets";
             }
             leaf queue-counters-red-packets-rate-low {
               type int32;
               description
                 "RED drop rate for low-loss packets";
             }
             leaf queue-counters-red-packets-medium-low {
               type int32;
               description
                 "Number of RED dropped medium-low-loss packets";
             }
             leaf queue-counters-red-packets-rate-medium-low {
               type int32;
               description
                 "RED drop rate for medium-low-loss packets";
             }
             leaf queue-counters-red-packets-medium-high {
               type int32;
               description
                 "Number of RED dropped medium-high-loss packets";
             }
             leaf queue-counters-red-packets-rate-medium-high {
               type int32;
               description
                 "RED drop rate for medium-high-loss packets";
             }
             leaf queue-counters-red-packets-medium {
               type int32;
               description
                 "Number of RED dropped medium-loss packets";
             }
             leaf queue-counters-red-packets-rate-medium {
               type int32;
               description
                 "RED drop rate for medium-loss packets";
             }
             leaf queue-counters-red-packets-high {
               type int32;
               description
                 "Number of RED dropped high-loss packets";
             }
             leaf queue-counters-red-packets-rate-high {
               type int32;
               description
                 "RED drop rate for high-loss packets";
             }
             leaf queue-counters-red-bytes-na {
               type string;
               description
                 "Number of bytes dropped due to RED not available";
             }
             leaf queue-counters-red-bytes {
               type int32;
               description
                 "Number of bytes dropped due to RED";
             }
             leaf queue-counters-red-bytes-rate {
               type int32;
               description
                 "Rate at which bytes are dropped due to RED";
             }
             leaf queue-counters-red-bytes-ln {
               type int32;
               description
                 "Number of RED dropped low-loss, non-TCP bytes";
             }
             leaf queue-counters-red-bytes-rate-ln {
               type int32;
               description
                 "RED drop rate for low-loss, non-TCP bytes";
             }
             leaf queue-counters-red-bytes-lt {
               type int32;
               description
                 "Number of RED dropped low-loss, TCP bytes";
             }
             leaf queue-counters-red-bytes-rate-lt {
               type int32;
               description
                 "RED drop rate for low-loss, TCP bytes";
             }
             leaf queue-counters-red-bytes-hn {
               type int32;
               description
                 "Number of RED dropped high-loss, non-TCP bytes";
             }
             leaf queue-counters-red-bytes-rate-hn {
               type int32;
               description
                 "RED drop rate for high-loss, non-TCP bytes";
             }
             leaf queue-counters-red-bytes-ht {
               type int32;
               description
                 "Number of RED dropped high-loss, TCP bytes";
             }
             leaf queue-counters-red-bytes-rate-ht {
               type int32;
               description
                 "RED drop rate for high-loss, TCP bytes";
             }
             leaf queue-counters-red-bytes-low {
               type int32;
               description
                 "Number of RED dropped low-loss bytes";
             }
             leaf queue-counters-red-bytes-rate-low {
               type int32;
               description
                 "RED drop rate for low-loss bytes";
             }
             leaf queue-counters-red-bytes-medium-low {
               type int32;
               description
                 "Number of RED dropped medium-low-loss bytes";
             }
             leaf queue-counters-red-bytes-rate-medium-low {
               type int32;
               description
                 "RED drop rate for medium-low-loss bytes";
             }
             leaf queue-counters-red-bytes-medium-high {
               type int32;
               description
                 "Number of RED dropped medium-high-loss bytes";
             }
             leaf queue-counters-red-bytes-rate-medium-high {
               type int32;
               description
                 "RED drop rate for medium-high-loss bytes";
             }
             leaf queue-counters-red-bytes-medium {
               type int32;
               description
                 "Number of RED dropped medium-loss bytes";
             }
             leaf queue-counters-red-bytes-rate-medium {
               type int32;
               description
                 "RED drop rate for medium-loss bytes";
             }
             leaf queue-counters-red-bytes-high {
               type int32;
               description
                 "Number of RED dropped high-loss bytes";
             }
             leaf queue-counters-red-bytes-rate-high {
               type int32;
               description
                 "RED drop rate for high-loss bytes";
             }
             leaf queue-counters-timestamp {
               type int32;
               description
                 "Last packet enqueued timestamp";
             }
             leaf queue-counters-total-drop-packets-rate {
               type int32;
               description
                 "Number of total packets dropped at the queue";
             }
             leaf queue-counters-total-drop-bytes {
               type int32;
               description
                 "Number of total packets dropped at the queue";
             }
             leaf queue-counters-total-drop-bytes-rate {
               type int32;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
         }
         container ingress-queue-counters {
           description
             "Ingress queue counter statistics";
           list queue {
             key "queue-number";
             description
               "Counters for a single queue";
             leaf queue-number {
               type uint32;
               description
                 "Queue number";
             }
             leaf forwarding-class-name {
               type string;
               description
                 "Forwarding class name associated with queue";
             }
             leaf queue-counters-queued-packets {
               type int32;
               description
                 "Queued packet count";
             }
             leaf queue-counters-queued-packets-rate {
               type int32;
               description
                 "Rate at which packets are queued";
             }
             leaf queue-counters-queued-bytes {
               type int32;
               description
                 "Queued bytes count";
             }
             leaf queue-counters-queued-bytes-rate {
               type int32;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets {
               type int32;
               description
                 "Total number of transmitted packets";
             }
             leaf queue-counters-trans-packets-rate {
               type int32;
               description
                 "Rate at which packets are transmitted";
             }
             leaf queue-counters-trans-bytes {
               type int32;
               description
                 "Total number of transmitted bytes";
             }
             leaf queue-counters-trans-bytes-rate {
               type int32;
               description
                 "Rate at which bytes are transmitted";
             }
             leaf queue-counters-tail-drop-packets-na {
               type string;
               description
                 "Number of packets dropped due to tail drop not available";
             }
             leaf queue-counters-tail-drop-packets {
               type int32;
               description
                 "Number of packets dropped at the tail of the queue";
             }
             leaf queue-counters-tail-drop-packets-rate {
               type int32;
               description
                 "Rate at which packets are dropped at tail of queue";
             }
             leaf queue-counters-tail-drop-bytes {
               type int32;
               description
                 "Number of packets dropped at tail drop of the queue";
             }
             leaf queue-counters-tail-drop-bytes-rate {
               type int32;
               description
                 "Number of packets dropped at tail drop of the queue";
             }
             leaf queue-counters-ecn-ce-packets {
               type int32;
               description
                 "Total number of ECN CE packets";
             }
             leaf queue-counters-ecn-ce-packets-rate {
               type int32;
               description
                 "Rate at which ECN CE packets are transmitted";
             }
             leaf queue-counters-ecn-ce-bytes {
               type int32;
               description
                 "Total number of ECN CE bytes";
             }
             leaf queue-counters-ecn-ce-bytes-rate {
               type int32;
               description
                 "Rate at which ECN CE bytes are transmitted";
             }
             leaf queue-counters-rate-limit-drop-packets-na {
               type string;
               description
                 "Number of packets dropped due to rate-limit drop not 
                 available";
             }
             leaf queue-counters-rate-limit-drop-packets {
               type int32;
               description
                 "Number of packets dropped by rate-limit for the queue";
             }
             leaf queue-counters-rate-limit-drop-packets-rate {
               type int32;
               description
                 "Rate at which packets are dropped by rate-limit for the 
                 queue";
             }
             leaf queue-counters-rate-limit-drop-bytes-na {
               type string;
               description
                 "Number of bytes dropped due to tail drop not available";
             }
             leaf queue-counters-rate-limit-drop-bytes {
               type int32;
               description
                 "Number of bytes dropped at the tail of the queue";
             }
             leaf queue-counters-rate-limit-drop-bytes-rate {
               type int32;
               description
                 "Rate at which bytes are dropped at the tail of the queue";
             }
             leaf queue-counters-red-packets-na {
               type string;
               description
                 "Number of packets dropped due to RED not available";
             }
             leaf queue-counters-red-packets {
               type int32;
               description
                 "Number of packets dropped due to RED";
             }
             leaf queue-counters-red-packets-rate {
               type int32;
               description
                 "Rate at which packets are dropped due to RED";
             }
             leaf queue-counters-red-packets-ln {
               type int32;
               description
                 "Number of RED dropped low-loss, non-TCP packets";
             }
             leaf queue-counters-red-packets-rate-ln {
               type int32;
               description
                 "RED drop rate for low-loss, non-TCP packets";
             }
             leaf queue-counters-red-packets-lt {
               type int32;
               description
                 "Number of RED dropped of low-loss, TCP packets";
             }
             leaf queue-counters-red-packets-rate-lt {
               type int32;
               description
                 "RED drop rate for low-loss, TCP packets";
             }
             leaf queue-counters-red-packets-hn {
               type int32;
               description
                 "Number of RED dropped high-loss, non-TCP packets";
             }
             leaf queue-counters-red-packets-rate-hn {
               type int32;
               description
                 "RED drop rate for high-loss, non-TCP packets";
             }
             leaf queue-counters-red-packets-ht {
               type int32;
               description
                 "Number of RED dropped high-loss, TCP packets";
             }
             leaf queue-counters-red-packets-rate-ht {
               type int32;
               description
                 "RED drop rate for high-loss, TCP packets";
             }
             leaf queue-counters-red-packets-low {
               type int32;
               description
                 "Number of RED dropped low-loss packets";
             }
             leaf queue-counters-red-packets-rate-low {
               type int32;
               description
                 "RED drop rate for low-loss packets";
             }
             leaf queue-counters-red-packets-medium-low {
               type int32;
               description
                 "Number of RED dropped medium-low-loss packets";
             }
             leaf queue-counters-red-packets-rate-medium-low {
               type int32;
               description
                 "RED drop rate for medium-low-loss packets";
             }
             leaf queue-counters-red-packets-medium-high {
               type int32;
               description
                 "Number of RED dropped medium-high-loss packets";
             }
             leaf queue-counters-red-packets-rate-medium-high {
               type int32;
               description
                 "RED drop rate for medium-high-loss packets";
             }
             leaf queue-counters-red-packets-medium {
               type int32;
               description
                 "Number of RED dropped medium-loss packets";
             }
             leaf queue-counters-red-packets-rate-medium {
               type int32;
               description
                 "RED drop rate for medium-loss packets";
             }
             leaf queue-counters-red-packets-high {
               type int32;
               description
                 "Number of RED dropped high-loss packets";
             }
             leaf queue-counters-red-packets-rate-high {
               type int32;
               description
                 "RED drop rate for high-loss packets";
             }
             leaf queue-counters-red-bytes-na {
               type string;
               description
                 "Number of bytes dropped due to RED not available";
             }
             leaf queue-counters-red-bytes {
               type int32;
               description
                 "Number of bytes dropped due to RED";
             }
             leaf queue-counters-red-bytes-rate {
               type int32;
               description
                 "Rate at which bytes are dropped due to RED";
             }
             leaf queue-counters-red-bytes-ln {
               type int32;
               description
                 "Number of RED dropped low-loss, non-TCP bytes";
             }
             leaf queue-counters-red-bytes-rate-ln {
               type int32;
               description
                 "RED drop rate for low-loss, non-TCP bytes";
             }
             leaf queue-counters-red-bytes-lt {
               type int32;
               description
                 "Number of RED dropped low-loss, TCP bytes";
             }
             leaf queue-counters-red-bytes-rate-lt {
               type int32;
               description
                 "RED drop rate for low-loss, TCP bytes";
             }
             leaf queue-counters-red-bytes-hn {
               type int32;
               description
                 "Number of RED dropped high-loss, non-TCP bytes";
             }
             leaf queue-counters-red-bytes-rate-hn {
               type int32;
               description
                 "RED drop rate for high-loss, non-TCP bytes";
             }
             leaf queue-counters-red-bytes-ht {
               type int32;
               description
                 "Number of RED dropped high-loss, TCP bytes";
             }
             leaf queue-counters-red-bytes-rate-ht {
               type int32;
               description
                 "RED drop rate for high-loss, TCP bytes";
             }
             leaf queue-counters-red-bytes-low {
               type int32;
               description
                 "Number of RED dropped low-loss bytes";
             }
             leaf queue-counters-red-bytes-rate-low {
               type int32;
               description
                 "RED drop rate for low-loss bytes";
             }
             leaf queue-counters-red-bytes-medium-low {
               type int32;
               description
                 "Number of RED dropped medium-low-loss bytes";
             }
             leaf queue-counters-red-bytes-rate-medium-low {
               type int32;
               description
                 "RED drop rate for medium-low-loss bytes";
             }
             leaf queue-counters-red-bytes-medium-high {
               type int32;
               description
                 "Number of RED dropped medium-high-loss bytes";
             }
             leaf queue-counters-red-bytes-rate-medium-high {
               type int32;
               description
                 "RED drop rate for medium-high-loss bytes";
             }
             leaf queue-counters-red-bytes-medium {
               type int32;
               description
                 "Number of RED dropped medium-loss bytes";
             }
             leaf queue-counters-red-bytes-rate-medium {
               type int32;
               description
                 "RED drop rate for medium-loss bytes";
             }
             leaf queue-counters-red-bytes-high {
               type int32;
               description
                 "Number of RED dropped high-loss bytes";
             }
             leaf queue-counters-red-bytes-rate-high {
               type int32;
               description
                 "RED drop rate for high-loss bytes";
             }
             leaf queue-counters-timestamp {
               type int32;
               description
                 "Last packet enqueued timestamp";
             }
             leaf queue-counters-total-drop-packets {
               type int32;
               description
                 "Number of total packets dropped at the queue";
             }
             leaf queue-counters-total-drop-packets-rate {
               type int32;
               description
                 "Number of total packets dropped at the queue";
             }
             leaf queue-counters-total-drop-bytes {
               type int32;
               description
                 "Number of total packets dropped at the queue";
             }
             leaf queue-counters-total-drop-bytes-rate {
               type int32;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
           container interface-cos-short-summary {
             description
               "Summary of queue information on an interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           list queue-num-forwarding-class-name-map {
             key "queue-number";
             leaf queue-number {
               type uint32;
               description
                 "Queue number";
             }
             leaf forwarding-class-name {
               type string;
               description
                 "Forwarding class name associated with queue";
             }
           }
         }
       }
       container voq-counters {
         description
           "VOQ counter statistics";
         leaf voq-counters-error-message {
           type string;
           description
             "VOQ statistics not available for this interface";
         }
         container voq {
           description
             "Counters for a single voq";
           container fpc {
             description
               "Counters for a single FPC";
             leaf fpc-no {
               type int32;
               description
                 "FPC number";
             }
             container pfe {
               description
                 "Counters for a single PFE";
               leaf-list pfe-no {
                 type int32;
                 description
                   "PFE number";
               }
               leaf voq-counters-tail-drop-packets {
                 type int32;
                 description
                   "Tail DROP packet count";
               }
               leaf voq-counters-tail-drop-packets-rate {
                 type int32;
                 description
                   "Rate at which tail packets are dropped";
               }
               leaf voq-counters-tail-drop-bytes {
                 type int32;
                 description
                   "Tail DROP bytes count";
               }
               leaf voq-counters-tail-drop-bytes-rate {
                 type int32;
                 description
                   "Rate at which tail bytes are dropped";
               }
               leaf voq-counters-drop-packets {
                 type int32;
                 description
                   "DROP packet count";
               }
               leaf voq-counters-drop-packets-rate {
                 type int32;
                 description
                   "Rate at which packets are dropped";
               }
               leaf voq-counters-drop-bytes {
                 type int32;
                 description
                   "DROP bytes count";
               }
               leaf voq-counters-drop-bytes-rate {
                 type int32;
                 description
                   "Rate at which bytes are dropped";
               }
               leaf voq-counters-queued-packets {
                 type int32;
                 description
                   "QUEUED packets count";
               }
               leaf voq-counters-queued-packets-rate {
                 type int32;
                 description
                   "Rate at which packets are queued";
               }
               leaf voq-counters-queued-bytes {
                 type int32;
                 description
                   "QUEUED bytes count";
               }
               leaf voq-counters-queued-bytes-rate {
                 type int32;
                 description
                   "Rate at which bytes are queued";
               }
               leaf voq-counters-transmitted-packets {
                 type int32;
                 description
                   "Transmitted packets count";
               }
               leaf voq-counters-transmitted-packets-rate {
                 type int32;
                 description
                   "Rate at which packets are transmitted";
               }
               leaf voq-counters-transmitted-bytes {
                 type int32;
                 description
                   "Transmitted bytes count";
               }
               leaf voq-counters-transmitted-bytes-rate {
                 type int32;
                 description
                   "Rate at which bytes are transmitted";
               }
               leaf voq-counters-queue-depth-bytes-current {
                 type int32;
                 description
                   "Current queue length";
               }
               leaf voq-counters-queue-depth-bytes-peak {
                 type int32;
                 description
                   "Peak queue length";
               }
               leaf voq-counters-queue-depth-bytes-average {
                 type int32;
                 description
                   "Average queue length";
               }
             }
           }
           leaf queue-number {
             type uint32;
             description
               "Queue number";
           }
           leaf forwarding-class-name {
             type string;
             description
               "Forwarding class name associated with queue";
           }
           leaf restricted-forwarding-class-name {
             type string;
           }
         }
       }
       leaf interface-set-index {
         type int32;
       }
       leaf snmp-index {
         type int32;
         description
           "SNMP ifIndex for this interface";
       }
       list interface-set-member-list {
         key "interface-set-member";
         leaf interface-set-member {
           type string;
         }
       }
       container aci-vlan-iflset-information {
         leaf agent-circuit-id {
           type string;
           description
             "Agent Circuit ID";
         }
         leaf agent-remote-id {
           type string;
           description
             "Agent Remote ID";
         }
       }
       container line-identity-iflset-information {
         leaf agent-circuit-id {
           type string;
           description
             "Agent Circuit ID";
         }
         leaf agent-remote-id {
           type string;
           description
             "Agent Remote ID";
         }
         leaf mac-address {
           type jt:mac-addr;
         }
       }
       container pppoe-uifl-iflset-information {
         leaf dynamic-profile {
           type string;
           description
             "Dynamic Profile name";
         }
         leaf max-sessions {
           type int32;
           description
             "Maximum number of PPPoE sessions";
         }
         leaf max-sessions-vsa-ignore {
           type string;
           description
             "Ignore max-sessions VSA";
         }
       }
       list lag-targeting-summary {
         leaf targeting-intf-name {
           type string;
         }
         leaf targeting-intf-type {
           type string;
         }
         leaf targeting-intf-link-state {
           type string;
         }
       }
     }
     list ifd-slice {
       key "slice-name";
       description
         "IFD-network-slice queue counter statistics";
       leaf slice-name {
         type string;
         description
           "Name of this item";
       }
       leaf slice-index {
         type uint32;
         description
           "Local kernel index of this slice";
       }
       leaf interface-name {
         type string;
         description
           "Interface name";
       }
       leaf interface-index {
         type string;
         description
           "Index";
       }
       container queue-counters {
         description
           "Queue counter statistics";
         leaf queue-counters-error-message {
           type string;
           description
             "Queue statistics not available for this interface";
         }
         container interface-cos-short-summary {
           description
             "Summary of queue information on an interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
         }
         list queue {
           key "queue-number";
           description
             "Counters for a single queue";
           leaf queue-number {
             type uint32;
             description
               "Queue number";
           }
           leaf queue-counters-queued-packets {
             type int32;
             description
               "Queued packet count";
           }
           leaf queue-counters-trans-packets {
             type int32;
             description
               "Total number of transmitted packets";
           }
           leaf queue-counters-total-drop-packets {
             type int32;
             description
               "Number of total packets dropped at the queue";
           }
           leaf forwarding-class-name {
             type string;
             description
               "Forwarding class name associated with queue";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-queued-packets-na {
             type string;
             description
               "Queued packets not available";
           }
           leaf queue-counters-queued-bytes-na {
             type string;
             description
               "Queued bytes not available";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets-na {
             type string;
             description
               "Number of packets dropped due to tail drop not available";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of packets dropped at tail drop of the queue";
           }
           leaf queue-counters-tail-drop-bytes-rate {
             type int32;
             description
               "Number of packets dropped at tail drop of the queue";
           }
           leaf queue-counters-ecn-ce-packets {
             type int32;
             description
               "Total number of ECN CE packets";
           }
           leaf queue-counters-ecn-ce-packets-rate {
             type int32;
             description
               "Rate at which ECN CE packets are transmitted";
           }
           leaf queue-counters-ecn-ce-bytes {
             type int32;
             description
               "Total number of ECN CE bytes";
           }
           leaf queue-counters-ecn-ce-bytes-rate {
             type int32;
             description
               "Rate at which ECN CE bytes are transmitted";
           }
           leaf queue-counters-rate-limit-drop-packets-na {
             type string;
             description
               "Number of packets dropped due to rate-limit drop not 
               available";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes-na {
             type string;
             description
               "Number of bytes dropped due to tail drop not available";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets-na {
             type string;
             description
               "Number of packets dropped due to RED not available";
           }
           leaf queue-counters-red-packets {
             type int32;
             description
               "Number of packets dropped due to RED";
           }
           leaf queue-counters-red-packets-rate {
             type int32;
             description
               "Rate at which packets are dropped due to RED";
           }
           leaf queue-counters-red-packets-ln {
             type int32;
             description
               "Number of RED dropped low-loss, non-TCP packets";
           }
           leaf queue-counters-red-packets-rate-ln {
             type int32;
             description
               "RED drop rate for low-loss, non-TCP packets";
           }
           leaf queue-counters-red-packets-lt {
             type int32;
             description
               "Number of RED dropped of low-loss, TCP packets";
           }
           leaf queue-counters-red-packets-rate-lt {
             type int32;
             description
               "RED drop rate for low-loss, TCP packets";
           }
           leaf queue-counters-red-packets-hn {
             type int32;
             description
               "Number of RED dropped high-loss, non-TCP packets";
           }
           leaf queue-counters-red-packets-rate-hn {
             type int32;
             description
               "RED drop rate for high-loss, non-TCP packets";
           }
           leaf queue-counters-red-packets-ht {
             type int32;
             description
               "Number of RED dropped high-loss, TCP packets";
           }
           leaf queue-counters-red-packets-rate-ht {
             type int32;
             description
               "RED drop rate for high-loss, TCP packets";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-medium {
             type int32;
             description
               "Number of RED dropped medium-loss packets";
           }
           leaf queue-counters-red-packets-rate-medium {
             type int32;
             description
               "RED drop rate for medium-loss packets";
           }
           leaf queue-counters-red-packets-high {
             type int32;
             description
               "Number of RED dropped high-loss packets";
           }
           leaf queue-counters-red-packets-rate-high {
             type int32;
             description
               "RED drop rate for high-loss packets";
           }
           leaf queue-counters-red-bytes-na {
             type string;
             description
               "Number of bytes dropped due to RED not available";
           }
           leaf queue-counters-red-bytes {
             type int32;
             description
               "Number of bytes dropped due to RED";
           }
           leaf queue-counters-red-bytes-rate {
             type int32;
             description
               "Rate at which bytes are dropped due to RED";
           }
           leaf queue-counters-red-bytes-ln {
             type int32;
             description
               "Number of RED dropped low-loss, non-TCP bytes";
           }
           leaf queue-counters-red-bytes-rate-ln {
             type int32;
             description
               "RED drop rate for low-loss, non-TCP bytes";
           }
           leaf queue-counters-red-bytes-lt {
             type int32;
             description
               "Number of RED dropped low-loss, TCP bytes";
           }
           leaf queue-counters-red-bytes-rate-lt {
             type int32;
             description
               "RED drop rate for low-loss, TCP bytes";
           }
           leaf queue-counters-red-bytes-hn {
             type int32;
             description
               "Number of RED dropped high-loss, non-TCP bytes";
           }
           leaf queue-counters-red-bytes-rate-hn {
             type int32;
             description
               "RED drop rate for high-loss, non-TCP bytes";
           }
           leaf queue-counters-red-bytes-ht {
             type int32;
             description
               "Number of RED dropped high-loss, TCP bytes";
           }
           leaf queue-counters-red-bytes-rate-ht {
             type int32;
             description
               "RED drop rate for high-loss, TCP bytes";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-medium {
             type int32;
             description
               "Number of RED dropped medium-loss bytes";
           }
           leaf queue-counters-red-bytes-rate-medium {
             type int32;
             description
               "RED drop rate for medium-loss bytes";
           }
           leaf queue-counters-red-bytes-high {
             type int32;
             description
               "Number of RED dropped high-loss bytes";
           }
           leaf queue-counters-red-bytes-rate-high {
             type int32;
             description
               "RED drop rate for high-loss bytes";
           }
           leaf queue-counters-timestamp {
             type int32;
             description
               "Last packet enqueued timestamp";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
           leaf queue-counters-reserved-buffer-packets {
             type int32;
             description
               "Queues's usage of reserved buffer pool in pkts";
           }
           leaf queue-counters-reserved-buffer-bytes {
             type int32;
             description
               "Queues's usage of reserved buffer pool in bytes";
           }
           leaf queue-counters-shared-buffer-packets {
             type int32;
             description
               "Queues's usage of shared buffer pool in pkts";
           }
           leaf queue-counters-shared-buffer-bytes {
             type int32;
             description
               "Queues's usage of shared buffer pool in bytes";
           }
           leaf queue-counters-depth-average {
             type int32;
             description
               "Time averaged queue depth";
           }
           leaf queue-counters-depth-current {
             type int32;
             description
               "Current instantaneous queue depth";
           }
           leaf queue-counters-depth-peak {
             type int32;
             description
               "Peak queue depth";
           }
           leaf queue-counters-depth-max {
             type int32;
             description
               "Maximum queue depth attained";
           }
           leaf queue-counters-srx-reserved-buffer-bytes {
             type int32;
             description
               "Queues's usage of reserved buffer pool in bytes";
           }
           leaf queue-counters-srx-depth-current {
             type int32;
             description
               "Current instantaneous queue depth";
           }
         }
         container interface-cos-summary {
           description
             "Summary of forwarding class and queue information on an 
             interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
           leaf intf-cos-burst-size-for-ifl {
             type int32;
             description
               "Burst size for the logical interface";
           }
         }
       }
       container aggregate-queue {
         description
           "Aggregated queue counters";
         container aggregate-queue-counters {
           description
             "Node aggregated queue counters";
           leaf queue-counters-queued-packets {
             type int32;
             description
               "Queued packet count";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-trans-packets {
             type int32;
             description
               "Total number of transmitted packets";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-total-drop-packets {
             type int32;
             description
               "Number of total packets dropped at the queue";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
         }
       }
     }
     container aggregate-queue {
       description
         "Aggregated queue counters";
       container aggregate-queue-counters {
         description
           "Node aggregated queue counters";
         leaf queue-counters-queued-packets {
           type int32;
           description
             "Queued packet count";
         }
         leaf queue-counters-queued-packets-rate {
           type int32;
           description
             "Rate at which packets are queued";
         }
         leaf queue-counters-queued-bytes {
           type int32;
           description
             "Queued bytes count";
         }
         leaf queue-counters-queued-bytes-rate {
           type int32;
           description
             "Rate at which bytes are queued";
         }
         leaf queue-counters-trans-packets {
           type int32;
           description
             "Total number of transmitted packets";
         }
         leaf queue-counters-trans-packets-rate {
           type int32;
           description
             "Rate at which packets are transmitted";
         }
         leaf queue-counters-trans-bytes {
           type int32;
           description
             "Total number of transmitted bytes";
         }
         leaf queue-counters-trans-bytes-rate {
           type int32;
           description
             "Rate at which bytes are transmitted";
         }
         leaf queue-counters-total-drop-packets {
           type int32;
           description
             "Number of total packets dropped at the queue";
         }
         leaf queue-counters-total-drop-packets-rate {
           type int32;
           description
             "Number of total packets dropped at the queue";
         }
         leaf queue-counters-total-drop-bytes {
           type int32;
           description
             "Number of total packets dropped at the queue";
         }
         leaf queue-counters-total-drop-bytes-rate {
           type int32;
           description
             "Number of total packets dropped at the queue";
         }
       }
     }
     container summary-information {
       container system-generic-information {
         leaf max-ifls {
           type int32;
           description
             "Maximum number of IFLs";
         }
         leaf ifls-alloc {
           type int32;
           description
             "Total number of IFLs allocated";
         }
         leaf ifls-avail {
           type int32;
           description
             "Total number of IFLs available";
         }
       }
       list system-specific-information {
         leaf module-name {
           type string;
           description
             "Module Name";
         }
         leaf ifl-total {
           type int32;
           description
             "Total number of IFLs";
         }
         leaf ifl-up-count {
           type int32;
           description
             "Total number of IFLs with status UP";
         }
         leaf ifl-down-count {
           type int32;
           description
             "Total number of IFLs with status DOWN";
         }
         leaf ifl-lsi {
           type int32;
           description
             "Number of LSI IFLs";
         }
         leaf lsi-up-count {
           type int32;
           description
             "Number of LSI IFLs with status UP";
         }
         leaf lsi-down-count {
           type int32;
           description
             "Number of LSI IFLs with status DOWN";
         }
         leaf untagged-vlan {
           type int32;
           description
             "Number of Untagged Vlans";
         }
         leaf uvlan-up-count {
           type int32;
           description
             "Number of Untagged Vlans with status UP";
         }
         leaf uvlan-down-count {
           type int32;
           description
             "Number of Untagged Vlans with status DOWN";
         }
         leaf tagged-vlan {
           type int32;
           description
             "Number of tagged Vlans";
         }
         leaf tvlan-up-count {
           type int32;
           description
             "Number of tagged Vlans with status UP";
         }
         leaf tvlan-down-count {
           type int32;
           description
             "Number of tagged Vlans with status DOWN";
         }
         leaf other {
           type int32;
           description
             "Number of dynamic and other Logical Interfaces ";
         }
         leaf other-up-count {
           type int32;
           description
             "Number of Other Logical Interfaces with status UP";
         }
         leaf other-down-count {
           type int32;
           description
             "Number of Other Logical Interfaces with status DOWN";
         }
       }
     }
     container docsis-information {
       container docsis-status-information {
         description
           "Status of DOCSIS interface";
         leaf docsis-state {
           type string;
           description
             "State of the DOCSIS interface";
         }
         leaf docsis-mode {
           type string;
           description
             "DOCSIS mode (2.0/3.0) of the DOCSIS interface";
         }
         leaf docsis-upstream-speed {
           type string;
           description
             "Operational upstream speed of the interface";
         }
         leaf downstream-scanning {
           type string;
           description
             "Result of scanning in downstream direction";
         }
         leaf ranging {
           type string;
           description
             "Result of ranging action";
         }
         leaf signal-to-noise-ratio {
           type string;
           description
             "Signal to noise ratio for all channels";
         }
         leaf power {
           type string;
           description
             "Operational power of the signal on all channels";
         }
       }
       container docsis-media-properties {
         description
           "Information about media properties of DOCSIS interface";
         leaf downstream-buffers-free {
           type int32;
           description
             "Number of free buffers in downstream direction";
         }
         leaf downstream-buffers-used {
           type int32;
           description
             "Number of buffers used in downstream direction";
         }
         leaf upstream-buffers-used {
           type int32;
           description
             "Number of buffers used in upstream direction";
         }
         leaf upstream-buffers-free {
           type int32;
           description
             "Number of free buffers in upstream direction";
         }
         leaf request-opportunity-burst {
           type int32;
           description
             "Size of requested burst in upstream direction";
         }
         leaf physical-burst {
           type int32;
           description
             "Size of burst in downstream direction";
         }
         leaf tuner-frequency {
           type string;
           description
             "Frequency of operation of the tuner";
         }
         leaf standard-short-grant {
           type int32;
           description
             "Size of the short grant given by CMTS";
         }
         leaf standard-long-grant {
           type int32;
           description
             "Size of the long grant given by CMTS";
         }
       }
       container docsis-security-properties {
         description
           "Information on security related properties of DOCSIS interface";
         leaf docsis-bpi {
           type string;
           description
             "State of baseline privacy negotiation";
         }
         leaf encryption-algorithm {
           type string;
           description
             "Type of encryption algorithm used";
         }
         leaf key-length {
           type int32;
           description
             "Length of the key used to encrypt data";
         }
       }
     }
     leaf sample-string {
       type string;
     }
   }
   grouping mc-ae-status-information-list-block {
     container mc-ae-status-information {
       description
         "Information about an mc-ae";
       container mc-ae-status {
         leaf member-link {
           type string;
           description
             "Aggregate interface name";
         }
         leaf init-sm-state {
           type string;
           description
             "Current state of MC-AE state machine";
         }
         leaf cfg-err-status {
           type string;
           description
             "Configuration Error Detected";
         }
         leaf local-status {
           type string;
           description
             "Local MC-AE node status";
         }
         leaf local-state {
           type string;
           description
             "Local MC-AE link state";
         }
         leaf peer-status {
           type string;
           description
             "Peer MC-AE node status";
         }
         leaf peer-state {
           type string;
           description
             "Peer MC-AE link state";
         }
       }
       list mc-ae-revertive-status {
         description
           "Information about Revertive ";
         leaf ae-member-link {
           type string;
           description
             "Aggregate interface name";
         }
         leaf switchover-mode {
           type string;
           description
             "Switchover mode";
         }
         leaf switchover-status {
           type string;
           description
             "Switchover status";
         }
         leaf revert-time {
           type string;
           description
             "Configured Revert Time";
         }
         leaf switchover-remaining-time {
           type string;
           description
             "Remaining time to trigger switchover";
         }
       }
       list mc-ae-ifl-list {
         leaf logical-interface {
           type string;
           description
             "Logical interface name";
         }
         leaf topology-type {
           type string;
           description
             "Topology type";
         }
         leaf local-logical-interface-state {
           type string;
           description
             "Local logical interface MC-AE link state";
         }
         leaf peer-logical-interface-state {
           type string;
           description
             "Peer logical interface MC-AE link state";
         }
         leaf mcp-state {
           type string;
           description
             "Multi Chassis Protection state";
         }
       }
       container mc-ae-stitching-peer {
         leaf stitching-peer {
           type string;
           description
             "Stitching peer name";
         }
       }
       list mc-ae-clink {
         leaf la-status {
           type string;
           description
             "Local Advertised Status";
         }
         leaf pa-status {
           type string;
           description
             "Peer Advertised Status";
         }
         leaf vc-id {
           type uint32;
           description
             "Vc Id";
         }
         leaf local-ip {
           type string;
           description
             "Local Ip Address";
         }
         leaf remote-ip {
           type string;
           description
             "Remote Ip Address";
         }
         leaf clink-state {
           type string;
           description
             "Clink Operation State";
         }
         leaf clink-type {
           type string;
           description
             "Local or Remote clink";
         }
       }
       list mc-ae-additional-information {
         key "mcae-id";
         description
           "Additional Information about LACP,MCAE Parameters ";
         leaf redundancy-grp-id {
           type string;
           description
             "Redundancy Group Id configured";
         }
         leaf mcae-id {
           type string;
           description
             "Local mcae-id configured";
         }
         leaf local-mode {
           type string;
           description
             "Local mcae mode configured";
         }
         leaf local-status-control {
           type string;
           description
             "Local status-control configured";
         }
         leaf local-chassis-id {
           type string;
           description
             "Local Chassis Id configured";
         }
         leaf local-system-id {
           type string;
           description
             "Local System Id configured";
         }
         leaf local-admin-key {
           type string;
           description
             "Local Admin Key Configured";
         }
         leaf local-partner-system-id {
           type string;
           description
             "Local Partner System Id";
         }
         leaf peer-partner-system-id {
           type string;
           description
             "Peer Partner System Id";
         }
       }
     }
   }
   grouping interface-transport-information-block {
     list interface-transport-state {
       leaf interface-transport-admin-state {
         type string;
         description
           "GR1093 Administrative state";
       }
       leaf interface-transport-oper-state {
         type string;
         description
           "GR1093 Operational state";
       }
     }
   }
   grouping interface-filter-information-block {
     list physical-interface {
       key "name";
       description
         "Information about a single physical interface";
       leaf name {
         type string;
         description
           "Name of this item";
       }
       leaf admin-status {
         type string;
         description
           "Desired state of the interface";
       }
       leaf oper-status {
         type string;
         description
           "Current operational state of the interface";
       }
       leaf esi-source-bmac {
         type jt:mac-addr;
         description
           "Ethernet segment source B-MAC for this interface";
       }
       leaf sonet-payload-pointer-curptr {
         type string;
         description
           "Value of the SONET/SDH payload pointer, derived from the H1 and 
           H2 overhead bytes";
       }
       leaf sonet-payload-pointer-ptrinc-count {
         type string;
         description
           "Number of times the value of the SONET/SDH payload pointer had 
           positive justification";
       }
       leaf sonet-payload-pointer-ptrdec-count {
         type string;
         description
           "Number of times the value of the SONET/SDH payload pointer had 
           negative justification";
       }
       leaf sonet-payload-pointer-newptr-ndf-count {
         type string;
         description
           "Number of times a new payload pointer was created with the New 
           Data Found flag set";
       }
       leaf link-partner-status {
         type string;
         description
           "Auto-negotiation status of link partner";
       }
       container optics-diagnostics {
         description
           "Optics diagnostics";
         leaf optic-diagnostics-not-available {
           type string;
           description
             "Optical diagnostics not supported by this transceiver";
         }
         leaf laser-bias-current-not-available {
           type string;
           description
             "Laser bias current measurement not available";
         }
         leaf soa-bias-current-not-available {
           type string;
           description
             "SOA bias current measurement not available";
         }
         leaf laser-tx-power-not-available {
           type string;
           description
             "Laser output power measurement not available";
         }
         leaf module-temperature-not-available {
           type string;
           description
             "Module temperature measurement not available";
         }
         leaf tx-module-temperature-not-available {
           type string;
           description
             "Tx module temperature measurement not available";
         }
         leaf rx-module-temperature-not-available {
           type string;
           description
             "Rx module temperature measurement not available";
         }
         leaf laser-rx-power-not-available {
           type string;
           description
             "Laser receiver optical power measurement not available";
         }
         leaf laser-tx-power-high-alarm-threshold-not-available {
           type string;
           description
             "Laser output power high alarm threshold not available";
         }
         leaf laser-tx-power-low-alarm-threshold-not-available {
           type string;
           description
             "Laser output power low alarm threshold not available";
         }
         leaf laser-tx-power-high-warning-threshold-not-available {
           type string;
           description
             "Laser output power high warning threshold not available";
         }
         leaf laser-tx-power-low-warning-threshold-not-available {
           type string;
           description
             "Laser output power low warning threshold not available";
         }
         leaf laser-bias-current-high-alarm-threshold-not-available {
           type string;
           description
             "Laser bias current high alarm threshold not available";
         }
         leaf laser-bias-current-low-alarm-threshold-not-available {
           type string;
           description
             "Laser bias current low alarm threshold not available";
         }
         leaf laser-bias-current-high-warning-threshold-not-available {
           type string;
           description
             "Laser bias current high warning threshold not available";
         }
         leaf laser-bias-current-low-warning-threshold-not-available {
           type string;
           description
             "Laser bias current low warning threshold not available";
         }
         leaf laser-bias-current {
           type string;
           description
             "Laser bias current (milliamperes)";
         }
         leaf soa-bias-current {
           type string;
           description
             "SOA bias current (milliamperes)";
         }
         leaf laser-output-power {
           type string;
           description
             "Laser output power (milliwatts)";
         }
         leaf laser-output-power-dbm {
           type string;
           description
             "Laser output power (dBm)";
         }
         leaf module-temperature {
           type string;
           description
             "Module temperature";
         }
         leaf tx-module-temperature {
           type string;
           description
             "Tx module temperature";
         }
         leaf rx-module-temperature {
           type string;
           description
             "Rx module temperature";
         }
         leaf host-id {
           type uint32;
           description
             "Host code of this interface";
         }
         leaf media-id {
           type uint32;
           description
             "Media code of this interface";
         }
         leaf host-code-desc {
           type string;
           description
             "Current optics host code";
         }
         leaf media-code-desc {
           type string;
           description
             "Current optics media code";
         }
         leaf module-voltage {
           type string;
           description
             "Module voltage";
         }
         leaf module-max-power {
           type string;
           description
             "Module max power";
         }
         leaf corrected-error-ratio {
           type string;
           description
             "Corrected error ratio";
         }
         leaf uncorrected-words-ratio {
           type string;
           description
             "Uncorrected words ratio";
         }
         leaf tx-module-voltage {
           type string;
           description
             "Tx module voltage";
         }
         leaf rx-module-voltage {
           type string;
           description
             "Rx module voltage";
         }
         leaf rx-signal-avg-optical-power {
           type string;
           description
             "Receiver signal average power (milliwatts)";
         }
         leaf rx-signal-avg-optical-power-dbm {
           type string;
           description
             "Receiver signal average power (dBm)";
         }
         leaf laser-rx-optical-power {
           type string;
           description
             "Laser receiver optical power (milliwatts)";
         }
         leaf laser-rx-optical-power-dbm {
           type string;
           description
             "Laser receiver optical power (dBm)";
         }
         leaf wavelength-channel {
           type string;
           description
             "Wavelength channel number set";
         }
         leaf wavelength-setpoint {
           type string;
           description
             "Wavelength point set";
         }
         leaf tx-dither {
           type string;
           description
             "Tx dither status";
         }
         leaf frequency-error {
           type string;
           description
             "Frequency error value";
         }
         leaf wavelength-error {
           type string;
           description
             "Wavelength error value";
         }
         leaf laser-bias-current-high-alarm {
           type string;
           description
             "Laser bias current high alarm";
         }
         leaf laser-bias-current-low-alarm {
           type string;
           description
             "Laser bias current low alarm";
         }
         leaf laser-bias-current-high-warn {
           type string;
           description
             "Laser bias current high warning";
         }
         leaf laser-bias-current-low-warn {
           type string;
           description
             "Laser bias current low warning";
         }
         leaf soa-bias-current-high-alarm {
           type string;
           description
             "SOA bias current high alarm";
         }
         leaf soa-bias-current-low-alarm {
           type string;
           description
             "SOA bias current low alarm";
         }
         leaf soa-bias-current-high-warn {
           type string;
           description
             "SOA bias current high warning";
         }
         leaf soa-bias-current-low-warn {
           type string;
           description
             "SOA bias current low warning";
         }
         leaf laser-tx-power-high-alarm {
           type string;
           description
             "Laser output power high alarm";
         }
         leaf laser-tx-power-low-alarm {
           type string;
           description
             "Laser output power low alarm";
         }
         leaf laser-tx-power-high-warn {
           type string;
           description
             "Laser output power high warning";
         }
         leaf laser-tx-power-low-warn {
           type string;
           description
             "Laser output power low warning";
         }
         leaf tx-power-high-alarm {
           type string;
           description
             "Tx power high alarm";
         }
         leaf tx-power-low-alarm {
           type string;
           description
             "Tx power low alarm";
         }
         leaf tx-power-high-warn {
           type string;
           description
             "Tx power high warning";
         }
         leaf tx-power-low-warn {
           type string;
           description
             "Tx power low warning";
         }
         leaf module-temperature-high-alarm {
           type string;
           description
             "Module temperature high alarm";
         }
         leaf module-temperature-low-alarm {
           type string;
           description
             "Module temperature low alarm";
         }
         leaf module-temperature-high-warn {
           type string;
           description
             "Module temperature high warning";
         }
         leaf module-temperature-low-warn {
           type string;
           description
             "Module temperature low warning";
         }
         leaf tx-module-temperature-high-alarm {
           type string;
           description
             "Tx module temperature high alarm";
         }
         leaf tx-module-temperature-low-alarm {
           type string;
           description
             "Tx module temperature low alarm";
         }
         leaf rx-module-temperature-high-alarm {
           type string;
           description
             "Rx module temperature high alarm";
         }
         leaf rx-module-temperature-low-alarm {
           type string;
           description
             "Rx module temperature low alarm";
         }
         leaf module-voltage-high-alarm {
           type string;
           description
             "Module voltage high alarm";
         }
         leaf module-voltage-low-alarm {
           type string;
           description
             "Module voltage low alarm";
         }
         leaf module-voltage-high-warn {
           type string;
           description
             "Module voltage high warning";
         }
         leaf module-voltage-low-warn {
           type string;
           description
             "Module voltage low warning";
         }
         leaf tx-module-voltage-high-alarm {
           type string;
           description
             "Tx module voltage high alarm";
         }
         leaf tx-module-voltage-low-alarm {
           type string;
           description
             "Tx module voltage low alarm";
         }
         leaf rx-module-voltage-high-alarm {
           type string;
           description
             "Rx module voltage high alarm";
         }
         leaf rx-module-voltage-low-alarm {
           type string;
           description
             "Rx module voltage low alarm";
         }
         leaf laser-rx-power-high-alarm {
           type string;
           description
             "Laser receiver power high alarm";
         }
         leaf laser-rx-power-low-alarm {
           type string;
           description
             "Laser receiver power low alarm";
         }
         leaf laser-rx-power-high-warn {
           type string;
           description
             "Laser receiver power high warning";
         }
         leaf laser-rx-power-low-warn {
           type string;
           description
             "Laser receiver power low warning";
         }
         leaf rx-power-high-alarm {
           type string;
           description
             "Receiver power high alarm";
         }
         leaf rx-power-low-alarm {
           type string;
           description
             "Receiver power low alarm";
         }
         leaf rx-power-high-warn {
           type string;
           description
             "Receiver power high warning";
         }
         leaf rx-power-low-warn {
           type string;
           description
             "Receiver power low warning";
         }
         leaf laser-end-of-life-alarm {
           type string;
           description
             "Laser end-of-life alarm";
         }
         leaf laser-wavelength-alarm {
           type string;
           description
             "Laser wavelength alarm";
         }
         leaf laser-bias-current-alarm {
           type string;
           description
             "Laser bias current alarm";
         }
         leaf module-temperature-alarm {
           type string;
           description
             "Module temperature alarm";
         }
         leaf laser-power-alarm {
           type string;
           description
             "Laser power alarm";
         }
         leaf modulator-temperature-alarm {
           type string;
           description
             "Modulator temperature alarm";
         }
         leaf modulator-bias-alarm {
           type string;
           description
             "Modulator bias alarm";
         }
         leaf module-not-ready-alarm {
           type string;
           description
             "Module not ready alarm";
         }
         leaf module-power-down-alarm {
           type string;
           description
             "Module power down alarm";
         }
         leaf module-not-init-done-alarm {
           type string;
           description
             "Module initialization not done alarm";
         }
         leaf module-not-high-power-on-alarm {
           type string;
           description
             "Module not high powered on alarm";
         }
         leaf module-fault-alarm {
           type string;
           description
             "Module in fault state alarm";
         }
         leaf pld-flash-init-fault-alarm {
           type string;
           description
             "PLD or Flash initialization fault alarm";
         }
         leaf power-supply-fault-alarm {
           type string;
           description
             "Power supply fault alarm";
         }
         leaf checksum-fault-alarm {
           type string;
           description
             "Checksum fault alarm";
         }
         leaf apd-supply-fault-alarm {
           type string;
           description
             "APD supply fault alarm";
         }
         leaf tec-fault-alarm {
           type string;
           description
             "TEC fault alarm";
         }
         leaf wavelength-unlocked-alarm {
           type string;
           description
             "Wavelength unlocked alarm";
         }
         leaf tx-tune-alarm {
           type string;
           description
             "Tx tune alarm";
         }
         leaf tx-mux-fifo-error-alarm {
           type string;
           description
             "Tx multiplexer fifo error alarm";
         }
         leaf tx-loss-of-pll-alarm {
           type string;
           description
             "Tx loss of PLL alarm";
         }
         leaf tx-data-not-ready-alarm {
           type string;
           description
             "Tx data not ready alarm";
         }
         leaf tx-not-ready-alarm {
           type string;
           description
             "Tx not ready alarm";
         }
         leaf tx-laser-fault-alarm {
           type string;
           description
             "Tx laser fault alarm";
         }
         leaf tx-laser-disabled-alarm {
           type string;
           description
             "Tx laser disabled alarm";
         }
         leaf tx-loss-of-signal-functionality-alarm {
           type string;
           description
             "Tx loss of signal functionality alarm";
         }
         leaf tx-cdr-loss-of-lock-alarm {
           type string;
           description
             "Tx CDR loss of lock alarm";
         }
         leaf rx-loss-avg-opt-power-alarm {
           type string;
           description
             "Receiver loss of average optical power alarm";
         }
         leaf rx-loss-ac-power-alarm {
           type string;
           description
             "Receiver loss of AC power alarm";
         }
         leaf rx-loss-of-pll-alarm {
           type string;
           description
             "Receiver loss of PLL alarm";
         }
         leaf rx-not-ready-alarm {
           type string;
           description
             "Receiver not ready alarm";
         }
         leaf rx-loss-of-signal-alarm {
           type string;
           description
             "Receiver loss of signal alarm";
         }
         leaf rx-cdr-loss-of-lock-alarm {
           type string;
           description
             "Receiver CDR loss of lock alarm";
         }
         leaf laser-bias-current-high-alarm-threshold {
           type string;
           description
             "Laser bias current high alarm threshold (milliamperes)";
         }
         leaf laser-bias-current-low-alarm-threshold {
           type string;
           description
             "Laser bias current low alarm threshold (milliamperes)";
         }
         leaf laser-bias-current-high-warn-threshold {
           type string;
           description
             "Laser bias current high warning threshold (milliamperes)";
         }
         leaf laser-bias-current-low-warn-threshold {
           type string;
           description
             "Laser bias current low warning threshold (milliamperes)";
         }
         leaf soa-bias-current-high-alarm-threshold {
           type string;
           description
             "SOA bias current high alarm threshold (milliamperes)";
         }
         leaf soa-bias-current-low-alarm-threshold {
           type string;
           description
             "SOA bias current low alarm threshold (milliamperes)";
         }
         leaf soa-bias-current-high-warn-threshold {
           type string;
           description
             "SOA bias current high warning threshold (milliamperes)";
         }
         leaf soa-bias-current-low-warn-threshold {
           type string;
           description
             "SOA bias current low warning threshold (milliamperes)";
         }
         leaf laser-tx-power-high-alarm-threshold {
           type string;
           description
             "Laser transmitter power high alarm threshold (milliwatts)";
         }
         leaf laser-tx-power-high-alarm-threshold-dbm {
           type string;
           description
             "Laser transmitter power high alarm threshold (dBm)";
         }
         leaf laser-tx-power-low-alarm-threshold {
           type string;
           description
             "Laser transmitter power low alarm threshold (milliwatts)";
         }
         leaf laser-tx-power-low-alarm-threshold-dbm {
           type string;
           description
             "Laser transmitter power low alarm threshold (dBm)";
         }
         leaf laser-tx-power-high-warn-threshold {
           type string;
           description
             "Laser transmitter power high warning threshold (milliwatts)";
         }
         leaf laser-tx-power-high-warn-threshold-dbm {
           type string;
           description
             "Laser transmitter power high warning threshold (dBm)";
         }
         leaf laser-tx-power-low-warn-threshold {
           type string;
           description
             "Laser transmitter power low warning threshold (milliwatts)";
         }
         leaf laser-tx-power-low-warn-threshold-dbm {
           type string;
           description
             "Laser transmitter power low warning threshold (dBm)";
         }
         leaf module-temperature-high-alarm-threshold {
           type string;
           description
             "Module temperature high alarm threshold";
         }
         leaf module-temperature-low-alarm-threshold {
           type string;
           description
             "Module temperature low alarm threshold";
         }
         leaf module-temperature-high-warn-threshold {
           type string;
           description
             "Module temperature high warning threshold";
         }
         leaf module-temperature-low-warn-threshold {
           type string;
           description
             "Module temperature low warning threshold";
         }
         leaf laser-temperature-high-alarm-threshold {
           type string;
           description
             "Laser temperature high alarm threshold";
         }
         leaf laser-temperature-low-alarm-threshold {
           type string;
           description
             "Laser temperature low alarm threshold";
         }
         leaf laser-temperature-high-warn-threshold {
           type string;
           description
             "Laser temperature high warning threshold";
         }
         leaf laser-temperature-low-warn-threshold {
           type string;
           description
             "Laser temperature low warning threshold";
         }
         leaf module-voltage-high-alarm-threshold {
           type string;
           description
             "Module voltage high alarm threshold (volts)";
         }
         leaf module-voltage-low-alarm-threshold {
           type string;
           description
             "Module voltage low alarm threshold (volts)";
         }
         leaf module-voltage-high-warn-threshold {
           type string;
           description
             "Module voltage high warning threshold (volts)";
         }
         leaf module-voltage-low-warn-threshold {
           type string;
           description
             "Module voltage low warning threshold (volts)";
         }
         leaf laser-rx-power-high-alarm-threshold {
           type string;
           description
             "Laser receiver power high alarm (milliwatts)";
         }
         leaf laser-rx-power-high-alarm-threshold-dbm {
           type string;
           description
             "Laser receiver power high alarm (dBm)";
         }
         leaf laser-rx-power-low-alarm-threshold {
           type string;
           description
             "Laser receiver power low alarm (milliwatts)";
         }
         leaf laser-rx-power-low-alarm-threshold-dbm {
           type string;
           description
             "Laser receiver power low alarm (dBm)";
         }
         leaf laser-rx-power-high-warn-threshold {
           type string;
           description
             "Laser receiver power high warning (milliwatts)";
         }
         leaf laser-rx-power-high-warn-threshold-dbm {
           type string;
           description
             "Laser receiver power high warning (dBm)";
         }
         leaf laser-rx-power-low-warn-threshold {
           type string;
           description
             "Laser receiver power low warning (milliwatts)";
         }
         leaf laser-rx-power-low-warn-threshold-dbm {
           type string;
           description
             "Laser receiver power low warning (dBm)";
         }
         leaf rx-power-high-alarm-threshold {
           type string;
           description
             "Receiver power high alarm (milliwatts)";
         }
         leaf rx-power-high-alarm-threshold-dbm {
           type string;
           description
             "Receiver power high alarm (dBm)";
         }
         leaf rx-power-low-alarm-threshold {
           type string;
           description
             "Receiver power low alarm (milliwatts)";
         }
         leaf rx-power-low-alarm-threshold-dbm {
           type string;
           description
             "Receiver power low alarm (dBm)";
         }
         leaf rx-power-high-warning-threshold {
           type string;
           description
             "Receiver power high warning (milliwatts)";
         }
         leaf rx-power-high-warning-threshold-dbm {
           type string;
           description
             "Receiver power high warning (dBm)";
         }
         leaf rx-power-low-warning-threshold {
           type string;
           description
             "Receiver power low warning (milliwatts)";
         }
         leaf rx-power-low-warning-threshold-dbm {
           type string;
           description
             "Receiver power low warning (dBm)";
         }
         leaf los-alarm-threshold {
           type string;
           description
             "LOS alarm threshold (milliwatts)";
         }
         leaf los-alarm-threshold-dbm {
           type string;
           description
             "LOS alarm threshold (dBm)";
         }
         leaf los-warning-threshold {
           type string;
           description
             "LOS warning threshold (milliwatts)";
         }
         leaf los-warning-threshold-dbm {
           type string;
           description
             "LOS warning threshold (dBm)";
         }
         leaf dsp-module-state {
           type string;
           description
             "DSP module state";
         }
         leaf rx-pow-manual-threshold-enabled {
           type string;
           description
             "Manual RX Power High Alarm Threshold";
         }
         leaf rx-pow-high-alarm-threshold-manual {
           type string;
           description
             "Manual RX Power High Alarm Threshold";
         }
         leaf rx-pow-high-warning-threshold-manual {
           type string;
           description
             "Manual RX Power High Warning Threshold";
         }
         leaf rx-pow-low-warning-threshold-manual {
           type string;
           description
             "Manual RX Power Low Warning Threshold";
         }
         leaf rx-pow-low-alarm-threshold-manual {
           type string;
           description
             "Manual RX Power Low Alarm Threshold";
         }
         leaf output-power {
           type string;
           description
             "Output power (milliwatts)";
         }
         leaf output-power-dbm {
           type string;
           description
             "Output power (dBm)";
         }
         leaf input-power {
           type string;
           description
             "Input power (milliwatts)";
         }
         leaf input-power-dbm {
           type string;
           description
             "Input power (dBm)";
         }
         leaf per-wave-rx-optical-power {
           type string;
           description
             "Per-wavelength receiver optical power (milliwatts)";
         }
         leaf per-wave-rx-optical-power-dbm {
           type string;
           description
             "Per-wavelength receiver optical power (dBm)";
         }
         leaf lane-laser-frequency-error {
           type string;
           description
             "Lane laser frequency error (MHz)";
         }
         leaf tec-current {
           type string;
           description
             "Tec current";
         }
         leaf residual-isi {
           type string;
           description
             "Residual ISI";
         }
         container optics-diagnostics-ot {
           description
             "OT interface optics diagnostics";
           leaf module-temp-fault {
             type string;
             description
               "Module temperature fault";
           }
           leaf specific-hw-fault {
             type string;
             description
               "Specific HW fault";
           }
           leaf internal-power-fault {
             type string;
             description
               "Internal power fault";
           }
           leaf post-therm-fault {
             type string;
             description
               "Power thermal fault";
           }
           leaf post-fault {
             type string;
             description
               "Post fault";
           }
           leaf command-error {
             type string;
             description
               "Command error";
           }
           leaf rx-pll-lock {
             type string;
             description
               "RX PLL lock";
           }
           leaf network-lane-los {
             type string;
             description
               "Network Lane LOS";
           }
           leaf network-lane-lof {
             type string;
             description
               "Network Lane LOF";
           }
           leaf network-lane-oof {
             type string;
             description
               "Network Lane OOF";
           }
           leaf network-lane-lom {
             type string;
             description
               "Network Lane LOM";
           }
           leaf network-lane-oom {
             type string;
             description
               "Network Lane OOM";
           }
           leaf network-lane-otu-bdi {
             type string;
             description
               "Network Lane OTU BDI";
           }
           leaf lane-rx-fifo-error {
             type string;
             description
               "Lane RX FIFO error";
           }
           leaf tx-reference-clock-fault {
             type string;
             description
               "TX reference clock fault";
           }
           leaf rx-modem-sync-fault {
             type string;
             description
               "Rx modem sync fault";
           }
           leaf rx-modem-loss-of-lock {
             type string;
             description
               "RX modem loss of lock";
           }
           leaf rx-loss-of-alignment {
             type string;
             description
               "RX loss of alignment";
           }
           leaf rx-out-of-alignment {
             type string;
             description
               "RX out of alignment";
           }
           leaf rx-timing-fault {
             type string;
             description
               "Rx timing fault";
           }
           leaf link-msg-data-available {
             type string;
             description
               "Link msg data available";
           }
           leaf modulator-bias-control-loop-fail {
             type string;
             description
               "Modulator Bias Control Loop Fail";
           }
           leaf itla-fault {
             type string;
             description
               "ITLA fault";
           }
           leaf dac-calib-fault {
             type string;
             description
               "DAC calib fault";
           }
           leaf adc-calib-fault {
             type string;
             description
               "ADC calib fault";
           }
           leaf prom-fault {
             type string;
             description
               "PROM fault";
           }
           leaf tx-mod-bias-voa-ctrl-loop-high-alarm {
             type string;
             description
               "TX mod bias VOA ctrl loop high alarm";
           }
           leaf tx-mod-bias-voa-ctrl-loop-low-alarm {
             type string;
             description
               "TX mod bias VOA ctrl loop low alarm";
           }
           leaf rx-phase-control-loop-high-alarm {
             type string;
             description
               "RX phase control loop high alarm";
           }
           leaf rx-phase-control-loop-low-alarm {
             type string;
             description
               "RX phase control loop low alarm";
           }
           leaf rx-phase-control-loop-high-warning {
             type string;
             description
               "RX phase control loop high warning";
           }
           leaf rx-phase-control-loop-low-warning {
             type string;
             description
               "RX phase control loop low warning";
           }
           leaf oa-pump-bias-current-high-alarm {
             type string;
             description
               "OA pump bias current high alarm";
           }
           leaf oa-pump-bias-current-low-alarm {
             type string;
             description
               "OA pump bias current low alarm";
           }
           leaf oa-pump-bias-current-high-warning {
             type string;
             description
               "OA pump bias current high warning";
           }
           leaf oa-pump-bias-current-low-warning {
             type string;
             description
               "OA pump bias current low warning";
           }
           leaf tx-jitter-pll-lol-input-nw-lane {
             type string;
             description
               "Tx jitter PLL LOL i/p nw lane";
           }
           leaf tx-out-of-alignment {
             type string;
             description
               "TX out of alignment";
           }
           leaf tx-cmu-lock-fault {
             type string;
             description
               "Tx CMU lock fault";
           }
           leaf adc-signal-below-threshold {
             type string;
             description
               "ADC signal below threshold";
           }
           leaf tx-output-power-adjustment-fault {
             type string;
             description
               "Tx output power adjustment fault";
           }
           leaf tx-output-mod-converge-fault {
             type string;
             description
               "TX output mod converge fault";
           }
           leaf tx-laser-ready-fault {
             type string;
             description
               "Tx laser ready fault";
           }
           leaf tx-laser-ready-off-fault {
             type string;
             description
               "Tx laser ready off fault";
           }
           leaf tx-asic-ready-fault {
             type string;
             description
               "Tx asic ready fault";
           }
           leaf tx-initialization-fault {
             type string;
             description
               "Tx initialization fault";
           }
           leaf rx-demodulator-lock-fault {
             type string;
             description
               "Rx demodulator lock fault";
           }
           leaf rx-dispersion-lock-fault {
             type string;
             description
               "Rx dispersion lock fault";
           }
           leaf rx-adc-output-fault {
             type string;
             description
               "Rx ADC output fault";
           }
           leaf rx-optical-input-fault {
             type string;
             description
               "Rx optical input fault";
           }
           leaf rx-asic-ready-fault {
             type string;
             description
               "Rx asic ready fault";
           }
           leaf rx-initialization-fault {
             type string;
             description
               "Rx initialization fault";
           }
           leaf tx-mod-bias-high-alarm {
             type string;
             description
               "TX modulator bias high alarm";
           }
           leaf tx-mod-bias-low-alarm {
             type string;
             description
               "TX modulator bias low alarm";
           }
           leaf tx-mod-bias-high-warning {
             type string;
             description
               "TX modulator bias high warning";
           }
           leaf tx-mod-bias-low-warning {
             type string;
             description
               "TX modulator bias low warning";
           }
           leaf rx-pwr-high-alarm {
             type string;
             description
               "RX power high alarm";
           }
           leaf rx-pwr-low-alarm {
             type string;
             description
               "RX power low alarm";
           }
           leaf rx-pwr-high-warn {
             type string;
             description
               "RX power high warning";
           }
           leaf rx-pwr-low-warn {
             type string;
             description
               "RX power low warning";
           }
           leaf tx-laser-power-high-alarm {
             type string;
             description
               "TX laser power high alarm";
           }
           leaf tx-laser-power-low-alarm {
             type string;
             description
               "TX laser power low alarm";
           }
           leaf tx-laser-power-high-warn {
             type string;
             description
               "TX laser power high warning";
           }
           leaf tx-laser-power-low-warn {
             type string;
             description
               "TX laser power low warning";
           }
           leaf tx-bias-high-alarm {
             type string;
             description
               "TX laser current high alarm";
           }
           leaf tx-bias-low-alarm {
             type string;
             description
               "TX laser current low alarm";
           }
           leaf tx-bias-high-warn {
             type string;
             description
               "TX laser current high warning";
           }
           leaf tx-bias-low-warn {
             type string;
             description
               "TX laser current low warning";
           }
           leaf tx-laser-temp-high-alarm {
             type string;
             description
               "TX laser temperature high alarm";
           }
           leaf tx-laser-temp-low-alarm {
             type string;
             description
               "TX laser temperature low alarm";
           }
           leaf tx-laser-temp-high-warn {
             type string;
             description
               "TX laser temperature high warning";
           }
           leaf tx-laser-temp-low-warn {
             type string;
             description
               "TX laser temperature low warning";
           }
         }
         list optics-diagnostics-lane-values {
           key "lane-index";
           leaf lane-index {
             type int32;
           }
           leaf laser-bias-current {
             type string;
             description
               "Laser bias current (milliamperes)";
           }
           leaf laser-bias-current-not-available {
             type string;
             description
               "Laser bias current measurement not available";
           }
           leaf laser-output-power {
             type string;
             description
               "Laser output power (milliwatts)";
           }
           leaf laser-output-power-dbm {
             type string;
             description
               "Laser output power (dBm)";
           }
           leaf output-power {
             type string;
             description
               "Output power (milliwatts)";
           }
           leaf output-power-dbm {
             type string;
             description
               "Output power (dBm)";
           }
           leaf laser-temperature {
             type string;
             description
               "Laser temperature";
           }
           leaf laser-module-temperature {
             type string;
             description
               "Module temperature";
           }
           leaf laser-tx-optical-power {
             type string;
             description
               "Laser transmitter optical power (milliwatts)";
           }
           leaf laser-tx-optical-power-dbm {
             type string;
             description
               "Laser transmitter optical power (dBm)";
           }
           leaf laser-rx-optical-power {
             type string;
             description
               "Laser receiver optical power (milliwatts)";
           }
           leaf laser-rx-optical-power-dbm {
             type string;
             description
               "Laser receiver optical power (dBm)";
           }
           leaf input-power {
             type string;
             description
               "Input power (milliwatts)";
           }
           leaf input-power-dbm {
             type string;
             description
               "Input power (dBm)";
           }
           leaf input-total-power {
             type string;
             description
               "Input power (total) (milliwatts)";
           }
           leaf input-total-power-dbm {
             type string;
             description
               "Input power (dBm)";
           }
           leaf per-wave-rx-optical-power {
             type string;
             description
               "Per-wavelength receiver optical power (milliwatts)";
           }
           leaf per-wave-rx-optical-power-dbm {
             type string;
             description
               "Per-wavelength receiver optical power (dBm)";
           }
           leaf lane-configured-cd {
             type string;
             description
               "Lane configured chromatic dispersion (ps/nm)";
           }
           leaf lane-chromatic-dispersion {
             type string;
             description
               "Lane chromatic dispersion (ps/nm)";
           }
           leaf lane-avg-chromatic-dispersion {
             type string;
             description
               "Lane avg chromatic dispersion (ps/nm)";
           }
           leaf lane-min-chromatic-dispersion {
             type string;
             description
               "Lane min chromatic dispersion (ps/nm)";
           }
           leaf lane-max-chromatic-dispersion {
             type string;
             description
               "Lane max chromatic dispersion (ps/nm)";
           }
           leaf lane-differential-group-delay {
             type string;
             description
               "Lane differential group delay (ps)";
           }
           leaf lane-avg-differential-group-delay {
             type string;
             description
               "Lane avg differential group delay (ps)";
           }
           leaf lane-min-differential-group-delay {
             type string;
             description
               "Lane min differential group delay (ps)";
           }
           leaf lane-max-differential-group-delay {
             type string;
             description
               "Lane max differential group delay (ps)";
           }
           leaf lane-sopmd {
             type string;
             description
               "Lane sopmd";
           }
           leaf lane-avg-sopmd {
             type string;
             description
               "Lane avg sopmd";
           }
           leaf lane-min-sopmd {
             type string;
             description
               "Lane min sopmd";
           }
           leaf lane-max-sopmd {
             type string;
             description
               "Lane max sopmd";
           }
           leaf q-factor {
             type string;
             description
               "Lane q-factor";
           }
           leaf q-factor-not-available {
             type string;
             description
               "Lane q-factor not available";
           }
           leaf q-margin {
             type string;
             description
               "Lane q-margin";
           }
           leaf q-margin-not-available {
             type string;
             description
               "Lane q-margin not available";
           }
           leaf lane-state-of-polarization {
             type string;
             description
               "Lane state of polarization (rad/s)";
           }
           leaf lane-avg-state-of-polarization {
             type string;
             description
               "Lane avg state of polarization (rad/s)";
           }
           leaf lane-min-state-of-polarization {
             type string;
             description
               "Lane min state of polarization (rad/s)";
           }
           leaf lane-max-state-of-polarization {
             type string;
             description
               "Lane max state of polarization (rad/s)";
           }
           leaf lane-polarization-dependent-loss {
             type string;
             description
               "Lane polarization dependent loss (dB)";
           }
           leaf lane-avg-polarization-dependent-loss {
             type string;
             description
               "Lane avg polarization dependent loss (dB)";
           }
           leaf lane-min-polarization-dependent-loss {
             type string;
             description
               "Lane min polarization dependent loss (dB)";
           }
           leaf lane-max-polarization-dependent-loss {
             type string;
             description
               "Lane max polarization dependent loss (dB)";
           }
           leaf lane-q2-factor {
             type string;
             description
               "Lane Q2 factor (dB)";
           }
           leaf lane-q-value {
             type string;
             description
               "Lane q value (dB)";
           }
           leaf lane-avg-q-value {
             type string;
             description
               "Lane avg q value (dB)";
           }
           leaf lane-min-q-value {
             type string;
             description
               "Lane min q value (dB)";
           }
           leaf lane-max-q-value {
             type string;
             description
               "Lane max q value (dB)";
           }
           leaf lane-carrier-frequency-offset {
             type string;
             description
               "Lane carrier frequency offset (MHz)";
           }
           leaf lane-avg-carrier-frequency-offset {
             type string;
             description
               "Lane avg carrier frequency offset (MHz)";
           }
           leaf lane-min-carrier-frequency-offset {
             type string;
             description
               "Lane min carrier frequency offset (MHz)";
           }
           leaf lane-max-carrier-frequency-offset {
             type string;
             description
               "Lane max carrier frequency offset (MHz)";
           }
           leaf lane-electrical-snr {
             type string;
             description
               "Lane electrical SNR (dB)";
           }
           leaf lane-snr {
             type string;
             description
               "Lane snr (dB)";
           }
           leaf lane-avg-snr {
             type string;
             description
               "Lane avg snr (dB)";
           }
           leaf lane-min-snr {
             type string;
             description
               "Lane min snr (dB)";
           }
           leaf lane-max-snr {
             type string;
             description
               "Lane max snr (dB)";
           }
           leaf lane-rx-laser-bias {
             type string;
             description
               "Lane rx laser bias (mA)";
           }
           leaf lane-rx-laser-power {
             type string;
             description
               "Lane rx laser power (dBm)";
           }
           leaf lane-rx-laser-temp {
             type string;
             description
               "Lane rx laser temp (C)";
           }
           leaf lane-tx-modulator-bias-x-i {
             type string;
             description
               "Lane tx modulator bias x i (mV)";
           }
           leaf lane-tx-modulator-bias-x-q {
             type string;
             description
               "Lane tx modulator bias x q (mV)";
           }
           leaf lane-tx-modulator-bias-y-i {
             type string;
             description
               "Lane tx modulator bias y i (mV)";
           }
           leaf lane-tx-modulator-bias-y-q {
             type string;
             description
               "Lane tx modulator bias y q (mV)";
           }
           leaf lane-tx-modulator-bias-x-phase {
             type string;
             description
               "Lane tx modulator bias x phase (mV)";
           }
           leaf lane-tx-modulator-bias-y-phase {
             type string;
             description
               "Lane tx modulator bias y phase (mV)";
           }
           leaf tx-input-equalization {
             type string;
             description
               "Tx input equalization";
           }
           leaf rx-output-amplitude {
             type string;
             description
               "Rx output amplitude";
           }
           leaf rx-output-pre-emphasis {
             type string;
             description
               "Rx output pre epmhasis";
           }
           leaf lane-laser-frequency-error {
             type string;
             description
               "Lane laser frequency error (MHz)";
           }
           leaf tec-current {
             type string;
             description
               "Tec current";
           }
           leaf residual-isi {
             type string;
             description
               "Residual ISI";
           }
           leaf pam-histogram {
             type string;
             description
               "PAM histogram";
           }
           leaf laser-bias-current-high-alarm {
             type string;
             description
               "Laser bias current high alarm";
           }
           leaf laser-bias-current-low-alarm {
             type string;
             description
               "Laser bias current low alarm";
           }
           leaf laser-bias-current-high-warn {
             type string;
             description
               "Laser bias current high warning";
           }
           leaf laser-bias-current-low-warn {
             type string;
             description
               "Laser bias current low warning";
           }
           leaf laser-tx-power-high-alarm {
             type string;
             description
               "Laser output power high alarm";
           }
           leaf laser-tx-power-low-alarm {
             type string;
             description
               "Laser output power low alarm";
           }
           leaf laser-tx-power-high-warn {
             type string;
             description
               "Laser output power high warning";
           }
           leaf laser-tx-power-low-warn {
             type string;
             description
               "Laser output power low warning";
           }
           leaf tx-power-high-alarm {
             type string;
             description
               "Tx power high alarm";
           }
           leaf tx-power-low-alarm {
             type string;
             description
               "Tx power low alarm";
           }
           leaf tx-power-high-warn {
             type string;
             description
               "Tx power high warning";
           }
           leaf tx-power-low-warn {
             type string;
             description
               "Tx power low warning";
           }
           leaf laser-temp-high-alarm {
             type string;
             description
               "Laser temperature high alarm";
           }
           leaf laser-temp-low-alarm {
             type string;
             description
               "Laser temperature low alarm";
           }
           leaf laser-temp-high-warn {
             type string;
             description
               "Laser temperature high warning";
           }
           leaf laser-temp-low-warn {
             type string;
             description
               "Laser temperature low warning";
           }
           leaf laser-rx-power-high-alarm {
             type string;
             description
               "Laser receiver power high alarm";
           }
           leaf laser-rx-power-low-alarm {
             type string;
             description
               "Laser receiver power low alarm";
           }
           leaf laser-rx-power-high-warn {
             type string;
             description
               "Laser receiver power high warning";
           }
           leaf laser-rx-power-low-warn {
             type string;
             description
               "Laser receiver power low warning";
           }
           leaf rx-power-high-alarm {
             type string;
             description
               "Receiver power high alarm";
           }
           leaf rx-power-low-alarm {
             type string;
             description
               "Receiver power low alarm";
           }
           leaf rx-power-high-warn {
             type string;
             description
               "Receiver power high warning";
           }
           leaf rx-power-low-warn {
             type string;
             description
               "Receiver power low warning";
           }
           leaf tx-loss-of-signal-functionality-alarm {
             type string;
             description
               "Tx loss of signal functionality alarm";
           }
           leaf rx-loss-of-signal-functionality-alarm {
             type string;
             description
               "Rx loss of signal functionality alarm";
           }
           leaf tx-cdr-loss-of-lock-alarm {
             type string;
             description
               "Tx CDR loss of lock alarm";
           }
           leaf tx-loss-of-signal-alarm {
             type string;
             description
               "Transmitter loss of signal alarm";
           }
           leaf rx-loss-of-signal-alarm {
             type string;
             description
               "Receiver loss of signal alarm";
           }
           leaf tx-laser-disabled-alarm {
             type string;
             description
               "Tx laser disabled alarm";
           }
           leaf rx-cdr-loss-of-lock-alarm {
             type string;
             description
               "Receiver CDR loss of lock alarm";
           }
           leaf tec-fault-alarm {
             type string;
             description
               "TEC fault alarm";
           }
           leaf wavelength-unlocked-alarm {
             type string;
             description
               "Wavelength unlocked alarm";
           }
           leaf apd-supply-fault-alarm {
             type string;
             description
               "APD supply fault alarm";
           }
           leaf tx-channel-disabled-alarm {
             type string;
             description
               "Tx channel disabled alarm";
           }
           leaf rx-channel-disabled-alarm {
             type string;
             description
               "Rx channel disabled alarm";
           }
           leaf tx-output-disabled-alarm {
             type string;
             description
               "Rx laser disabled alarm";
           }
           leaf rx-output-disabled-alarm {
             type string;
             description
               "Rx laser disabled alarm";
           }
           leaf tx-squelch-disabled-alarm {
             type string;
             description
               "Tx squelch disabled alarm";
           }
           leaf rx-squelch-disabled-alarm {
             type string;
             description
               "Rx squelch disabled alarm";
           }
           leaf laser-end-of-life-alarm {
             type string;
             description
               "Laser end-of-life alarm";
           }
           leaf lane-cd {
             type string;
             description
               "Lane chromatic dispersion";
           }
           leaf lane-dgd {
             type string;
             description
               "Lane differential group delay";
           }
           leaf lane-cfo {
             type string;
             description
               "Lane carrier frequency offset";
           }
           leaf lane-pdl {
             type string;
             description
               "Lane polarization dependent loss";
           }
           leaf lane-osnr {
             type string;
             description
               "Optical signal-to-noise ratio(dB)";
           }
         }
       }
       container optics-diagnostics-vendor-extension {
         description
           "Optics diagnostics vendor extension";
         leaf optics-vendor-part-number {
           type string;
           description
             "Optics component vendor part number";
         }
         leaf optics-vendor-material-number {
           type string;
           description
             "Optic component vendor material number";
         }
       }
       list optics-chromatics {
         key "optics-chromatic-diagnostics-support";
         leaf optics-chromatic-diagnostics-support {
           type string;
           description
             "Optics chromatic not supported for interface";
         }
         leaf opticstype {
           type string;
           description
             "Type of optical module";
         }
         list optics-chromatic {
           key "supported-cd supported-mediaid";
           leaf supported-speed {
             type string;
             description
               "Supported Speed";
           }
           leaf supported-cd {
             type string;
             description
               "Supported Chromatic Dispersion";
           }
           leaf supported-distance {
             type string;
             description
               "Supported Distance";
           }
           leaf supported-mediaid {
             type string;
             description
               "Supported Mediaid";
           }
         }
       }
       list jrr-optics-diagnostics {
         description
           "Optics diagnostics";
         leaf jrr-optics-diagnostics-not-available {
           type string;
           description
             "Optical diagnostics not available at this time for this 
             transceiver";
         }
         leaf laser-bias-current {
           type string;
           description
             "Laser bias current (milliamperes)";
         }
         leaf laser-output-power {
           type string;
           description
             "Laser output power (milliwatts)";
         }
         leaf module-temperature {
           type string;
           description
             "Module temperature";
         }
         leaf module-voltage {
           type string;
           description
             "Module voltage";
         }
         leaf module-max-power {
           type string;
           description
             "Module max power";
         }
         leaf rx-signal-avg-optical-power {
           type string;
           description
             "Receiver signal average power (milliwatts)";
         }
         leaf laser-bias-current-high-alarm {
           type string;
           description
             "Laser bias current high alarm";
         }
         leaf laser-bias-current-low-alarm {
           type string;
           description
             "Laser bias current low alarm";
         }
         leaf laser-bias-current-high-warn {
           type string;
           description
             "Laser bias current high warning";
         }
         leaf laser-bias-current-low-warn {
           type string;
           description
             "Laser bias current low warning";
         }
         leaf laser-tx-power-high-alarm {
           type string;
           description
             "Laser output power high alarm";
         }
         leaf laser-tx-power-low-alarm {
           type string;
           description
             "Laser output power low alarm";
         }
         leaf laser-tx-power-high-warn {
           type string;
           description
             "Laser output power high warning";
         }
         leaf laser-tx-power-low-warn {
           type string;
           description
             "Laser output power low warning";
         }
         leaf module-temperature-high-alarm {
           type string;
           description
             "Module temperature high alarm";
         }
         leaf module-temperature-low-alarm {
           type string;
           description
             "Module temperature low alarm";
         }
         leaf module-temperature-high-warn {
           type string;
           description
             "Module temperature high warning";
         }
         leaf module-temperature-low-warn {
           type string;
           description
             "Module temperature low warning";
         }
         leaf module-voltage-high-alarm {
           type string;
           description
             "Module voltage high alarm";
         }
         leaf module-voltage-low-alarm {
           type string;
           description
             "Module voltage low alarm";
         }
         leaf module-voltage-high-warn {
           type string;
           description
             "Module voltage high warning";
         }
         leaf module-voltage-low-warn {
           type string;
           description
             "Module voltage low warning";
         }
         leaf laser-rx-power-high-alarm {
           type string;
           description
             "Laser receiver power high alarm";
         }
         leaf laser-rx-power-low-alarm {
           type string;
           description
             "Laser receiver power low alarm";
         }
         leaf laser-rx-power-high-warn {
           type string;
           description
             "Laser receiver power high warning";
         }
         leaf laser-rx-power-low-warn {
           type string;
           description
             "Laser receiver power low warning";
         }
         leaf laser-bias-current-high-alarm-threshold {
           type string;
           description
             "Laser bias current high alarm threshold (milliamperes)";
         }
         leaf laser-bias-current-low-alarm-threshold {
           type string;
           description
             "Laser bias current low alarm threshold (milliamperes)";
         }
         leaf laser-bias-current-high-warn-threshold {
           type string;
           description
             "Laser bias current high warning threshold (milliamperes)";
         }
         leaf laser-bias-current-low-warn-threshold {
           type string;
           description
             "Laser bias current low warning threshold (milliamperes)";
         }
         leaf laser-tx-power-high-alarm-threshold {
           type string;
           description
             "Laser transmitter power high alarm threshold (milliwatts)";
         }
         leaf laser-tx-power-low-alarm-threshold {
           type string;
           description
             "Laser transmitter power low alarm threshold (milliwatts)";
         }
         leaf laser-tx-power-high-warn-threshold {
           type string;
           description
             "Laser transmitter power high warning threshold (milliwatts)";
         }
         leaf laser-tx-power-low-warn-threshold {
           type string;
           description
             "Laser transmitter power low warning threshold (milliwatts)";
         }
         leaf module-temperature-high-alarm-threshold {
           type string;
           description
             "Module temperature high alarm threshold";
         }
         leaf module-temperature-low-alarm-threshold {
           type string;
           description
             "Module temperature low alarm threshold";
         }
         leaf module-temperature-high-warn-threshold {
           type string;
           description
             "Module temperature high warning threshold";
         }
         leaf module-temperature-low-warn-threshold {
           type string;
           description
             "Module temperature low warning threshold";
         }
         leaf module-voltage-high-alarm-threshold {
           type string;
           description
             "Module voltage high alarm threshold (volts)";
         }
         leaf module-voltage-low-alarm-threshold {
           type string;
           description
             "Module voltage low alarm threshold (volts)";
         }
         leaf module-voltage-high-warn-threshold {
           type string;
           description
             "Module voltage high warning threshold (volts)";
         }
         leaf module-voltage-low-warn-threshold {
           type string;
           description
             "Module voltage low warning threshold (volts)";
         }
         leaf laser-rx-power-high-alarm-threshold {
           type string;
           description
             "Laser receiver power high alarm (milliwatts)";
         }
         leaf laser-rx-power-low-alarm-threshold {
           type string;
           description
             "Laser receiver power low alarm (milliwatts)";
         }
         leaf laser-rx-power-high-warn-threshold {
           type string;
           description
             "Laser receiver power high warning (milliwatts)";
         }
         leaf laser-rx-power-low-warn-threshold {
           type string;
           description
             "Laser receiver power low warning (milliwatts)";
         }
       }
       container optics-properties {
         description
           "Optics properties";
         leaf wavelength {
           type string;
           description
             "Wavelength of optics in nanometers";
         }
         leaf frequency {
           type string;
           description
             "Frequency of optics in terahertz";
         }
         leaf optic-loopback {
           type string;
           description
             "Optic loopback status";
         }
         leaf optic-loopback-type {
           type string;
           description
             "Optic loopback type";
         }
         leaf media-code-desc {
           type string;
           description
             "Current optics media code";
         }
         leaf host-code-desc {
           type string;
           description
             "Current optics host code";
         }
       }
       container queue-counters {
         description
           "Queue counter statistics";
         leaf queue-counters-error-message {
           type string;
           description
             "Queue statistics not available for this interface";
         }
         container interface-cos-short-summary {
           description
             "Summary of queue information on an interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
         }
         list queue {
           key "queue-number";
           description
             "Counters for a single queue";
           leaf queue-number {
             type uint32;
             description
               "Queue number";
           }
           leaf queue-counters-queued-packets {
             type int32;
             description
               "Queued packet count";
           }
           leaf queue-counters-trans-packets {
             type int32;
             description
               "Total number of transmitted packets";
           }
           leaf queue-counters-total-drop-packets {
             type int32;
             description
               "Number of total packets dropped at the queue";
           }
           leaf forwarding-class-name {
             type string;
             description
               "Forwarding class name associated with queue";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-queued-packets-na {
             type string;
             description
               "Queued packets not available";
           }
           leaf queue-counters-queued-bytes-na {
             type string;
             description
               "Queued bytes not available";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets-na {
             type string;
             description
               "Number of packets dropped due to tail drop not available";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of packets dropped at tail drop of the queue";
           }
           leaf queue-counters-tail-drop-bytes-rate {
             type int32;
             description
               "Number of packets dropped at tail drop of the queue";
           }
           leaf queue-counters-ecn-ce-packets {
             type int32;
             description
               "Total number of ECN CE packets";
           }
           leaf queue-counters-ecn-ce-packets-rate {
             type int32;
             description
               "Rate at which ECN CE packets are transmitted";
           }
           leaf queue-counters-ecn-ce-bytes {
             type int32;
             description
               "Total number of ECN CE bytes";
           }
           leaf queue-counters-ecn-ce-bytes-rate {
             type int32;
             description
               "Rate at which ECN CE bytes are transmitted";
           }
           leaf queue-counters-rate-limit-drop-packets-na {
             type string;
             description
               "Number of packets dropped due to rate-limit drop not 
               available";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes-na {
             type string;
             description
               "Number of bytes dropped due to tail drop not available";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets-na {
             type string;
             description
               "Number of packets dropped due to RED not available";
           }
           leaf queue-counters-red-packets {
             type int32;
             description
               "Number of packets dropped due to RED";
           }
           leaf queue-counters-red-packets-rate {
             type int32;
             description
               "Rate at which packets are dropped due to RED";
           }
           leaf queue-counters-red-packets-ln {
             type int32;
             description
               "Number of RED dropped low-loss, non-TCP packets";
           }
           leaf queue-counters-red-packets-rate-ln {
             type int32;
             description
               "RED drop rate for low-loss, non-TCP packets";
           }
           leaf queue-counters-red-packets-lt {
             type int32;
             description
               "Number of RED dropped of low-loss, TCP packets";
           }
           leaf queue-counters-red-packets-rate-lt {
             type int32;
             description
               "RED drop rate for low-loss, TCP packets";
           }
           leaf queue-counters-red-packets-hn {
             type int32;
             description
               "Number of RED dropped high-loss, non-TCP packets";
           }
           leaf queue-counters-red-packets-rate-hn {
             type int32;
             description
               "RED drop rate for high-loss, non-TCP packets";
           }
           leaf queue-counters-red-packets-ht {
             type int32;
             description
               "Number of RED dropped high-loss, TCP packets";
           }
           leaf queue-counters-red-packets-rate-ht {
             type int32;
             description
               "RED drop rate for high-loss, TCP packets";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-medium {
             type int32;
             description
               "Number of RED dropped medium-loss packets";
           }
           leaf queue-counters-red-packets-rate-medium {
             type int32;
             description
               "RED drop rate for medium-loss packets";
           }
           leaf queue-counters-red-packets-high {
             type int32;
             description
               "Number of RED dropped high-loss packets";
           }
           leaf queue-counters-red-packets-rate-high {
             type int32;
             description
               "RED drop rate for high-loss packets";
           }
           leaf queue-counters-red-bytes-na {
             type string;
             description
               "Number of bytes dropped due to RED not available";
           }
           leaf queue-counters-red-bytes {
             type int32;
             description
               "Number of bytes dropped due to RED";
           }
           leaf queue-counters-red-bytes-rate {
             type int32;
             description
               "Rate at which bytes are dropped due to RED";
           }
           leaf queue-counters-red-bytes-ln {
             type int32;
             description
               "Number of RED dropped low-loss, non-TCP bytes";
           }
           leaf queue-counters-red-bytes-rate-ln {
             type int32;
             description
               "RED drop rate for low-loss, non-TCP bytes";
           }
           leaf queue-counters-red-bytes-lt {
             type int32;
             description
               "Number of RED dropped low-loss, TCP bytes";
           }
           leaf queue-counters-red-bytes-rate-lt {
             type int32;
             description
               "RED drop rate for low-loss, TCP bytes";
           }
           leaf queue-counters-red-bytes-hn {
             type int32;
             description
               "Number of RED dropped high-loss, non-TCP bytes";
           }
           leaf queue-counters-red-bytes-rate-hn {
             type int32;
             description
               "RED drop rate for high-loss, non-TCP bytes";
           }
           leaf queue-counters-red-bytes-ht {
             type int32;
             description
               "Number of RED dropped high-loss, TCP bytes";
           }
           leaf queue-counters-red-bytes-rate-ht {
             type int32;
             description
               "RED drop rate for high-loss, TCP bytes";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-medium {
             type int32;
             description
               "Number of RED dropped medium-loss bytes";
           }
           leaf queue-counters-red-bytes-rate-medium {
             type int32;
             description
               "RED drop rate for medium-loss bytes";
           }
           leaf queue-counters-red-bytes-high {
             type int32;
             description
               "Number of RED dropped high-loss bytes";
           }
           leaf queue-counters-red-bytes-rate-high {
             type int32;
             description
               "RED drop rate for high-loss bytes";
           }
           leaf queue-counters-timestamp {
             type int32;
             description
               "Last packet enqueued timestamp";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
           leaf queue-counters-reserved-buffer-packets {
             type int32;
             description
               "Queues's usage of reserved buffer pool in pkts";
           }
           leaf queue-counters-reserved-buffer-bytes {
             type int32;
             description
               "Queues's usage of reserved buffer pool in bytes";
           }
           leaf queue-counters-shared-buffer-packets {
             type int32;
             description
               "Queues's usage of shared buffer pool in pkts";
           }
           leaf queue-counters-shared-buffer-bytes {
             type int32;
             description
               "Queues's usage of shared buffer pool in bytes";
           }
           leaf queue-counters-depth-average {
             type int32;
             description
               "Time averaged queue depth";
           }
           leaf queue-counters-depth-current {
             type int32;
             description
               "Current instantaneous queue depth";
           }
           leaf queue-counters-depth-peak {
             type int32;
             description
               "Peak queue depth";
           }
           leaf queue-counters-depth-max {
             type int32;
             description
               "Maximum queue depth attained";
           }
           leaf queue-counters-srx-reserved-buffer-bytes {
             type int32;
             description
               "Queues's usage of reserved buffer pool in bytes";
           }
           leaf queue-counters-srx-depth-current {
             type int32;
             description
               "Current instantaneous queue depth";
           }
         }
         container interface-cos-summary {
           description
             "Summary of forwarding class and queue information on an 
             interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
           leaf intf-cos-burst-size-for-ifl {
             type int32;
             description
               "Burst size for the logical interface";
           }
         }
       }
       container voq-counters {
         description
           "VOQ counter statistics";
         leaf voq-counters-error-message {
           type string;
           description
             "VOQ statistics not available for this interface";
         }
         container voq {
           description
             "Counters for a single voq";
           container fpc {
             description
               "Counters for a single FPC";
             leaf fpc-no {
               type int32;
               description
                 "FPC number";
             }
             container pfe {
               description
                 "Counters for a single PFE";
               leaf-list pfe-no {
                 type int32;
                 description
                   "PFE number";
               }
               leaf voq-counters-tail-drop-packets {
                 type int32;
                 description
                   "Tail DROP packet count";
               }
               leaf voq-counters-tail-drop-packets-rate {
                 type int32;
                 description
                   "Rate at which tail packets are dropped";
               }
               leaf voq-counters-tail-drop-bytes {
                 type int32;
                 description
                   "Tail DROP bytes count";
               }
               leaf voq-counters-tail-drop-bytes-rate {
                 type int32;
                 description
                   "Rate at which tail bytes are dropped";
               }
               leaf voq-counters-drop-packets {
                 type int32;
                 description
                   "DROP packet count";
               }
               leaf voq-counters-drop-packets-rate {
                 type int32;
                 description
                   "Rate at which packets are dropped";
               }
               leaf voq-counters-drop-bytes {
                 type int32;
                 description
                   "DROP bytes count";
               }
               leaf voq-counters-drop-bytes-rate {
                 type int32;
                 description
                   "Rate at which bytes are dropped";
               }
               leaf voq-counters-queued-packets {
                 type int32;
                 description
                   "QUEUED packets count";
               }
               leaf voq-counters-queued-packets-rate {
                 type int32;
                 description
                   "Rate at which packets are queued";
               }
               leaf voq-counters-queued-bytes {
                 type int32;
                 description
                   "QUEUED bytes count";
               }
               leaf voq-counters-queued-bytes-rate {
                 type int32;
                 description
                   "Rate at which bytes are queued";
               }
               leaf voq-counters-transmitted-packets {
                 type int32;
                 description
                   "Transmitted packets count";
               }
               leaf voq-counters-transmitted-packets-rate {
                 type int32;
                 description
                   "Rate at which packets are transmitted";
               }
               leaf voq-counters-transmitted-bytes {
                 type int32;
                 description
                   "Transmitted bytes count";
               }
               leaf voq-counters-transmitted-bytes-rate {
                 type int32;
                 description
                   "Rate at which bytes are transmitted";
               }
               leaf voq-counters-queue-depth-bytes-current {
                 type int32;
                 description
                   "Current queue length";
               }
               leaf voq-counters-queue-depth-bytes-peak {
                 type int32;
                 description
                   "Peak queue length";
               }
               leaf voq-counters-queue-depth-bytes-average {
                 type int32;
                 description
                   "Average queue length";
               }
             }
           }
           leaf queue-number {
             type uint32;
             description
               "Queue number";
           }
           leaf forwarding-class-name {
             type string;
             description
               "Forwarding class name associated with queue";
           }
           leaf restricted-forwarding-class-name {
             type string;
           }
         }
       }
       container smart-sfp-av-titan-statistics {
         description
           "AimValley Smart SFP statistics";
         leaf smart-sfp-av-titan-error-message {
           type string;
           description
             "AV Smart SFP un-available";
         }
         container smart-sfp-av-titan-eth-port-statistics {
           leaf rx-crct-frames {
             type uint32;
           }
           leaf rx-crct-bytes {
             type uint32;
           }
           leaf rx-fragments {
             type uint32;
           }
           leaf rx-crct-unicast-frames {
             type uint32;
           }
           leaf rx-crct-multicast-frames {
             type uint32;
           }
           leaf rx-crct-broadcast-frames {
             type uint32;
           }
           leaf rx-err-fcs-frames {
             type uint32;
           }
           leaf rx-len-err-frames {
             type uint32;
           }
           leaf rx-undersize-frames {
             type uint32;
           }
           leaf rx-oversize-frames {
             type uint32;
           }
           leaf rx-inv-vlan-mismatch-frames {
             type uint32;
           }
           leaf rx-discarded-frames {
             type uint32;
           }
           leaf rx-dropped-q-overflow-frames {
             type uint32;
           }
           leaf tx-frames {
             type uint32;
           }
           leaf tx-bytes {
             type uint32;
           }
           leaf tx-unicast-frames {
             type uint32;
           }
           leaf tx-multicast-frames {
             type uint32;
           }
           leaf tx-broadcast-frames {
             type uint32;
           }
         }
         container smart-sfp-av-titan-iwf-statistics {
           leaf rx-packets {
             type uint32;
           }
           leaf tx-packets {
             type uint32;
           }
           leaf malformed-packets {
             type uint32;
           }
           leaf reordered-packets {
             type uint32;
           }
           leaf misordered-dropped-packets {
             type uint32;
           }
           leaf missing-packets {
             type uint32;
           }
           leaf played-out-packets {
             type uint32;
           }
           leaf jb-overrun {
             type uint32;
           }
           leaf jb-underrun {
             type uint32;
           }
         }
         container smart-sfp-av-titan-ds3-statistics {
           leaf rx-bpvexzerrors {
             type uint32;
           }
           leaf rx-cvperrors {
             type uint32;
           }
           leaf b3-errors {
             type uint32;
           }
         }
         container smart-sfp-av-titan-stm-statistics {
           leaf rx-b1-errors {
             type uint32;
           }
           leaf tx-b1-errors {
             type uint32;
           }
         }
       }
       container smart-sfp-av-titan-defects {
         description
           "AimValley Smart SFP defects";
         container smart-sfp-av-titan-defect-list {
           leaf sfp-tdm-defects {
             type string;
           }
           leaf sfp-system-defects {
             type string;
           }
         }
       }
       container forwarding-class-counters {
         description
           "Forwarding-class counter statistics";
         leaf forwarding-class-counters-error-message {
           type string;
           description
             "Forwarding-class statistics not available for this interface";
         }
         container ipv4-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container ipv6-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container mpls-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container layer2-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container other-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container protocol-aggregate-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container forwarding-class-statistics {
           container protocol-aggregate-forwarding-class-counters {
           }
           container ipv4-forwarding-class-counters {
           }
           container ipv6-forwarding-class-counters {
           }
           container mpls-forwarding-class-counters {
           }
           container layer2-forwarding-class-counters {
           }
           container other-forwarding-class-counters {
           }
         }
         container forwarding-class-accounting-parameters {
           leaf forwarding-class-accounting-for-protocol {
             type string;
           }
           leaf forwarding-class-accounting-for-traffic-direction {
             type string;
           }
           leaf forwarding-class-accounting-for-traffic-type {
             type string;
           }
           leaf forwarding-class-accounting-overhead-bytes {
             type uint32;
           }
         }
         container per-forwarding-class-counters {
           leaf fc_name_header {
             type string;
           }
           leaf forwarding-class-name {
             type string;
             description
               "Forwarding class name associated with queue";
           }
           leaf fc-input-bytes {
             type int32;
           }
           leaf fc-input-bytes-rate {
             type int32;
             description
               "Input bytes rate";
           }
           leaf fc-output-bytes {
             type int32;
           }
           leaf fc-output-bytes-rate {
             type int32;
             description
               "Output bytes rate";
           }
           leaf fc-input-packets {
             type int32;
           }
           leaf fc-input-packets-rate {
             type int32;
             description
               "Input packets rate";
           }
           leaf fc-output-packets {
             type int32;
           }
           leaf fc-output-packets-rate {
             type int32;
             description
               "Output packets rate";
           }
           leaf input-unicast-bytes {
             type int32;
           }
           leaf output-unicast-bytes {
             type int32;
           }
           leaf input-unicast-packets {
             type int32;
           }
           leaf output-unicast-packets {
             type int32;
           }
           leaf input-multicast-bytes {
             type int32;
           }
           leaf output-multicast-bytes {
             type int32;
           }
           leaf input-multicast-packets {
             type int32;
           }
           leaf output-multicast-packets {
             type int32;
           }
         }
       }
       container keepalive-statistics {
         description
           "Keepalive statistics for this interface";
         leaf keepalive-lmi-descriptor {
           type string;
         }
         leaf keepalive-input-count {
           type int32;
         }
         leaf keepalive-input-time {
           type string;
         }
         leaf keepalive-output-count {
           type int32;
         }
         leaf keepalive-output-time {
           type string;
         }
       }
       container optics-bit-rate {
         leaf bit-rate {
           type string;
           description
             " Optics Bit Rate";
         }
       }
       container optics-fec-statistics {
         leaf fec-corrected-errors {
           type int32;
         }
         leaf fec-valid-time {
           type int32;
         }
         leaf fec-corrected-error-ratio {
           type int32;
         }
         leaf fec-uncorrected-words {
           type int32;
         }
       }
       container optic-fec-mode {
         leaf fec-mode {
           type string;
           description
             "Optics FEC mode";
         }
       }
       container optic-fec-statistics {
         leaf fec-corrected-errors {
           type int32;
         }
         leaf fec-uncorrected-words {
           type int32;
         }
         leaf fec-corrected-error-rate {
           type int32;
         }
         leaf fec-uncorrected-error-rate {
           type int32;
         }
         leaf optic-fec-uncorrected-error-ratio {
           type string;
         }
         leaf fec-valid-time {
           type int32;
         }
         leaf optic-fec-corrected-error-ratio {
           type string;
         }
       }
       container ngpe-ep-vxlan-info {
         leaf ngpe-ep-vtep-address-family {
           type uint32;
           description
             "NGPE EP VxLAN Endpoint IP Address Familiy";
         }
       }
       container traffic-statistics {
         leaf input-bps {
           type int32;
         }
         leaf input-pps {
           type int32;
         }
         leaf output-bps {
           type int32;
         }
         leaf output-pps {
           type int32;
         }
         leaf input-packets {
           type uint64;
         }
         leaf output-packets {
           type uint64;
         }
         container ipv4-traffic-statistics {
           leaf input-bps {
             type int32;
           }
           leaf output-bps {
             type int32;
           }
           leaf input-pps {
             type int32;
           }
           leaf output-pps {
             type int32;
           }
           leaf input-bytes {
             type int32;
           }
           leaf output-bytes {
             type int32;
           }
           leaf input-packets {
             type uint64;
           }
           leaf output-packets {
             type uint64;
           }
         }
         leaf input-bytes {
           type int32;
         }
         leaf output-bytes {
           type int32;
         }
         container ipv6-transit-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-traffic-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-total-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
       }
       container multicast-statistics {
         description
           "Multicast statistics for interface";
         leaf multicast-statistics-header {
           type empty;
         }
         container ipv4-multicast-statistics {
           description
             "IPV4 multicast statistics for interface";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-multicast-statistics {
           description
             "IPV6 multicast statistics for interface";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
       }
       container ingress-traffic-statistics {
         description
           "Traffic statistics at ingress before entering Packet Forwarding 
           Engine";
         leaf input-bps {
           type int32;
         }
         leaf input-pps {
           type int32;
         }
         leaf input-drop-bps {
           type int32;
           description
             "Drop rate at ingress in bits per second ";
         }
         leaf input-drop-pps {
           type int32;
           description
             "Drop rate at ingress in packets per second ";
         }
         leaf input-bytes {
           type int32;
         }
         leaf input-packets {
           type uint64;
         }
         leaf input-drop-bytes {
           type int32;
           description
             "Drop statistics at ingress in bytes";
         }
         leaf input-drop-packets {
           type int32;
           description
             "Drop statistics at ingress in packets";
         }
       }
       container active-alarms {
       }
       container active-defects {
       }
       container media-state-information {
       }
       container sonet-errors {
         list media-alarm {
           leaf media-alarm-name {
             type string;
           }
           leaf media-alarm-count {
             type int32;
           }
         }
       }
       container sonet-physical-information {
         list media-alarm {
           leaf media-alarm-name {
             type string;
           }
           leaf media-alarm-seconds {
             type int32;
           }
           leaf media-alarm-count {
             type int32;
           }
           leaf media-alarm-state {
             type string;
           }
         }
       }
       container sonet-section-information {
         list media-alarm {
           leaf media-alarm-name {
             type string;
           }
           leaf media-alarm-seconds {
             type int32;
           }
           leaf media-alarm-count {
             type int32;
           }
           leaf media-alarm-state {
             type string;
           }
         }
       }
       container sonet-line-information {
         list media-alarm {
           leaf media-alarm-name {
             type string;
           }
           leaf media-alarm-seconds {
             type int32;
           }
           leaf media-alarm-count {
             type int32;
           }
           leaf media-alarm-state {
             type string;
           }
         }
       }
       container sonet-path-information {
         list media-alarm {
           leaf media-alarm-name {
             type string;
           }
           leaf media-alarm-seconds {
             type int32;
           }
           leaf media-alarm-count {
             type int32;
           }
           leaf media-alarm-state {
             type string;
           }
         }
       }
       container sonet-vt-information {
         list media-alarm {
           leaf media-alarm-name {
             type string;
           }
           leaf media-alarm-seconds {
             type int32;
           }
           leaf media-alarm-count {
             type int32;
           }
           leaf media-alarm-state {
             type string;
           }
         }
       }
       container otn-errors {
         list media-alarm {
           leaf media-alarm-name {
             type string;
           }
           leaf media-alarm-count {
             type int32;
           }
         }
       }
       container otn-fec-statistics {
         leaf fec-corrected-errors {
           type int32;
         }
         leaf fec-valid-time {
           type int32;
         }
         leaf fec-corrected-error-ratio {
           type int32;
         }
         leaf fec-uncorrected-words {
           type int32;
         }
       }
       container otn-fec-alarms {
         description
           "OTN degraded and excessive FEC error rates";
         list media-alarm {
           leaf media-alarm-name {
             type string;
           }
           leaf media-alarm-seconds {
             type int32;
           }
           leaf media-alarm-count {
             type int32;
           }
           leaf media-alarm-state {
             type string;
           }
         }
       }
       container otn-fec-mode {
         leaf fec-mode {
           type string;
           description
             "Optics FEC mode";
         }
       }
       container otn-otn-mode {
         leaf otn-mode {
           type string;
         }
       }
       container otn-otn-rate {
         leaf otn-rate {
           type string;
         }
       }
       container otn-otn-loopback {
         leaf otn-loopback {
           type string;
         }
       }
       container otn-local-loopback {
         leaf local-loopback {
           type string;
         }
       }
       container otn-payload-prbs {
         leaf payload-prbs {
           type string;
         }
       }
       container otn-laser-enable {
         leaf laser-enable {
           type string;
           description
             "Optics laser status";
         }
       }
       container media-information {
         description
           "Information about media alarms";
         leaf media-type {
           type string;
           description
             "Type of media this information is for";
         }
         list media-alarm {
           leaf media-alarm-name {
             type string;
           }
           leaf media-alarm-count {
             type int32;
           }
           leaf media-alarm-seconds {
             type int32;
           }
           leaf media-alarm-state {
             type string;
           }
           leaf ce-counter-name {
             type string;
             description
               "Circuit Emulation counter information";
           }
           leaf ce-counter-packets {
             type int32;
             description
               "Circuit Emulation number of packets";
           }
           leaf ce-counter-bytes {
             type int32;
             description
               "Circuit Emulation number of bytes";
           }
           leaf ce-counter-count {
             type int32;
             description
               "Circuit Emulation number of event occurrences";
           }
         }
         leaf ds1-timeslots {
           type string;
         }
         leaf ds1-line-encoding {
           type string;
         }
         leaf ds1-byte-encoding {
           type string;
         }
         leaf ds1-data-inversion {
           type string;
         }
         leaf idle-cycle-flag {
           type string;
         }
         leaf start-end-flag {
           type string;
         }
         leaf ds0-byte-encoding {
           type string;
         }
         leaf ds0-data-inversion {
           type string;
         }
         leaf e3-data-inversion {
           type string;
         }
         leaf ds1-buildout {
           type string;
           description
             "Number of feet";
         }
       }
       container ethernet-pcs-statistics {
         description
           "Ethernet PCS statistics";
         leaf bit-error-seconds {
           type int32;
           description
             "Bit error duration";
         }
         leaf errored-blocks-seconds {
           type int32;
           description
             "Errored blocks duration";
         }
       }
       container ethernet-fec-mode {
         description
           "Ethernet FEC Mode";
         leaf enabled_fec_mode {
           type string;
           description
             "Enabled FEC mode: <NONE/FEC74/FEC91/FEC108/FEC161>";
         }
         leaf fec_codeword_size {
           type uint32;
           description
             "FEC Codeword size";
         }
         leaf fec_codeword_rate {
           type jt:unsigned-float;
           description
             "FEC Codeword rate";
         }
       }
       container ethernet-fec-statistics {
         description
           "Ethernet FEC statistics";
         leaf fec_ccw_count {
           type int32;
           description
             "FEC Corrected Error Count";
         }
         leaf fec_nccw_count {
           type int32;
           description
             "FEC Uncorrected Error Count";
         }
         leaf fec_ccw_error_rate {
           type int32;
           description
             "FEC Corrected Error Rate (errors/sec)";
         }
         leaf fec_nccw_error_rate {
           type int32;
           description
             "FEC Uncorrected Error Rate (errors/sec)";
         }
         leaf pre-fec-ber {
           type jt:unsigned-float;
           description
             "PRE_FEC BER";
         }
       }
       container ethernet-fechistogram-statistics {
         description
           "Ethernet Fec Histogram stats";
         leaf bin-num {
           type int32;
           description
             "Bin number";
         }
         leaf sym-live-err {
           type int32;
           description
             "Sym Live Err";
         }
         leaf sym-harvest-err {
           type int32;
           description
             "Sym harvested Err";
         }
         leaf sym-harvest-last-update {
           type string;
           description
             "Sym harvested last update";
         }
       }
       container ctle {
         description
           "Ctle ";
         leaf ctle_value {
           type int32;
           description
             "Ctle value";
         }
       }
       container pre-emphasis {
         description
           "Pre-emphasis ";
         leaf pre_emphasis_value {
           type int32;
           description
             "Pre-emphasis value";
         }
       }
       container differential-amplitude {
         description
           "Differential-amplitude ";
         leaf differential_amplitude_value {
           type int32;
           description
             "Differential-amplitude value";
         }
       }
       container ethernet-mac-statistics {
         description
           "Ethernet MAC statistics";
         leaf input-bytes {
           type int32;
         }
         leaf input-packets {
           type uint64;
         }
         leaf output-bytes {
           type int32;
         }
         leaf output-packets {
           type uint64;
         }
         leaf input-undersized-frames {
           type int32;
         }
         leaf input-unicasts {
           type int32;
         }
         leaf output-unicasts {
           type int32;
         }
         leaf input-broadcasts {
           type int32;
         }
         leaf output-broadcasts {
           type int32;
         }
         leaf input-multicasts {
           type int32;
         }
         leaf output-multicasts {
           type int32;
         }
         leaf input-crc-errors {
           type int32;
         }
         leaf output-crc-errors {
           type int32;
         }
         leaf input-fifo-errors {
           type int32;
         }
         leaf output-fifo-errors {
           type int32;
         }
         leaf input-dma-errors {
           type int32;
         }
         leaf output-dma-errors {
           type int32;
         }
         leaf input-mac-control-frames {
           type int32;
         }
         leaf output-mac-control-frames {
           type int32;
         }
         leaf input-mac-pause-frames {
           type int32;
         }
         leaf output-mac-pause-frames {
           type int32;
         }
         leaf input-oversized-frames {
           type int32;
         }
         leaf input-jabber-frames {
           type int32;
         }
         leaf input-fragment-frames {
           type int32;
         }
         leaf input-vlan-tagged-frames {
           type int32;
         }
         leaf input-code-violations {
           type int32;
         }
         leaf input-total-errors {
           type int32;
         }
         leaf output-total-errors {
           type int32;
         }
         leaf input-policer-frame-drops {
           type int32;
         }
         leaf input-policer-byte-drops {
           type int32;
         }
       }
       container ethernet-prbs-mode {
         description
           "PRBS Mode";
         leaf prbs-mode {
           type string;
           description
             "PRBS Mode: <Enabled/Disabled>";
         }
       }
       container ethernet-prbs-pattern {
         description
           "PRBS Pattern";
         leaf prbs-pattern {
           type int32;
           description
             "PRBS Pattern";
         }
       }
       container ethernet-prbs-statistics {
         description
           "Ethernet PRBS statistics";
         leaf prbs-lane {
           type int32;
           description
             "PRBS Lane";
         }
         leaf prbs-error-count {
           type int32;
           description
             "PRBS Error Count";
         }
         leaf prbs-loop-count {
           type int32;
           description
             "PRBS Loop Count";
         }
         leaf prbs-ber-sec {
           type int32;
           description
             "PRBS BER seconds";
         }
         leaf prbs-bits {
           type int32;
           description
             "PRBS Bits";
         }
         leaf prbs-run-sec {
           type int32;
           description
             "PRBS Run seconds";
         }
         leaf prbs-state {
           type string;
           description
             "PRBS State";
         }
         leaf prbs-ber-rate {
           type string;
           description
             "PRBS BER rate";
         }
       }
       container smart-sfp-configurable-type {
         leaf smart-sfp-tdm-management {
           type string;
         }
         leaf smart-sfp-mac {
           type jt:mac-addr;
         }
       }
       container smart-sfp-type {
         leaf smart-sfp-module-type {
           type string;
         }
         leaf smart-sfp-present {
           type string;
         }
       }
       container smart-sfp-config {
         leaf tdm-loopback {
           type string;
         }
         leaf dmac-check-enable {
           type string;
         }
         leaf encap-ecid {
           type int32;
         }
         leaf decap-ecid {
           type int32;
         }
         leaf vlan-id-1 {
           type int32;
         }
         leaf vlan-id-2 {
           type int32;
         }
         leaf mode {
           type string;
         }
         leaf chan-dmac {
           type jt:mac-addr;
         }
         leaf ces-psn-port-channel-id-state {
           type string;
         }
         leaf tdm-intf-signal {
           type string;
         }
       }
       list smart-sfp-channel-config {
         key "channel-num";
         description
           "Smart SFP channel config";
         leaf channel-num {
           type uint32;
           description
             "Channel number";
         }
         leaf channel-klm {
           type string;
           description
             "K (TUG3), L (TUG2), M (TU-12/VC-12/E1) Mapping";
         }
         leaf encap-ecid {
           type int32;
         }
         leaf encap-rtp-freq {
           type string;
         }
         leaf decap-ecid {
           type int32;
         }
         leaf decap-timing {
           type string;
         }
         leaf decap-rtp-freq {
           type string;
         }
         leaf ces-psn-mode {
           type string;
         }
         leaf ces-psn-dmac {
           type jt:mac-addr;
         }
         leaf ces-psn-vlan-1 {
           type int32;
         }
         leaf ces-psn-vlan-2 {
           type int32;
         }
         leaf encap-rtphdr-insert {
           type string;
         }
         leaf decap-rtphdr {
           type string;
         }
       }
       container smart-sfp-oc3-statistics {
         leaf fcs-error-count {
           type uint32;
         }
         leaf sec-sefs {
           type uint32;
         }
         leaf sec-es {
           type uint32;
         }
         leaf sec-es-min15 {
           type uint32;
         }
         leaf sec-ses {
           type uint32;
         }
         leaf sec-ses-min15 {
           type uint32;
         }
         leaf sec-cv {
           type uint32;
         }
         leaf sec-cv-min15 {
           type uint32;
         }
         leaf line-es {
           type uint32;
         }
         leaf line-es-min15 {
           type uint32;
         }
         leaf line-ses {
           type uint32;
         }
         leaf line-ses-min15 {
           type uint32;
         }
         leaf line-cv {
           type uint32;
         }
         leaf line-cv-min15 {
           type uint32;
         }
         leaf line-uas {
           type uint32;
         }
         leaf line-uas-min15 {
           type uint32;
         }
         leaf path-es {
           type uint32;
         }
         leaf path-es-min15 {
           type uint32;
         }
         leaf path-ses {
           type uint32;
         }
         leaf path-ses-min15 {
           type uint32;
         }
         leaf path-cv {
           type uint32;
         }
         leaf path-cv-min15 {
           type uint32;
         }
         leaf path-uas {
           type uint32;
         }
         leaf path-uas-min15 {
           type uint32;
         }
       }
       container smart-sfp-e1t1-statistics {
         leaf e1t1-es {
           type uint32;
         }
         leaf e1t1-es-min15 {
           type uint32;
         }
         leaf e1t1-ses {
           type uint32;
         }
         leaf e1t1-ses-min15 {
           type uint32;
         }
         leaf e1t1-uas {
           type uint32;
         }
         leaf e1t1-uas-min15 {
           type uint32;
         }
         leaf e1t1-bes {
           type uint32;
         }
         leaf e1t1-bes-min15 {
           type uint32;
         }
         leaf e1t1-les {
           type uint32;
         }
         leaf e1t1-les-min15 {
           type uint32;
         }
         leaf e1t1-pes {
           type uint32;
         }
         leaf e1t1-pes-min15 {
           type uint32;
         }
         leaf e1t1-psess {
           type uint32;
         }
         leaf e1t1-psess-min15 {
           type uint32;
         }
         leaf e1t1-ces {
           type uint32;
         }
         leaf e1t1-ces-min15 {
           type uint32;
         }
         leaf e1t1-cses {
           type uint32;
         }
         leaf e1t1-cses-min15 {
           type uint32;
         }
         leaf e1t1-sefs {
           type uint32;
         }
         leaf e1t1-sefs-min15 {
           type uint32;
         }
       }
       container smart-sfp-e3t3-statistics {
         leaf e3t3-les {
           type uint32;
         }
         leaf e3t3-les-min15 {
           type uint32;
         }
         leaf e3t3-pes {
           type uint32;
         }
         leaf e3t3-pes-min15 {
           type uint32;
         }
         leaf e3t3-psess {
           type uint32;
         }
         leaf e3t3-psess-min15 {
           type uint32;
         }
         leaf e3t3-ces {
           type uint32;
         }
         leaf e3t3-ces-min15 {
           type uint32;
         }
         leaf e3t3-cses {
           type uint32;
         }
         leaf e3t3-cses-min15 {
           type uint32;
         }
         leaf e3t3-sefs {
           type uint32;
         }
         leaf e3t3-sefs-min15 {
           type uint32;
         }
         leaf e3t3-uas {
           type uint32;
         }
         leaf e3t3-uas-min15 {
           type uint32;
         }
       }
       container fibrechannel-port-flow-control {
         description
           "Fibre Channel interface flow control";
         leaf fibrechannel-port-flow-control-mode {
           type string;
         }
         list fibrechannel-port-flow-control-credits {
           description
             "Generic flow control credits";
           leaf fibrechannel-port-flow-control-credits-subject {
             type string;
           }
           leaf fibrechannel-port-flow-control-credits-assigned {
             type uint64;
           }
           leaf fibrechannel-port-flow-control-credits-available {
             type uint64;
           }
         }
       }
       container fibrechannel-mac-statistics {
         description
           "Fibre Channel MAC statistics";
         container fibrechannel-mac-statistics-generic {
           leaf link-failures {
             type uint64;
           }
           leaf loss-of-sync {
             type uint64;
           }
           leaf loss-of-signal {
             type uint64;
           }
           leaf sw-link-resets {
             type uint64;
           }
           leaf buffer-to-buffer-credit-recovery-lost-frames {
             type uint64;
           }
           leaf buffer-to-buffer-credit-recovery-lost-rrdys {
             type uint64;
           }
         }
         container fibrechannel-mac-statistics-received {
           leaf rx-class-2-frames {
             type uint64;
           }
           leaf rx-class-2-octets {
             type uint64;
           }
           leaf rx-class-3-frames {
             type uint64;
           }
           leaf rx-class-3-octets {
             type uint64;
           }
           leaf rx-class-f-frames {
             type uint64;
           }
           leaf rx-class-f-octets {
             type uint64;
           }
           leaf class-2-discards {
             type uint64;
           }
           leaf class-3-discards {
             type uint64;
           }
           leaf class-f-discards {
             type uint64;
           }
           leaf rx-frames-too-long {
             type uint64;
           }
           leaf rx-frames-too-short {
             type uint64;
           }
           leaf rx-missing-eof {
             type uint64;
           }
           leaf rx-invalid-crcs {
             type uint64;
           }
           leaf rx-link-resets {
             type uint64;
           }
           leaf rx-link-reset-responses {
             type uint64;
           }
           leaf rx-offlines {
             type uint64;
           }
           leaf rx-not-operationals {
             type uint64;
           }
           leaf rx-invalid-tx-words {
             type uint64;
           }
           leaf rx-encoding-disparity-errors {
             type uint64;
           }
           leaf rx-delimiter-errors {
             type uint64;
           }
           leaf rx-input-buffers-full {
             type uint64;
           }
           leaf rx-invalid-ordered-sets {
             type uint64;
           }
           leaf rx-prim-seq-protocol-errors {
             type uint64;
           }
           leaf rx-other-errors {
             type uint64;
           }
         }
         container fibrechannel-mac-statistics-transmitted {
           leaf tx-class-2-frames {
             type uint64;
           }
           leaf tx-class-2-octets {
             type uint64;
           }
           leaf tx-class-3-frames {
             type uint64;
           }
           leaf tx-class-3-octets {
             type uint64;
           }
           leaf tx-class-f-frames {
             type uint64;
           }
           leaf tx-class-f-octets {
             type uint64;
           }
           leaf tx-link-resets {
             type uint64;
           }
           leaf tx-link-reset-responses {
             type uint64;
           }
           leaf tx-offlines {
             type uint64;
           }
           leaf tx-not-operationals {
             type uint64;
           }
           leaf tx-bb-credit-zeroes {
             type uint64;
           }
           leaf tx-other-errors {
             type uint64;
           }
         }
       }
       container ethernet-filter-statistics {
         description
           "Ethernet filter statistics";
         leaf input-reject-count {
           type int32;
         }
         leaf output-packet-pad-count {
           type int32;
         }
         leaf output-packet-error-count {
           type int32;
         }
         leaf input-packets {
           type uint64;
         }
         leaf input-reject-destination-address-count {
           type int32;
         }
         leaf input-reject-source-address-count {
           type int32;
         }
         leaf output-packets {
           type uint64;
         }
         leaf cam-destination-filter-count {
           type int32;
         }
         leaf cam-source-filter-count {
           type int32;
         }
       }
       container ethernet-autonegotiation {
         description
           "Ethernet autonegotiation information";
       }
       container mac-database {
       }
       container dsl-information {
         description
           "Operational information and statistics for ADSL interfaces";
         container dsl-statistics {
           leaf interleaved-rx-cells {
             type int32;
             description
               "Interleaved receiver cells";
           }
           leaf fast-rx-cells {
             type int32;
             description
               "Fast receiver cells";
           }
           leaf interleaved-tx-cells {
             type int32;
             description
               "Interleaved transmitter cells";
           }
           leaf fast-tx-cells {
             type int32;
             description
               "Fast transmitter cells";
           }
         }
       }
       container vdsl-information {
         description
           "Operational information and statistics for VDSL interfaces";
       }
       container dsl-sfp-information {
         description
           "Operational information and statistics for DSL SFP interfaces";
       }
       container shdsl-information {
         description
           "Operational information and statistics for SHDSL interfaces";
       }
       container efm-information {
         description
           "Operational information and statistics for EFM interfaces";
         container efm-line-statistics {
           container active-alarms-efm {
           }
           container active-defects-efm {
           }
           container media-information {
             description
               "Information about media alarms";
             leaf media-type {
               type string;
               description
                 "Type of media this information is for";
             }
             list media-alarm {
               leaf media-alarm-name {
                 type string;
               }
               leaf media-alarm-count {
                 type int32;
               }
               leaf media-alarm-seconds {
                 type int32;
               }
               leaf media-alarm-state {
                 type string;
               }
               leaf ce-counter-name {
                 type string;
                 description
                   "Circuit Emulation counter information";
               }
               leaf ce-counter-packets {
                 type int32;
                 description
                   "Circuit Emulation number of packets";
               }
               leaf ce-counter-bytes {
                 type int32;
                 description
                   "Circuit Emulation number of bytes";
               }
               leaf ce-counter-count {
                 type int32;
                 description
                   "Circuit Emulation number of event occurrences";
               }
             }
             leaf ds1-timeslots {
               type string;
             }
             leaf ds1-line-encoding {
               type string;
             }
             leaf ds1-byte-encoding {
               type string;
             }
             leaf ds1-data-inversion {
               type string;
             }
             leaf idle-cycle-flag {
               type string;
             }
             leaf start-end-flag {
               type string;
             }
             leaf ds0-byte-encoding {
               type string;
             }
             leaf ds0-data-inversion {
               type string;
             }
             leaf e3-data-inversion {
               type string;
             }
             leaf ds1-buildout {
               type string;
               description
                 "Number of feet";
             }
           }
           container shdsl-information {
             description
               "Operational information and statistics for SHDSL interfaces";
           }
         }
       }
       container atm-information {
         description
           "Operational information and statistics for ATM interfaces";
         container plcp-defects {
         }
         container atm-defects {
         }
       }
       container serial-information {
         description
           "Serial interfaces information and statistics";
         leaf dce-loopback-override {
           type string;
         }
         container eia530-control-signal {
         }
       }
       container virtual-path-information {
         description
           "Operational information and statistics for a virtual path";
         leaf cdvt {
           type int32;
         }
         container traffic-statistics {
           leaf input-bps {
             type int32;
           }
           leaf input-pps {
             type int32;
           }
           leaf output-bps {
             type int32;
           }
           leaf output-pps {
             type int32;
           }
           leaf input-packets {
             type uint64;
           }
           leaf output-packets {
             type uint64;
           }
           container ipv4-traffic-statistics {
             leaf input-bps {
               type int32;
             }
             leaf output-bps {
               type int32;
             }
             leaf input-pps {
               type int32;
             }
             leaf output-pps {
               type int32;
             }
             leaf input-bytes {
               type int32;
             }
             leaf output-bytes {
               type int32;
             }
             leaf input-packets {
               type uint64;
             }
             leaf output-packets {
               type uint64;
             }
           }
           leaf input-bytes {
             type int32;
           }
           leaf output-bytes {
             type int32;
           }
           container ipv6-transit-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-traffic-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-total-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
         }
       }
       container ct3-information {
         list interface-tx-queue {
           leaf output-drops-bytes {
             type int32;
           }
         }
       }
       container cds1-information {
         list interface-tx-queue {
           leaf output-drops-bytes {
             type int32;
           }
         }
       }
       container nxds0-information {
         list interface-tx-queue {
           leaf output-drops-bytes {
             type int32;
           }
         }
       }
       list logical-interface {
         key "name";
         description
           "Information about a single logical interface";
         leaf name {
           type string;
           description
             "Name of this item";
         }
         leaf admin-status {
           type string;
           description
             "Desired state of the interface";
         }
         leaf oper-status {
           type string;
           description
             "Current operational state of the interface";
         }
         leaf logical-interface-zone-name {
           type string;
           description
             "Zone name for this interface";
         }
         leaf subunit {
           type int32;
           description
             "Subunit for this interface";
         }
         leaf dialer-time-to-disconnect {
           type string;
           description
             "Time for dialer to disconnect due to idle timeout";
         }
         leaf lcp-state {
           type string;
           description
             "State of the Line Control Protocol";
         }
         leaf chap-state {
           type string;
           description
             "State of the Challenge Handshake Authentication Protocol";
         }
         leaf pap-state {
           type string;
           description
             "State of the Password Authentication Protocol";
         }
         container pppoe-information {
           description
             "PPPoE information";
           list pppoe-interface {
             leaf state {
               type string;
               description
                 "State";
             }
             leaf session-id {
               type string;
               description
                 "Session ID";
             }
             leaf ac-name-session {
               type string;
               description
                 "Session AC name";
             }
             leaf remote-mac {
               type string;
               description
                 "Remote MAC address";
             }
             leaf ac-name-config {
               type string;
               description
                 "Configured AC name";
             }
             leaf service-name {
               type string;
               description
                 "Service name";
             }
             leaf auto-reconnect {
               type string;
               description
                 "Autoreconnect timeout";
             }
             leaf idle-timeout {
               type string;
               description
                 "Idle timeout";
             }
             leaf underlying-interface-name {
               type string;
               description
                 "Underlying interface name";
             }
             leaf underlying-interface-index {
               type string;
               description
                 "Underlying interface index";
             }
             leaf padg-credits {
               type int32;
               description
                 "PADG transmit credits";
             }
             leaf pppoe-credit-scale-factor {
               type string;
               description
                 "Scaling factor";
             }
             leaf ignore-eol-tag {
               type string;
               description
                 "Ignore End-of-List TAG";
             }
             leaf ppp-max-payload-tag {
               type int32;
               description
                 "PPP-Max-Payload TAG";
             }
             leaf interface-name {
               type string;
               description
                 "Interface name";
             }
             leaf interface-index {
               type string;
               description
                 "Index";
             }
             leaf aci-iflset-name {
               type string;
               description
                 "ACI Interface Set name";
             }
             leaf aci-iflset-index {
               type string;
               description
                 "ACI Interface Set index";
             }
             leaf ifl-type {
               type string;
               description
                 "Type";
             }
             leaf session-uptime {
               type string;
               description
                 "Duration for which the session has been up";
             }
             leaf dynamic-profile {
               type string;
               description
                 "Dynamic Profile name";
             }
             leaf pppoe-credits {
               type string;
               description
                 "Forwarding credit balances";
             }
             leaf dynamic-interface-bandwidth {
               type string;
               description
                 "Dynamic interface bandwidth";
             }
             leaf agent-circuit-id {
               type string;
               description
                 "Agent Circuit ID";
             }
             leaf agent-remote-id {
               type string;
               description
                 "Agent Remote ID";
             }
             leaf padm-motm {
               type string;
               description
                 "PADM Message of the Moment tag";
             }
             leaf padm-hurl {
               type string;
               description
                 "PADM HTTP URL tag";
             }
             leaf pppoe-relay-session-id {
               type string;
               description
                 "PPPoE Relay Session ID";
             }
           }
         }
         container pppoe-underlying-information {
           description
             "PPPoE Underlying information";
           list pppoe-underlying-interface {
             leaf dynamic-profile {
               type string;
               description
                 "Dynamic Profile name";
             }
             leaf service-name-table {
               type string;
               description
                 "Name of Service Name Table";
             }
             leaf max-sessions {
               type int32;
               description
                 "Maximum number of PPPoE sessions";
             }
             leaf max-sessions-vsa-ignore {
               type string;
               description
                 "Ignore max-sessions VSA";
             }
             leaf duplicate-protection {
               type string;
               description
                 "Duplicate protection mode";
             }
             leaf short-cycle-protection {
               type string;
               description
                 "Short cycle protection mode";
             }
             leaf direct-connect {
               type string;
               description
                 "Direct connect mode";
             }
             leaf ac-name {
               type string;
               description
                 "Access Concentrator name";
             }
             leaf underlying-interface-name {
               type string;
               description
                 "Underlying interface name";
             }
             leaf underlying-interface-index {
               type string;
               description
                 "Underlying interface index";
             }
             leaf encapsulation-type-identifier {
               type string;
               description
                 "Encapsulation type identifier";
             }
             leaf state {
               type string;
               description
                 "State";
             }
             leaf active-sessions {
               type int32;
               description
                 "Number of active PPPoE sessions";
             }
             leaf aci-autosensing {
               type string;
               description
                 "ACI VLAN Autosensing mode";
             }
             leaf line-identity-autosensing {
               type string;
               description
                 "Line Identity Autosensing mode";
             }
           }
         }
         container aci-vlan-information {
           leaf dynamic-profile {
             type string;
             description
               "Dynamic Profile name";
           }
         }
         container line-identity-information {
           leaf dynamic-profile {
             type string;
             description
               "Dynamic Profile name";
           }
           leaf circuit-id {
             type string;
             description
               "Aci vlan attribute";
           }
           leaf remote-id {
             type string;
             description
               "Aci vlan attribute";
           }
           leaf accept-no-ids {
             type string;
             description
               "Aci vlan attribute";
           }
         }
         container demux-information {
           description
             "Demux information";
           container demux-interface {
             leaf demux-underlying-interface-name {
               type string;
               description
                 "Underlying interface name";
             }
             leaf demux-underlying-interface-index {
               type string;
               description
                 "Underlying interface index";
             }
             leaf demux-inet-prefix-type {
               type string;
               description
                 "Prefix type";
             }
             leaf demux-inet-prefix-count {
               type string;
               description
                 "IPv4 Prefix count";
             }
             leaf demux-inet-prefix {
               type string;
               description
                 "IPv4 Prefix";
             }
             leaf demux-inet6-prefix-type {
               type string;
               description
                 "Prefix type";
             }
             leaf demux-inet6-prefix-count {
               type string;
               description
                 "IPv6 Prefix count";
             }
             leaf demux-inet6-prefix {
               type string;
               description
                 "IPv6 Prefix";
             }
           }
         }
         container dual-ad-icl-color-information {
           container dual-ad-icl-color-info {
             description
               "Dual-AD ICL Color Information";
             leaf dual-ad-icl-color-type {
               type uint32;
               description
                 "Dual-AD ICL Color Type";
             }
             leaf dual-ad-icl-color {
               type uint32;
               description
                 "Dual-AD ICL Color";
             }
           }
         }
         container dialer-information {
           description
             "Dialer information";
           leaf dialer-time-to-disconnect {
             type string;
             description
               "Time for dialer to disconnect due to idle timeout";
           }
           container dialer-interface {
             container dialer-interface-flags {
               description
                 "Flags indicating interface configuration";
               leaf backup {
                 type empty;
                 description
                   "Dialer backup";
               }
               leaf multilink {
                 type empty;
                 description
                   "Dialer multilink";
               }
               leaf watchlist {
                 type empty;
                 description
                   "Dialer watchlist";
               }
               leaf interesting-detected {
                 type empty;
                 description
                   "Interesting packet detected";
               }
             }
             list dial-string-list {
               leaf dial-string {
                 type string;
                 description
                   "Dial string";
               }
             }
             list sub-interface-list {
               leaf sub-interface-name {
                 type string;
                 description
                   "Subordinate interface name";
               }
             }
             list watch-list {
               leaf watch-route {
                 type string;
                 description
                   "Watch route";
               }
             }
             leaf dialer-interface-name {
               type string;
               description
                 "Interface name";
             }
             leaf dialer-interface-state {
               type string;
               description
                 "Dialer interface state";
             }
             leaf pool-id {
               type string;
               description
                 "Pool identifier";
             }
             leaf primary-interface {
               type string;
               description
                 "Primary interface";
             }
             leaf activation-delay {
               type string;
               description
                 "Activation delay";
             }
             leaf deactivation-delay {
               type string;
               description
                 "Deactivation delay";
             }
             leaf activation-delay-elapsed {
               type string;
               description
                 "Activation delay elapsed";
             }
             leaf deactivation-delay-elapsed {
               type string;
               description
                 "Deactivation delay elapsed";
             }
             leaf call-idle-timeout {
               type string;
               description
                 "Call idle timeout";
             }
             leaf initial-route-check {
               type string;
               description
                 "Initial route check delay";
             }
             leaf redial-delay {
               type string;
               description
                 "Delay before dialer dials out again (seconds)";
             }
             leaf callback-wait-period {
               type string;
               description
                 "Delay before dialer attempts callback (seconds)";
             }
             leaf callback-wait-period-elapsed {
               type string;
               description
                 "Number of seconds in callback wait period that have 
                 elapsed";
             }
             leaf load-threshold {
               type string;
               description
                 "Load threshold that determines when interfaces are added 
                 to bundle";
             }
             leaf load-interval {
               type string;
               description
                 "Interval over which average load is calculated";
             }
           }
         }
         container shared-interface-information {
           description
             "Shared interface information";
           container shared-interface-logical-interface {
             description
               "Shared interface logical interface";
             leaf peer-interface-name {
               type string;
               description
                 "Peer interface name";
             }
             leaf interface-shared-with {
               type string;
               description
                 "Logical interface owner";
             }
             leaf rx-fe {
               type string;
               description
                 "Rx tunnel token forwarding element";
             }
             leaf rx-nhid {
               type string;
               description
                 "Rx tunnel token next hop index";
             }
             leaf tx-fe {
               type string;
               description
                 "Tx tunnel token forwarding element";
             }
             leaf tx-nhid {
               type string;
               description
                 "Tx tunnel token next hop index";
             }
           }
         }
         container mac-database {
         }
         container queue-counters {
           description
             "Queue counter statistics";
           leaf queue-counters-error-message {
             type string;
             description
               "Queue statistics not available for this interface";
           }
           container interface-cos-short-summary {
             description
               "Summary of queue information on an interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           list queue {
             key "queue-number";
             description
               "Counters for a single queue";
             leaf queue-number {
               type uint32;
               description
                 "Queue number";
             }
             leaf queue-counters-queued-packets {
               type int32;
               description
                 "Queued packet count";
             }
             leaf queue-counters-trans-packets {
               type int32;
               description
                 "Total number of transmitted packets";
             }
             leaf queue-counters-total-drop-packets {
               type int32;
               description
                 "Number of total packets dropped at the queue";
             }
             leaf forwarding-class-name {
               type string;
               description
                 "Forwarding class name associated with queue";
             }
             leaf queue-counters-queued-packets-rate {
               type int32;
               description
                 "Rate at which packets are queued";
             }
             leaf queue-counters-queued-bytes {
               type int32;
               description
                 "Queued bytes count";
             }
             leaf queue-counters-queued-bytes-rate {
               type int32;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets-rate {
               type int32;
               description
                 "Rate at which packets are transmitted";
             }
             leaf queue-counters-trans-bytes {
               type int32;
               description
                 "Total number of transmitted bytes";
             }
             leaf queue-counters-trans-bytes-rate {
               type int32;
               description
                 "Rate at which bytes are transmitted";
             }
             leaf queue-counters-tail-drop-packets-na {
               type string;
               description
                 "Number of packets dropped due to tail drop not available";
             }
             leaf queue-counters-tail-drop-packets {
               type int32;
               description
                 "Number of packets dropped at the tail of the queue";
             }
             leaf queue-counters-tail-drop-packets-rate {
               type int32;
               description
                 "Rate at which packets are dropped at tail of queue";
             }
             leaf queue-counters-tail-drop-bytes {
               type int32;
               description
                 "Number of packets dropped at tail drop of the queue";
             }
             leaf queue-counters-tail-drop-bytes-rate {
               type int32;
               description
                 "Number of packets dropped at tail drop of the queue";
             }
             leaf queue-counters-ecn-ce-packets {
               type int32;
               description
                 "Total number of ECN CE packets";
             }
             leaf queue-counters-ecn-ce-packets-rate {
               type int32;
               description
                 "Rate at which ECN CE packets are transmitted";
             }
             leaf queue-counters-ecn-ce-bytes {
               type int32;
               description
                 "Total number of ECN CE bytes";
             }
             leaf queue-counters-ecn-ce-bytes-rate {
               type int32;
               description
                 "Rate at which ECN CE bytes are transmitted";
             }
             leaf queue-counters-rate-limit-drop-packets-na {
               type string;
               description
                 "Number of packets dropped due to rate-limit drop not 
                 available";
             }
             leaf queue-counters-rate-limit-drop-packets {
               type int32;
               description
                 "Number of packets dropped by rate-limit for the queue";
             }
             leaf queue-counters-rate-limit-drop-packets-rate {
               type int32;
               description
                 "Rate at which packets are dropped by rate-limit for the 
                 queue";
             }
             leaf queue-counters-rate-limit-drop-bytes-na {
               type string;
               description
                 "Number of bytes dropped due to tail drop not available";
             }
             leaf queue-counters-rate-limit-drop-bytes {
               type int32;
               description
                 "Number of bytes dropped at the tail of the queue";
             }
             leaf queue-counters-rate-limit-drop-bytes-rate {
               type int32;
               description
                 "Rate at which bytes are dropped at the tail of the queue";
             }
             leaf queue-counters-red-packets-na {
               type string;
               description
                 "Number of packets dropped due to RED not available";
             }
             leaf queue-counters-red-packets {
               type int32;
               description
                 "Number of packets dropped due to RED";
             }
             leaf queue-counters-red-packets-rate {
               type int32;
               description
                 "Rate at which packets are dropped due to RED";
             }
             leaf queue-counters-red-packets-ln {
               type int32;
               description
                 "Number of RED dropped low-loss, non-TCP packets";
             }
             leaf queue-counters-red-packets-rate-ln {
               type int32;
               description
                 "RED drop rate for low-loss, non-TCP packets";
             }
             leaf queue-counters-red-packets-lt {
               type int32;
               description
                 "Number of RED dropped of low-loss, TCP packets";
             }
             leaf queue-counters-red-packets-rate-lt {
               type int32;
               description
                 "RED drop rate for low-loss, TCP packets";
             }
             leaf queue-counters-red-packets-hn {
               type int32;
               description
                 "Number of RED dropped high-loss, non-TCP packets";
             }
             leaf queue-counters-red-packets-rate-hn {
               type int32;
               description
                 "RED drop rate for high-loss, non-TCP packets";
             }
             leaf queue-counters-red-packets-ht {
               type int32;
               description
                 "Number of RED dropped high-loss, TCP packets";
             }
             leaf queue-counters-red-packets-rate-ht {
               type int32;
               description
                 "RED drop rate for high-loss, TCP packets";
             }
             leaf queue-counters-red-packets-low {
               type int32;
               description
                 "Number of RED dropped low-loss packets";
             }
             leaf queue-counters-red-packets-rate-low {
               type int32;
               description
                 "RED drop rate for low-loss packets";
             }
             leaf queue-counters-red-packets-medium-low {
               type int32;
               description
                 "Number of RED dropped medium-low-loss packets";
             }
             leaf queue-counters-red-packets-rate-medium-low {
               type int32;
               description
                 "RED drop rate for medium-low-loss packets";
             }
             leaf queue-counters-red-packets-medium-high {
               type int32;
               description
                 "Number of RED dropped medium-high-loss packets";
             }
             leaf queue-counters-red-packets-rate-medium-high {
               type int32;
               description
                 "RED drop rate for medium-high-loss packets";
             }
             leaf queue-counters-red-packets-medium {
               type int32;
               description
                 "Number of RED dropped medium-loss packets";
             }
             leaf queue-counters-red-packets-rate-medium {
               type int32;
               description
                 "RED drop rate for medium-loss packets";
             }
             leaf queue-counters-red-packets-high {
               type int32;
               description
                 "Number of RED dropped high-loss packets";
             }
             leaf queue-counters-red-packets-rate-high {
               type int32;
               description
                 "RED drop rate for high-loss packets";
             }
             leaf queue-counters-red-bytes-na {
               type string;
               description
                 "Number of bytes dropped due to RED not available";
             }
             leaf queue-counters-red-bytes {
               type int32;
               description
                 "Number of bytes dropped due to RED";
             }
             leaf queue-counters-red-bytes-rate {
               type int32;
               description
                 "Rate at which bytes are dropped due to RED";
             }
             leaf queue-counters-red-bytes-ln {
               type int32;
               description
                 "Number of RED dropped low-loss, non-TCP bytes";
             }
             leaf queue-counters-red-bytes-rate-ln {
               type int32;
               description
                 "RED drop rate for low-loss, non-TCP bytes";
             }
             leaf queue-counters-red-bytes-lt {
               type int32;
               description
                 "Number of RED dropped low-loss, TCP bytes";
             }
             leaf queue-counters-red-bytes-rate-lt {
               type int32;
               description
                 "RED drop rate for low-loss, TCP bytes";
             }
             leaf queue-counters-red-bytes-hn {
               type int32;
               description
                 "Number of RED dropped high-loss, non-TCP bytes";
             }
             leaf queue-counters-red-bytes-rate-hn {
               type int32;
               description
                 "RED drop rate for high-loss, non-TCP bytes";
             }
             leaf queue-counters-red-bytes-ht {
               type int32;
               description
                 "Number of RED dropped high-loss, TCP bytes";
             }
             leaf queue-counters-red-bytes-rate-ht {
               type int32;
               description
                 "RED drop rate for high-loss, TCP bytes";
             }
             leaf queue-counters-red-bytes-low {
               type int32;
               description
                 "Number of RED dropped low-loss bytes";
             }
             leaf queue-counters-red-bytes-rate-low {
               type int32;
               description
                 "RED drop rate for low-loss bytes";
             }
             leaf queue-counters-red-bytes-medium-low {
               type int32;
               description
                 "Number of RED dropped medium-low-loss bytes";
             }
             leaf queue-counters-red-bytes-rate-medium-low {
               type int32;
               description
                 "RED drop rate for medium-low-loss bytes";
             }
             leaf queue-counters-red-bytes-medium-high {
               type int32;
               description
                 "Number of RED dropped medium-high-loss bytes";
             }
             leaf queue-counters-red-bytes-rate-medium-high {
               type int32;
               description
                 "RED drop rate for medium-high-loss bytes";
             }
             leaf queue-counters-red-bytes-medium {
               type int32;
               description
                 "Number of RED dropped medium-loss bytes";
             }
             leaf queue-counters-red-bytes-rate-medium {
               type int32;
               description
                 "RED drop rate for medium-loss bytes";
             }
             leaf queue-counters-red-bytes-high {
               type int32;
               description
                 "Number of RED dropped high-loss bytes";
             }
             leaf queue-counters-red-bytes-rate-high {
               type int32;
               description
                 "RED drop rate for high-loss bytes";
             }
             leaf queue-counters-timestamp {
               type int32;
               description
                 "Last packet enqueued timestamp";
             }
             leaf queue-counters-total-drop-packets-rate {
               type int32;
               description
                 "Number of total packets dropped at the queue";
             }
             leaf queue-counters-total-drop-bytes {
               type int32;
               description
                 "Number of total packets dropped at the queue";
             }
             leaf queue-counters-total-drop-bytes-rate {
               type int32;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
         }
         container voq-counters {
           description
             "VOQ counter statistics";
           leaf voq-counters-error-message {
             type string;
             description
               "VOQ statistics not available for this interface";
           }
           container voq {
             description
               "Counters for a single voq";
             container fpc {
               description
                 "Counters for a single FPC";
               leaf fpc-no {
                 type int32;
                 description
                   "FPC number";
               }
               container pfe {
                 description
                   "Counters for a single PFE";
                 leaf-list pfe-no {
                   type int32;
                   description
                     "PFE number";
                 }
                 leaf voq-counters-tail-drop-packets {
                   type int32;
                   description
                     "Tail DROP packet count";
                 }
                 leaf voq-counters-tail-drop-packets-rate {
                   type int32;
                   description
                     "Rate at which tail packets are dropped";
                 }
                 leaf voq-counters-tail-drop-bytes {
                   type int32;
                   description
                     "Tail DROP bytes count";
                 }
                 leaf voq-counters-tail-drop-bytes-rate {
                   type int32;
                   description
                     "Rate at which tail bytes are dropped";
                 }
                 leaf voq-counters-drop-packets {
                   type int32;
                   description
                     "DROP packet count";
                 }
                 leaf voq-counters-drop-packets-rate {
                   type int32;
                   description
                     "Rate at which packets are dropped";
                 }
                 leaf voq-counters-drop-bytes {
                   type int32;
                   description
                     "DROP bytes count";
                 }
                 leaf voq-counters-drop-bytes-rate {
                   type int32;
                   description
                     "Rate at which bytes are dropped";
                 }
                 leaf voq-counters-queued-packets {
                   type int32;
                   description
                     "QUEUED packets count";
                 }
                 leaf voq-counters-queued-packets-rate {
                   type int32;
                   description
                     "Rate at which packets are queued";
                 }
                 leaf voq-counters-queued-bytes {
                   type int32;
                   description
                     "QUEUED bytes count";
                 }
                 leaf voq-counters-queued-bytes-rate {
                   type int32;
                   description
                     "Rate at which bytes are queued";
                 }
                 leaf voq-counters-transmitted-packets {
                   type int32;
                   description
                     "Transmitted packets count";
                 }
                 leaf voq-counters-transmitted-packets-rate {
                   type int32;
                   description
                     "Rate at which packets are transmitted";
                 }
                 leaf voq-counters-transmitted-bytes {
                   type int32;
                   description
                     "Transmitted bytes count";
                 }
                 leaf voq-counters-transmitted-bytes-rate {
                   type int32;
                   description
                     "Rate at which bytes are transmitted";
                 }
                 leaf voq-counters-queue-depth-bytes-current {
                   type int32;
                   description
                     "Current queue length";
                 }
                 leaf voq-counters-queue-depth-bytes-peak {
                   type int32;
                   description
                     "Peak queue length";
                 }
                 leaf voq-counters-queue-depth-bytes-average {
                   type int32;
                   description
                     "Average queue length";
                 }
               }
             }
             leaf queue-number {
               type uint32;
               description
                 "Queue number";
             }
             leaf forwarding-class-name {
               type string;
               description
                 "Forwarding class name associated with queue";
             }
             leaf restricted-forwarding-class-name {
               type string;
             }
           }
         }
         container ingress-queue-counters {
           description
             "Ingress queue counter statistics";
           list queue {
             key "queue-number";
             description
               "Counters for a single queue";
             leaf queue-number {
               type uint32;
               description
                 "Queue number";
             }
             leaf forwarding-class-name {
               type string;
               description
                 "Forwarding class name associated with queue";
             }
             leaf queue-counters-queued-packets {
               type int32;
               description
                 "Queued packet count";
             }
             leaf queue-counters-queued-packets-rate {
               type int32;
               description
                 "Rate at which packets are queued";
             }
             leaf queue-counters-queued-bytes {
               type int32;
               description
                 "Queued bytes count";
             }
             leaf queue-counters-queued-bytes-rate {
               type int32;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets {
               type int32;
               description
                 "Total number of transmitted packets";
             }
             leaf queue-counters-trans-packets-rate {
               type int32;
               description
                 "Rate at which packets are transmitted";
             }
             leaf queue-counters-trans-bytes {
               type int32;
               description
                 "Total number of transmitted bytes";
             }
             leaf queue-counters-trans-bytes-rate {
               type int32;
               description
                 "Rate at which bytes are transmitted";
             }
             leaf queue-counters-tail-drop-packets-na {
               type string;
               description
                 "Number of packets dropped due to tail drop not available";
             }
             leaf queue-counters-tail-drop-packets {
               type int32;
               description
                 "Number of packets dropped at the tail of the queue";
             }
             leaf queue-counters-tail-drop-packets-rate {
               type int32;
               description
                 "Rate at which packets are dropped at tail of queue";
             }
             leaf queue-counters-tail-drop-bytes {
               type int32;
               description
                 "Number of packets dropped at tail drop of the queue";
             }
             leaf queue-counters-tail-drop-bytes-rate {
               type int32;
               description
                 "Number of packets dropped at tail drop of the queue";
             }
             leaf queue-counters-ecn-ce-packets {
               type int32;
               description
                 "Total number of ECN CE packets";
             }
             leaf queue-counters-ecn-ce-packets-rate {
               type int32;
               description
                 "Rate at which ECN CE packets are transmitted";
             }
             leaf queue-counters-ecn-ce-bytes {
               type int32;
               description
                 "Total number of ECN CE bytes";
             }
             leaf queue-counters-ecn-ce-bytes-rate {
               type int32;
               description
                 "Rate at which ECN CE bytes are transmitted";
             }
             leaf queue-counters-rate-limit-drop-packets-na {
               type string;
               description
                 "Number of packets dropped due to rate-limit drop not 
                 available";
             }
             leaf queue-counters-rate-limit-drop-packets {
               type int32;
               description
                 "Number of packets dropped by rate-limit for the queue";
             }
             leaf queue-counters-rate-limit-drop-packets-rate {
               type int32;
               description
                 "Rate at which packets are dropped by rate-limit for the 
                 queue";
             }
             leaf queue-counters-rate-limit-drop-bytes-na {
               type string;
               description
                 "Number of bytes dropped due to tail drop not available";
             }
             leaf queue-counters-rate-limit-drop-bytes {
               type int32;
               description
                 "Number of bytes dropped at the tail of the queue";
             }
             leaf queue-counters-rate-limit-drop-bytes-rate {
               type int32;
               description
                 "Rate at which bytes are dropped at the tail of the queue";
             }
             leaf queue-counters-red-packets-na {
               type string;
               description
                 "Number of packets dropped due to RED not available";
             }
             leaf queue-counters-red-packets {
               type int32;
               description
                 "Number of packets dropped due to RED";
             }
             leaf queue-counters-red-packets-rate {
               type int32;
               description
                 "Rate at which packets are dropped due to RED";
             }
             leaf queue-counters-red-packets-ln {
               type int32;
               description
                 "Number of RED dropped low-loss, non-TCP packets";
             }
             leaf queue-counters-red-packets-rate-ln {
               type int32;
               description
                 "RED drop rate for low-loss, non-TCP packets";
             }
             leaf queue-counters-red-packets-lt {
               type int32;
               description
                 "Number of RED dropped of low-loss, TCP packets";
             }
             leaf queue-counters-red-packets-rate-lt {
               type int32;
               description
                 "RED drop rate for low-loss, TCP packets";
             }
             leaf queue-counters-red-packets-hn {
               type int32;
               description
                 "Number of RED dropped high-loss, non-TCP packets";
             }
             leaf queue-counters-red-packets-rate-hn {
               type int32;
               description
                 "RED drop rate for high-loss, non-TCP packets";
             }
             leaf queue-counters-red-packets-ht {
               type int32;
               description
                 "Number of RED dropped high-loss, TCP packets";
             }
             leaf queue-counters-red-packets-rate-ht {
               type int32;
               description
                 "RED drop rate for high-loss, TCP packets";
             }
             leaf queue-counters-red-packets-low {
               type int32;
               description
                 "Number of RED dropped low-loss packets";
             }
             leaf queue-counters-red-packets-rate-low {
               type int32;
               description
                 "RED drop rate for low-loss packets";
             }
             leaf queue-counters-red-packets-medium-low {
               type int32;
               description
                 "Number of RED dropped medium-low-loss packets";
             }
             leaf queue-counters-red-packets-rate-medium-low {
               type int32;
               description
                 "RED drop rate for medium-low-loss packets";
             }
             leaf queue-counters-red-packets-medium-high {
               type int32;
               description
                 "Number of RED dropped medium-high-loss packets";
             }
             leaf queue-counters-red-packets-rate-medium-high {
               type int32;
               description
                 "RED drop rate for medium-high-loss packets";
             }
             leaf queue-counters-red-packets-medium {
               type int32;
               description
                 "Number of RED dropped medium-loss packets";
             }
             leaf queue-counters-red-packets-rate-medium {
               type int32;
               description
                 "RED drop rate for medium-loss packets";
             }
             leaf queue-counters-red-packets-high {
               type int32;
               description
                 "Number of RED dropped high-loss packets";
             }
             leaf queue-counters-red-packets-rate-high {
               type int32;
               description
                 "RED drop rate for high-loss packets";
             }
             leaf queue-counters-red-bytes-na {
               type string;
               description
                 "Number of bytes dropped due to RED not available";
             }
             leaf queue-counters-red-bytes {
               type int32;
               description
                 "Number of bytes dropped due to RED";
             }
             leaf queue-counters-red-bytes-rate {
               type int32;
               description
                 "Rate at which bytes are dropped due to RED";
             }
             leaf queue-counters-red-bytes-ln {
               type int32;
               description
                 "Number of RED dropped low-loss, non-TCP bytes";
             }
             leaf queue-counters-red-bytes-rate-ln {
               type int32;
               description
                 "RED drop rate for low-loss, non-TCP bytes";
             }
             leaf queue-counters-red-bytes-lt {
               type int32;
               description
                 "Number of RED dropped low-loss, TCP bytes";
             }
             leaf queue-counters-red-bytes-rate-lt {
               type int32;
               description
                 "RED drop rate for low-loss, TCP bytes";
             }
             leaf queue-counters-red-bytes-hn {
               type int32;
               description
                 "Number of RED dropped high-loss, non-TCP bytes";
             }
             leaf queue-counters-red-bytes-rate-hn {
               type int32;
               description
                 "RED drop rate for high-loss, non-TCP bytes";
             }
             leaf queue-counters-red-bytes-ht {
               type int32;
               description
                 "Number of RED dropped high-loss, TCP bytes";
             }
             leaf queue-counters-red-bytes-rate-ht {
               type int32;
               description
                 "RED drop rate for high-loss, TCP bytes";
             }
             leaf queue-counters-red-bytes-low {
               type int32;
               description
                 "Number of RED dropped low-loss bytes";
             }
             leaf queue-counters-red-bytes-rate-low {
               type int32;
               description
                 "RED drop rate for low-loss bytes";
             }
             leaf queue-counters-red-bytes-medium-low {
               type int32;
               description
                 "Number of RED dropped medium-low-loss bytes";
             }
             leaf queue-counters-red-bytes-rate-medium-low {
               type int32;
               description
                 "RED drop rate for medium-low-loss bytes";
             }
             leaf queue-counters-red-bytes-medium-high {
               type int32;
               description
                 "Number of RED dropped medium-high-loss bytes";
             }
             leaf queue-counters-red-bytes-rate-medium-high {
               type int32;
               description
                 "RED drop rate for medium-high-loss bytes";
             }
             leaf queue-counters-red-bytes-medium {
               type int32;
               description
                 "Number of RED dropped medium-loss bytes";
             }
             leaf queue-counters-red-bytes-rate-medium {
               type int32;
               description
                 "RED drop rate for medium-loss bytes";
             }
             leaf queue-counters-red-bytes-high {
               type int32;
               description
                 "Number of RED dropped high-loss bytes";
             }
             leaf queue-counters-red-bytes-rate-high {
               type int32;
               description
                 "RED drop rate for high-loss bytes";
             }
             leaf queue-counters-timestamp {
               type int32;
               description
                 "Last packet enqueued timestamp";
             }
             leaf queue-counters-total-drop-packets {
               type int32;
               description
                 "Number of total packets dropped at the queue";
             }
             leaf queue-counters-total-drop-packets-rate {
               type int32;
               description
                 "Number of total packets dropped at the queue";
             }
             leaf queue-counters-total-drop-bytes {
               type int32;
               description
                 "Number of total packets dropped at the queue";
             }
             leaf queue-counters-total-drop-bytes-rate {
               type int32;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
           container interface-cos-short-summary {
             description
               "Summary of queue information on an interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           list queue-num-forwarding-class-name-map {
             key "queue-number";
             leaf queue-number {
               type uint32;
               description
                 "Queue number";
             }
             leaf forwarding-class-name {
               type string;
               description
                 "Forwarding class name associated with queue";
             }
           }
         }
         container forwarding-class-counters {
           description
             "Forwarding-class counter statistics";
           leaf forwarding-class-counters-error-message {
             type string;
             description
               "Forwarding-class statistics not available for this interface";
           }
           container ipv4-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container ipv6-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container mpls-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container layer2-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container other-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container protocol-aggregate-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container forwarding-class-statistics {
             container protocol-aggregate-forwarding-class-counters {
             }
             container ipv4-forwarding-class-counters {
             }
             container ipv6-forwarding-class-counters {
             }
             container mpls-forwarding-class-counters {
             }
             container layer2-forwarding-class-counters {
             }
             container other-forwarding-class-counters {
             }
           }
           container forwarding-class-accounting-parameters {
             leaf forwarding-class-accounting-for-protocol {
               type string;
             }
             leaf forwarding-class-accounting-for-traffic-direction {
               type string;
             }
             leaf forwarding-class-accounting-for-traffic-type {
               type string;
             }
             leaf forwarding-class-accounting-overhead-bytes {
               type uint32;
             }
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container multilink-bundle-options {
           leaf filler-packet-interval {
             type int32;
           }
         }
         container multilink-traffic-statistics {
           container bundle {
           }
           container class {
             description
               "Multilink class traffic statistics";
           }
           container multilink-detail-statistics {
             container bundle-detail {
             }
             container class-detail {
             }
           }
           container crtp {
             container crtp-sessions {
               leaf input-frames {
                 type int32;
               }
               leaf output-frames {
                 type int32;
               }
             }
             list crtp-statistics {
               key "name";
               leaf name {
                 type string;
                 description
                   "Name of this item";
               }
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
           }
         }
         container traffic-statistics {
           leaf input-bps {
             type int32;
           }
           leaf input-pps {
             type int32;
           }
           leaf output-bps {
             type int32;
           }
           leaf output-pps {
             type int32;
           }
           leaf input-packets {
             type uint64;
           }
           leaf output-packets {
             type uint64;
           }
           container ipv4-traffic-statistics {
             leaf input-bps {
               type int32;
             }
             leaf output-bps {
               type int32;
             }
             leaf input-pps {
               type int32;
             }
             leaf output-pps {
               type int32;
             }
             leaf input-bytes {
               type int32;
             }
             leaf output-bytes {
               type int32;
             }
             leaf input-packets {
               type uint64;
             }
             leaf output-packets {
               type uint64;
             }
           }
           leaf input-bytes {
             type int32;
           }
           leaf output-bytes {
             type int32;
           }
           container ipv6-transit-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-traffic-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-total-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
         }
         container multicast-statistics {
           description
             "Multicast statistics for interface";
           leaf multicast-statistics-header {
             type empty;
           }
           container ipv4-multicast-statistics {
             description
               "IPV4 multicast statistics for interface";
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-multicast-statistics {
             description
               "IPV6 multicast statistics for interface";
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
         }
         container ingress-traffic-statistics {
           description
             "Traffic statistics at ingress before entering Packet 
             Forwarding Engine";
           leaf input-bps {
             type int32;
           }
           leaf input-pps {
             type int32;
           }
           leaf input-drop-bps {
             type int32;
             description
               "Drop rate at ingress in bits per second ";
           }
           leaf input-drop-pps {
             type int32;
             description
               "Drop rate at ingress in packets per second ";
           }
           leaf input-bytes {
             type int32;
           }
           leaf input-packets {
             type uint64;
           }
           leaf input-drop-bytes {
             type int32;
             description
               "Drop statistics at ingress in bytes";
           }
           leaf input-drop-packets {
             type int32;
             description
               "Drop statistics at ingress in packets";
           }
         }
         container local-traffic-statistics {
           description
             "Statistics for locally originated traffic";
         }
         container transit-traffic-statistics {
           description
             "Statistics for traffic passing through the Packet Forwarding 
             Engine";
         }
         container layer3-statistics {
         }
         container keepalive-statistics {
           description
             "Keepalive statistics for this interface";
           leaf keepalive-lmi-descriptor {
             type string;
           }
           leaf keepalive-input-count {
             type int32;
           }
           leaf keepalive-input-time {
             type string;
           }
           leaf keepalive-output-count {
             type int32;
           }
           leaf keepalive-output-time {
             type string;
           }
         }
         container virtual-circuit-information {
           description
             "Operational information and statistics for a virtual circuit";
           container traffic-statistics {
             leaf input-bps {
               type int32;
             }
             leaf input-pps {
               type int32;
             }
             leaf output-bps {
               type int32;
             }
             leaf output-pps {
               type int32;
             }
             leaf input-packets {
               type uint64;
             }
             leaf output-packets {
               type uint64;
             }
             container ipv4-traffic-statistics {
               leaf input-bps {
                 type int32;
               }
               leaf output-bps {
                 type int32;
               }
               leaf input-pps {
                 type int32;
               }
               leaf output-pps {
                 type int32;
               }
               leaf input-bytes {
                 type int32;
               }
               leaf output-bytes {
                 type int32;
               }
               leaf input-packets {
                 type uint64;
               }
               leaf output-packets {
                 type uint64;
               }
             }
             leaf input-bytes {
               type int32;
             }
             leaf output-bytes {
               type int32;
             }
             container ipv6-transit-statistics {
               leaf input-bytes {
                 type int32;
               }
               leaf input-bps {
                 type int32;
               }
               leaf output-bytes {
                 type int32;
               }
               leaf output-bps {
                 type int32;
               }
               leaf input-packets {
                 type uint64;
               }
               leaf input-pps {
                 type int32;
               }
               leaf output-packets {
                 type uint64;
               }
               leaf output-pps {
                 type int32;
               }
             }
             container ipv6-traffic-statistics {
               leaf input-bytes {
                 type int32;
               }
               leaf input-bps {
                 type int32;
               }
               leaf output-bytes {
                 type int32;
               }
               leaf output-bps {
                 type int32;
               }
               leaf input-packets {
                 type uint64;
               }
               leaf input-pps {
                 type int32;
               }
               leaf output-packets {
                 type uint64;
               }
               leaf output-pps {
                 type int32;
               }
             }
             container ipv6-total-statistics {
               leaf input-bytes {
                 type int32;
               }
               leaf input-bps {
                 type int32;
               }
               leaf output-bytes {
                 type int32;
               }
               leaf output-bps {
                 type int32;
               }
               leaf input-packets {
                 type uint64;
               }
               leaf input-pps {
                 type int32;
               }
               leaf output-packets {
                 type uint64;
               }
               leaf output-pps {
                 type int32;
               }
             }
           }
           container atm-cos-information {
             leaf vc-cos-mode {
               type string;
               description
                 "Virtual circuit CoS scheduling mode";
             }
             list atm-cos-queue {
               container atm-cos-queue-parameters {
                 leaf cos-forwarding-class-name {
                   type string;
                   description
                     "Forwarding class name associated with queue";
                 }
                 leaf cos-queue-number {
                   type int32;
                   description
                     "Queue number";
                 }
                 leaf scheduling-priority {
                   type string;
                   description
                     "Scheduling priority";
                 }
                 leaf transmit-weight-cells {
                   type int32;
                   description
                     "Weight to apply to scheduling as number of cells";
                 }
                 leaf transmit-weight-percent {
                   type int32;
                   description
                     "Weight to apply to scheduling as fill percentage";
                 }
                 leaf epd-threshold {
                   type int32;
                   description
                     "Early packet drop threshold";
                 }
                 leaf epd-threshold-plp0 {
                   type int32;
                   description
                     "Early packet drop threshold for PLP 0";
                 }
                 leaf epd-threshold-plp1 {
                   type int32;
                   description
                     "Early packet drop threshold for PLP 1";
                 }
                 container linear-red-drop-profile {
                   leaf queue-depth {
                     type int32;
                     description
                       "Maximum queue depth";
                   }
                   leaf low-red {
                     type int32;
                     description
                       "Fill level percentage when linear RED is applied for
                       low PLP";
                   }
                   leaf high-red {
                     type int32;
                     description
                       "Fill level percentage when linear RED is applied for
                       high PLP";
                   }
                   leaf max-low-red {
                     type int32;
                     description
                       "Fill level percentage with 100% packet drop for low 
                       PLP";
                   }
                   leaf max-high-red {
                     type int32;
                     description
                       "Fill level percentage with 100% packet drop for high
                       PLP";
                   }
                 }
               }
               container atm-cos-queue-statistics {
                 leaf atm-output-bytes {
                   type int32;
                 }
                 leaf atm-output-packets {
                   type int32;
                 }
                 leaf atm-packet-drops {
                   type int32;
                 }
               }
               container atm-cos-plp-statistics {
                 leaf atm-plp0-output-bytes {
                   type int32;
                 }
                 leaf atm-plp1-output-bytes {
                   type int32;
                 }
                 leaf atm-plp0-output-packets {
                   type int32;
                 }
                 leaf atm-plp1-output-packets {
                   type int32;
                 }
                 leaf atm-plp0-byte-drops {
                   type int32;
                 }
                 leaf atm-plp1-byte-drops {
                   type int32;
                 }
                 leaf atm-plp0-packet-drops {
                   type int32;
                 }
                 leaf atm-plp1-packet-drops {
                   type int32;
                 }
               }
             }
           }
         }
         list filter-information {
           leaf filter-family {
             type string;
             description
               "Protocol family of the filter";
           }
           leaf-list filter-input {
             type string;
             description
               "Name of the input filter";
           }
           leaf-list filter-output {
             type string;
             description
               "Name of the output filter";
           }
         }
         container allowed-host-inbound-traffic {
           description
             "List of allowed system services and protocols";
           leaf inbound-all-protocols {
             type empty;
             description
               "All protocols";
           }
           leaf inbound-any-service {
             type empty;
             description
               "Any service";
           }
           leaf inbound-bootp {
             type empty;
             description
               "Bootp and dhcp relay-agent service";
           }
           leaf inbound-bfd {
             type empty;
             description
               "Bidirectional Forwarding Detection";
           }
           leaf inbound-bgp {
             type empty;
             description
               "Border Gateway Protocol";
           }
           leaf inbound-dns {
             type empty;
             description
               "DNS and DNS-proxy service";
           }
           leaf inbound-dvmrp {
             type empty;
             description
               "Distance Vector Multicast Routing Protocol";
           }
           leaf inbound-igmp {
             type empty;
             description
               "Internet Group Management Protocol";
           }
           leaf inbound-ldp {
             type empty;
             description
               "Label Distribution Protocol";
           }
           leaf inbound-msdp {
             type empty;
             description
               "Multicast Source Discovery Protocol";
           }
           leaf inbound-nhrp {
             type empty;
             description
               "Next Hop Resolution Protocol";
           }
           leaf inbound-ospf {
             type empty;
             description
               "Open Shortest Path First";
           }
           leaf inbound-ospf3 {
             type empty;
             description
               "Open Shortest Path First version 3";
           }
           leaf inbound-pgm {
             type empty;
             description
               "Pragmatic General Multicast";
           }
           leaf inbound-pim {
             type empty;
             description
               "Protocol Independent Multicast";
           }
           leaf inbound-rip {
             type empty;
             description
               "Routing Information Protocol";
           }
           leaf inbound-ripng {
             type empty;
             description
               "Routing Information Protocol next generation";
           }
           leaf inbound-router-discovery {
             type empty;
             description
               "Router Discovery";
           }
           leaf inbound-rsvp {
             type empty;
             description
               "Resource Reservation Protocol";
           }
           leaf inbound-sap {
             type empty;
             description
               "Session Announcement Protocol";
           }
           leaf inbound-vrrp {
             type empty;
             description
               "Virtual Router Redundancy Protocol";
           }
           leaf inbound-all-services {
             type empty;
             description
               "All system services";
           }
           leaf inbound-dhcp {
             type empty;
             description
               "Dynamic Host Configuration Protocol";
           }
           leaf inbound-finger {
             type empty;
             description
               "Finger service";
           }
           leaf inbound-ftp {
             type empty;
             description
               "File Transfer Protocol";
           }
           leaf inbound-tftp {
             type empty;
             description
               "Trivial File Transfer Protocol";
           }
           leaf ident-reset {
             type empty;
             description
               "Send back TCP RST to IDENT request for port 113";
           }
           leaf inbound-http {
             type empty;
             description
               "Web management service using HTTP";
           }
           leaf inbound-https {
             type empty;
             description
               "Web management service using HTTP secured by SSL";
           }
           leaf inbound-ike {
             type empty;
             description
               "Internet Key Exchange";
           }
           leaf inbound-netconf {
             type empty;
             description
               "NETCONF service";
           }
           leaf inbound-ping {
             type empty;
             description
               "Internet Control Message Protocol echo requests";
           }
           leaf inbound-reverse-telnet {
             type empty;
             description
               "Reverse telnet service";
           }
           leaf inbound-reverse-ssh {
             type empty;
             description
               "Reverse SSH service";
           }
           leaf inbound-rlogin {
             type empty;
             description
               "Rlogin service";
           }
           leaf inbound-rpm {
             type empty;
             description
               "Real-time performance monitoring";
           }
           leaf inbound-rsh {
             type empty;
             description
               "Rsh service";
           }
           leaf inbound-snmp {
             type empty;
             description
               "Simple Network Management Protocol service";
           }
           leaf inbound-snmp-trap {
             type empty;
             description
               "Simple Network Management Protocol traps";
           }
           leaf inbound-ssh {
             type empty;
             description
               "SSH service";
           }
           leaf inbound-telnet {
             type empty;
             description
               "Telnet service";
           }
           leaf inbound-traceroute {
             type empty;
             description
               "Traceroute service";
           }
           leaf inbound-xnm-clear-text {
             type empty;
             description
               "JUNOScript API for unencrypted traffic over TCP";
           }
           leaf inbound-xnm-ssl {
             type empty;
             description
               "JUNOScript API service over SSL";
           }
           leaf inbound-lsping {
             type empty;
             description
               "Label Switched Path ping service";
           }
           leaf inbound-lsselfping {
             type empty;
             description
               "Label Switched Path self ping service";
           }
           leaf inbound-ntp {
             type empty;
             description
               "Network Time Protocol service";
           }
           leaf inbound-sip {
             type empty;
             description
               "Session Initiation Protocol service";
           }
           leaf inbound-dhcpv6 {
             type empty;
             description
               "Dynamic Host Configuration Protocol for IPv6 service";
           }
           leaf inbound-r2cp {
             type empty;
             description
               "Radio Router Control Protocol service";
           }
           leaf inbound-webapi-clear-text {
             type empty;
             description
               "Webapi service using http";
           }
           leaf inbound-webapi-ssl {
             type empty;
             description
               "Webapi service using HTTP secured by SSL";
           }
           leaf inbound-tcp-encap {
             type empty;
             description
               "Tcp encapsulation service";
           }
           leaf inbound-sdwan-appqoe {
             type empty;
             description
               "Sdwan Appqoe service";
           }
           leaf inbound-high-availability {
             type empty;
             description
               "High Availability  service";
           }
         }
         list address-family {
           container pppoe-underlying-information {
             description
               "PPPoE Underlying information";
             list pppoe-underlying-interface {
               leaf dynamic-profile {
                 type string;
                 description
                   "Dynamic Profile name";
               }
               leaf service-name-table {
                 type string;
                 description
                   "Name of Service Name Table";
               }
               leaf max-sessions {
                 type int32;
                 description
                   "Maximum number of PPPoE sessions";
               }
               leaf max-sessions-vsa-ignore {
                 type string;
                 description
                   "Ignore max-sessions VSA";
               }
               leaf duplicate-protection {
                 type string;
                 description
                   "Duplicate protection mode";
               }
               leaf short-cycle-protection {
                 type string;
                 description
                   "Short cycle protection mode";
               }
               leaf direct-connect {
                 type string;
                 description
                   "Direct connect mode";
               }
               leaf ac-name {
                 type string;
                 description
                   "Access Concentrator name";
               }
               leaf underlying-interface-name {
                 type string;
                 description
                   "Underlying interface name";
               }
               leaf underlying-interface-index {
                 type string;
                 description
                   "Underlying interface index";
               }
               leaf encapsulation-type-identifier {
                 type string;
                 description
                   "Encapsulation type identifier";
               }
               leaf state {
                 type string;
                 description
                   "State";
               }
               leaf active-sessions {
                 type int32;
                 description
                   "Number of active PPPoE sessions";
               }
               leaf aci-autosensing {
                 type string;
                 description
                   "ACI VLAN Autosensing mode";
               }
               leaf line-identity-autosensing {
                 type string;
                 description
                   "Line Identity Autosensing mode";
               }
             }
           }
           list interface-address {
           }
           container destination-class-statistics {
             description
               "Destination class usage (DCU) statistics";
           }
           container source-class-statistics {
             description
               "Source class usage (SCU) statistics";
           }
           list local-bias-information {
             leaf local-bias-vtep-ifl-name {
               type string;
               description
                 "Interface name";
             }
             leaf local-bias-vtep-ifl-index {
               type uint32;
               description
                 "Interface index";
             }
             leaf local-bias-vtep-address {
               type string;
               description
                 "Protocol address of the connection";
             }
           }
           leaf ft-iff-dest-port {
             type uint32;
             description
               "Destination UDP port to be used for this family";
           }
         }
         list bridge-iff-properties {
           description
             "Information about Ethernet-switching address family";
         }
         container l2circuit-info {
           leaf out-of-sequence {
             type int32;
           }
           leaf denied-packets {
             type int32;
           }
           leaf cell-bundle-size {
             type int32;
           }
           leaf cell-bundle-timeout {
             type int32;
           }
           leaf cell-timeout-count {
             type int32;
           }
         }
         container media-information {
           description
             "Information about media alarms";
           leaf media-type {
             type string;
             description
               "Type of media this information is for";
           }
           list media-alarm {
             leaf media-alarm-name {
               type string;
             }
             leaf media-alarm-count {
               type int32;
             }
             leaf media-alarm-seconds {
               type int32;
             }
             leaf media-alarm-state {
               type string;
             }
             leaf ce-counter-name {
               type string;
               description
                 "Circuit Emulation counter information";
             }
             leaf ce-counter-packets {
               type int32;
               description
                 "Circuit Emulation number of packets";
             }
             leaf ce-counter-bytes {
               type int32;
               description
                 "Circuit Emulation number of bytes";
             }
             leaf ce-counter-count {
               type int32;
               description
                 "Circuit Emulation number of event occurrences";
             }
           }
           leaf ds1-timeslots {
             type string;
           }
           leaf ds1-line-encoding {
             type string;
           }
           leaf ds1-byte-encoding {
             type string;
           }
           leaf ds1-data-inversion {
             type string;
           }
           leaf idle-cycle-flag {
             type string;
           }
           leaf start-end-flag {
             type string;
           }
           leaf ds0-byte-encoding {
             type string;
           }
           leaf ds0-data-inversion {
             type string;
           }
           leaf e3-data-inversion {
             type string;
           }
           leaf ds1-buildout {
             type string;
             description
               "Number of feet";
           }
         }
         container macsec-statistics {
           description
             "MACSec Statistics ";
           leaf macsec-tx-sc-protected {
             type int32;
             description
               "Protected Secure Channel MACSec packets transmitted";
           }
           leaf macsec-tx-sc-encrypted {
             type int32;
             description
               "Encrypted Secure Channel MACSec packets transmitted";
           }
           leaf macsec-tx-sc-protectedbytes {
             type int32;
             description
               "Protected Secure Channel MACSec bytes transmitted";
           }
           leaf macsec-tx-sc-encryptedbytes {
             type int32;
             description
               "Encrypted Secure Channel MACSec bytes transmitted";
           }
           leaf macsec-rx-sc-ok {
             type int32;
             description
               "OK Secure Association MACSec packets received";
           }
           leaf macsec-rx-sc-validatedbytes {
             type int32;
             description
               "Validated Secure Association MACSec bytes received";
           }
           leaf macsec-rx-sc-decryptedbytes {
             type int32;
             description
               "Validated Secure Association MACSec bytes received";
           }
           leaf interface-name {
             type string;
             description
               "Class-of-service interface name";
           }
           leaf encrypted-packets {
             type uint64;
             description
               "Macsec encrypted packets sent";
           }
           leaf encrypted-bytes {
             type uint64;
             description
               "Macsec encrypted bytes sent";
           }
           leaf protected-packets {
             type uint64;
             description
               "Macsec packets sent with only integrity protection";
           }
           leaf protected-bytes {
             type uint64;
             description
               "Macsec bytes sent with only integrity protection";
           }
           leaf ok-packets {
             type uint64;
             description
               "Macsec packets accepted";
           }
           leaf decrypted-bytes {
             type uint64;
             description
               "Macsec received bytes decrypted";
           }
           leaf decrypted-packets {
             type uint64;
             description
               "Macsec received packets decrypted";
           }
           leaf validated-packets {
             type uint64;
             description
               "Macsec received packets validated";
           }
           leaf validated-bytes {
             type uint64;
             description
               "Macsec received bytes validated";
           }
           leaf untagged-packets {
             type uint64;
             description
               "Macsec untagged packets";
           }
           leaf toolong-packets {
             type uint64;
             description
               "Macsec too long packets transmitted on a secure channel";
           }
           leaf control-packets {
             type uint64;
             description
               "Macsec control packets received on a secure channel";
           }
           leaf tagged-miss-packets {
             type uint64;
             description
               "Macsec tagged miss packets received on a secure channel";
           }
           leaf untagged-hit-packets {
             type uint64;
             description
               "Macsec untagged hit packets received on a secure channel";
           }
           leaf notag-packets {
             type uint64;
             description
               "Macsec no tag packets received on a secure channel";
           }
           leaf badtag-packets {
             type uint64;
             description
               "Macsec bad tag packets received on a secure channel";
           }
           leaf unknown-sci-packets {
             type uint64;
             description
               "Macsec unknown sci packets received on a secure channel";
           }
           leaf no-sci-packets {
             type uint64;
             description
               "Macsec no sci packets received on a secure channel";
           }
           leaf control-pass-packets {
             type uint64;
             description
               "Macsec allowed control packets received on a secure channel";
           }
           leaf uncontrol-pass-packets {
             type uint64;
             description
               "Macsec allowed uncontrol packets received on a secure 
               channel";
           }
           leaf control-fail-packets {
             type uint64;
             description
               "Macsec dropped control packets received on a secure channel";
           }
           leaf uncontrol-fail-packets {
             type uint64;
             description
               "Macsec dropped uncontrol packets received on a secure 
               channel";
           }
           leaf hit-dropped-packets {
             type uint64;
             description
               "Macsec hit dropped packets received on a security channel";
           }
           leaf notusing-sa-packets {
             type uint64;
             description
               "Macsec not using sa packets received on a security channel";
           }
           leaf unused-sa-packets {
             type uint64;
             description
               "Macsec unused sa packets received on a security channel";
           }
           leaf late-packets {
             type uint64;
             description
               "Macsec late packets dropped on a security channel";
           }
           leaf delayed-packets {
             type uint64;
             description
               "Macsec delayed packets accepted on a security channel";
           }
           leaf unchecked-packets {
             type uint64;
             description
               "Macsec unchecked packets accepted on a security channel";
           }
           leaf notvalid-packets {
             type uint64;
             description
               "Macsec not valid packets dropped on a security channel";
           }
           leaf invalid-packets {
             type uint64;
             description
               "Macsec invalid packets accepted on a security channel";
           }
           list secure-channel-sent {
             leaf encrypted-packets {
               type uint64;
               description
                 "Macsec encrypted packets sent";
             }
             leaf encrypted-bytes {
               type uint64;
               description
                 "Macsec encrypted bytes sent";
             }
             leaf protected-packets {
               type uint64;
               description
                 "Macsec packets sent with only integrity protection";
             }
             leaf protected-bytes {
               type uint64;
               description
                 "Macsec bytes sent with only integrity protection";
             }
           }
           list secure-association-sent {
             leaf encrypted-packets {
               type uint64;
               description
                 "Macsec encrypted packets sent";
             }
             leaf encrypted-bytes {
               type uint64;
               description
                 "Macsec encrypted bytes sent";
             }
             leaf protected-packets {
               type uint64;
               description
                 "Macsec packets sent with only integrity protection";
             }
             leaf protected-bytes {
               type uint64;
               description
                 "Macsec bytes sent with only integrity protection";
             }
           }
           list secure-channel-received {
             leaf ok-packets {
               type uint64;
               description
                 "Macsec packets accepted";
             }
             leaf decrypted-packets {
               type uint64;
               description
                 "Macsec received packets decrypted";
             }
             leaf decrypted-bytes {
               type uint64;
               description
                 "Macsec received bytes decrypted";
             }
             leaf validated-packets {
               type uint64;
               description
                 "Macsec received packets validated";
             }
             leaf validated-bytes {
               type uint64;
               description
                 "Macsec received bytes validated";
             }
           }
           list secure-association-received {
             leaf ok-packets {
               type uint64;
               description
                 "Macsec packets accepted";
             }
             leaf decrypted-packets {
               type uint64;
               description
                 "Macsec received packets decrypted";
             }
             leaf decrypted-bytes {
               type uint64;
               description
                 "Macsec received bytes decrypted";
             }
             leaf validated-packets {
               type uint64;
               description
                 "Macsec received packets validated";
             }
             leaf validated-bytes {
               type uint64;
               description
                 "Macsec received bytes validated";
             }
           }
           list macsec-error-information {
             list secure-channel-sent-errors {
               leaf untagged-packets {
                 type uint64;
                 description
                   "Macsec untagged packets";
               }
               leaf toolong-packets {
                 type uint64;
                 description
                   "Macsec too long packets transmitted on a secure channel";
               }
             }
             list secure-channel-received-errors {
               leaf control-packets {
                 type uint64;
                 description
                   "Macsec control packets received on a secure channel";
               }
               leaf tagged-miss-packets {
                 type uint64;
                 description
                   "Macsec tagged miss packets received on a secure channel";
               }
               leaf untagged-hit-packets {
                 type uint64;
                 description
                   "Macsec untagged hit packets received on a secure channel";
               }
               leaf untagged-packets {
                 type uint64;
                 description
                   "Macsec untagged packets";
               }
               leaf notag-packets {
                 type uint64;
                 description
                   "Macsec no tag packets received on a secure channel";
               }
               leaf badtag-packets {
                 type uint64;
                 description
                   "Macsec bad tag packets received on a secure channel";
               }
               leaf unknown-sci-packets {
                 type uint64;
                 description
                   "Macsec unknown sci packets received on a secure channel";
               }
               leaf no-sci-packets {
                 type uint64;
                 description
                   "Macsec no sci packets received on a secure channel";
               }
               leaf control-pass-packets {
                 type uint64;
                 description
                   "Macsec allowed control packets received on a secure 
                   channel";
               }
               leaf control-fail-packets {
                 type uint64;
                 description
                   "Macsec dropped control packets received on a secure 
                   channel";
               }
               leaf uncontrol-pass-packets {
                 type uint64;
                 description
                   "Macsec allowed uncontrol packets received on a secure 
                   channel";
               }
               leaf uncontrol-fail-packets {
                 type uint64;
                 description
                   "Macsec dropped uncontrol packets received on a secure 
                   channel";
               }
             }
             list secure-channel-received-extended {
               leaf hit-dropped-packets {
                 type uint64;
                 description
                   "Macsec hit dropped packets received on a security 
                   channel";
               }
               leaf invalid-packets {
                 type uint64;
                 description
                   "Macsec invalid packets accepted on a security channel";
               }
               leaf late-packets {
                 type uint64;
                 description
                   "Macsec late packets dropped on a security channel";
               }
               leaf delayed-packets {
                 type uint64;
                 description
                   "Macsec delayed packets accepted on a security channel";
               }
               leaf unchecked-packets {
                 type uint64;
                 description
                   "Macsec unchecked packets accepted on a security channel";
               }
               leaf notvalid-packets {
                 type uint64;
                 description
                   "Macsec not valid packets dropped on a security channel";
               }
               leaf notusing-sa-packets {
                 type uint64;
                 description
                   "Macsec not using sa packets received on a security 
                   channel";
               }
               leaf unused-sa-packets {
                 type uint64;
                 description
                   "Macsec unused sa packets received on a security channel";
               }
               leaf untagged-hit-packets {
                 type uint64;
                 description
                   "Macsec untagged hit packets received on a secure channel";
               }
             }
           }
         }
         container security-input-flow-statistics {
           description
             "Flow input statistics for the interface";
           leaf flow-input-self-packets {
             type int32;
             description
               "Input Self packets";
           }
           leaf flow-input-icmp-packets {
             type int32;
             description
               "Input ICMP packets";
           }
           leaf flow-input-vpn-packets {
             type int32;
             description
               "Input VPN packets";
           }
           leaf flow-input-multicast-packets {
             type int32;
             description
               "Input multicast packets";
           }
           leaf flow-input-policy-bytes {
             type int32;
             description
               "Input policy bytes";
           }
           leaf flow-input-connections {
             type int32;
             description
               "Input connections";
           }
         }
         container security-output-flow-statistics {
           description
             "Flow output statistics for the interface";
           leaf flow-output-multicast-packets {
             type int32;
             description
               "Output multicast packets";
           }
           leaf flow-output-policy-bytes {
             type int32;
             description
               "Output bytes permitted by policy";
           }
         }
         container security-error-flow-statistics {
           description
             "Flow error statistics for the interface";
           leaf flow-error-policy-denied {
             type int32;
             description
               "Policy denied";
           }
           leaf flow-error-no-gate-parent {
             type int32;
             description
               "No parent for gate";
           }
           leaf flow-error-syn-protection {
             type int32;
             description
               "Syn-attack protection";
           }
           leaf flow-error-incoming-nat {
             type int32;
             description
               "Incoming NAT errors";
           }
           leaf flow-error-no-tunnel {
             type int32;
             description
               "No tunnel found";
           }
           leaf flow-error-no-more-session {
             type int32;
             description
               "No more sessions";
           }
           leaf flow-error-invalid-zone {
             type int32;
             description
               "Invalid zone received packet";
           }
           leaf flow-error-user-authentication {
             type int32;
             description
               "User authentication errors";
           }
           leaf flow-error-multiple-auth {
             type int32;
             description
               "Multiple user authentications";
           }
           leaf flow-error-multiple-incoming-nat {
             type int32;
             description
               "Multiple incoming NAT";
           }
           leaf flow-error-address-spoofing {
             type int32;
             description
               "Address spoofing";
           }
           leaf flow-error-null-zone {
             type int32;
             description
               "No zone or NULL zone binding";
           }
           leaf flow-error-no-nat-gate {
             type int32;
             description
               "No NAT gate";
           }
           leaf flow-error-no-minor-session {
             type int32;
             description
               "No minor session";
           }
           leaf flow-error-no-session-gate {
             type int32;
             description
               "No session for a gate";
           }
           leaf flow-error-seq-outside-window {
             type int32;
             description
               "TCP sequence number out of window";
           }
           leaf flow-error-no-route-present {
             type int32;
             description
               "No route present";
           }
           leaf flow-error-authentication-failed {
             type int32;
             description
               "Authentication failed";
           }
           leaf flow-error-security-association-missing {
             type int32;
             description
               "Security association not active";
           }
           leaf flow-error-no-sa-for-spi {
             type int32;
             description
               "No SA for incoming SPI";
           }
           leaf flow-error-no-interest-self-packet {
             type int32;
             description
               "No one interested in self packets";
           }
         }
         container lag-traffic-statistics {
           container lag-multicast-statistics {
             leaf lag-multicast-statistics-header {
               type empty;
             }
             container lag-ipv4-multicast-statistics {
               leaf input-packets {
                 type uint64;
               }
               leaf input-pps {
                 type int32;
               }
               leaf input-bytes {
                 type int32;
               }
               leaf input-bps {
                 type int32;
               }
               leaf output-packets {
                 type uint64;
               }
               leaf output-pps {
                 type int32;
               }
               leaf output-bytes {
                 type int32;
               }
               leaf output-bps {
                 type int32;
               }
             }
             container lag-ipv6-multicast-statistics {
               leaf input-packets {
                 type uint64;
               }
               leaf input-pps {
                 type int32;
               }
               leaf input-bytes {
                 type int32;
               }
               leaf input-bps {
                 type int32;
               }
               leaf output-packets {
                 type uint64;
               }
               leaf output-pps {
                 type int32;
               }
               leaf output-bytes {
                 type int32;
               }
               leaf output-bps {
                 type int32;
               }
             }
           }
           list if-distribution-list-information {
           }
           container ifd-lag-traffic-statistics {
           }
         }
         container ifd-lag-traffic-statistics {
         }
         container layer2-input-policer-statistics {
           description
             "Layer 2 input policer statistics for interface";
           leaf policer-medium-low-frames {
             type int32;
             description
               "Number of loss priority medium low frames";
           }
           leaf policer-medium-low-bytes {
             type int32;
             description
               "Number of loss priority medium low bytes";
           }
           leaf policer-medium-low-rate {
             type int32;
             description
               "Rate of loss priority medium low pkts";
           }
         }
         container layer2-output-policer-statistics {
           description
             "Layer 2 output policer statistics for interface";
           leaf policer-medium-low-frames {
             type int32;
             description
               "Number of loss priority medium low frames";
           }
           leaf policer-medium-low-bytes {
             type int32;
             description
               "Number of loss priority medium low bytes";
           }
           leaf policer-medium-low-rate {
             type int32;
             description
               "Rate of loss priority medium low pkts";
           }
         }
         container mac-policer-information {
           container ether-policer-list {
           }
         }
         leaf vrfname {
           type string;
           description
             "Routing instance name";
         }
         leaf zonename {
           type string;
           description
             "Zone name";
         }
       }
       container active-alarms-otn {
       }
       container active-defects-otn {
       }
       container active-alarms-optics {
       }
       container active-defects-optics {
       }
       container optics-defect-information {
         list media-alarm {
           leaf media-alarm-name {
             type string;
           }
           leaf media-alarm-seconds {
             type int32;
           }
           leaf media-alarm-count {
             type int32;
           }
           leaf media-alarm-state {
             type string;
           }
         }
       }
       container optics-fec-information {
         list media-alarm {
           leaf media-alarm-name {
             type string;
           }
           leaf media-alarm-seconds {
             type int32;
           }
           leaf media-alarm-count {
             type int32;
           }
           leaf media-alarm-state {
             type string;
           }
         }
       }
       container active-alerts-otn {
       }
       container links {
         description
           "Aggregated SONET/SDH link information";
         list link-entry {
           description
             "SONET/SDH link information";
           leaf sonet-payload-pointer-curptr {
             type string;
             description
               "Value of the SONET/SDH payload pointer, derived from the H1 
               and H2 overhead bytes";
           }
           leaf sonet-payload-pointer-ptrinc-count {
             type string;
             description
               "Number of times the value of the SONET/SDH payload pointer 
               had positive justification";
           }
           leaf sonet-payload-pointer-ptrdec-count {
             type string;
             description
               "Number of times the value of the SONET/SDH payload pointer 
               had negative justification";
           }
           leaf sonet-payload-pointer-newptr-ndf-count {
             type string;
             description
               "Number of times a new payload pointer was created with the 
               New Data Found flag set";
           }
           leaf sonet-rx-overhead {
             type string;
           }
           leaf sonet-tx-overhead {
             type string;
           }
           leaf sonet-rx-path-trace {
             type string;
             description
               "Received SONET path trace";
           }
           leaf sonet-tx-path-trace {
             type string;
             description
               "Transmitted SONET path trace";
           }
           container active-alarms {
           }
           container active-defects {
           }
           container sonet-errors {
             list media-alarm {
               leaf media-alarm-name {
                 type string;
               }
               leaf media-alarm-count {
                 type int32;
               }
             }
           }
           container sonet-physical-information {
             list media-alarm {
               leaf media-alarm-name {
                 type string;
               }
               leaf media-alarm-seconds {
                 type int32;
               }
               leaf media-alarm-count {
                 type int32;
               }
               leaf media-alarm-state {
                 type string;
               }
             }
           }
           container sonet-section-information {
             list media-alarm {
               leaf media-alarm-name {
                 type string;
               }
               leaf media-alarm-seconds {
                 type int32;
               }
               leaf media-alarm-count {
                 type int32;
               }
               leaf media-alarm-state {
                 type string;
               }
             }
           }
           container sonet-line-information {
             list media-alarm {
               leaf media-alarm-name {
                 type string;
               }
               leaf media-alarm-seconds {
                 type int32;
               }
               leaf media-alarm-count {
                 type int32;
               }
               leaf media-alarm-state {
                 type string;
               }
             }
           }
           container sonet-path-information {
             list media-alarm {
               leaf media-alarm-name {
                 type string;
               }
               leaf media-alarm-seconds {
                 type int32;
               }
               leaf media-alarm-count {
                 type int32;
               }
               leaf media-alarm-state {
                 type string;
               }
             }
           }
           container sonet-vt-information {
             list media-alarm {
               leaf media-alarm-name {
                 type string;
               }
               leaf media-alarm-seconds {
                 type int32;
               }
               leaf media-alarm-count {
                 type int32;
               }
               leaf media-alarm-state {
                 type string;
               }
             }
           }
           container optics-diagnostics {
             description
               "Optics diagnostics";
             leaf output-power {
               type string;
               description
                 "Output power (milliwatts)";
             }
             leaf output-power-dbm {
               type string;
               description
                 "Output power (dBm)";
             }
             leaf input-power {
               type string;
               description
                 "Input power (milliwatts)";
             }
             leaf input-power-dbm {
               type string;
               description
                 "Input power (dBm)";
             }
             leaf per-wave-rx-optical-power {
               type string;
               description
                 "Per-wavelength receiver optical power (milliwatts)";
             }
             leaf per-wave-rx-optical-power-dbm {
               type string;
               description
                 "Per-wavelength receiver optical power (dBm)";
             }
             leaf lane-laser-frequency-error {
               type string;
               description
                 "Lane laser frequency error (MHz)";
             }
             leaf tec-current {
               type string;
               description
                 "Tec current";
             }
             leaf residual-isi {
               type string;
               description
                 "Residual ISI";
             }
             container optics-diagnostics-ot {
               description
                 "OT interface optics diagnostics";
               leaf module-temp-fault {
                 type string;
                 description
                   "Module temperature fault";
               }
               leaf specific-hw-fault {
                 type string;
                 description
                   "Specific HW fault";
               }
               leaf internal-power-fault {
                 type string;
                 description
                   "Internal power fault";
               }
               leaf post-therm-fault {
                 type string;
                 description
                   "Power thermal fault";
               }
               leaf post-fault {
                 type string;
                 description
                   "Post fault";
               }
               leaf command-error {
                 type string;
                 description
                   "Command error";
               }
               leaf rx-pll-lock {
                 type string;
                 description
                   "RX PLL lock";
               }
               leaf network-lane-los {
                 type string;
                 description
                   "Network Lane LOS";
               }
               leaf network-lane-lof {
                 type string;
                 description
                   "Network Lane LOF";
               }
               leaf network-lane-oof {
                 type string;
                 description
                   "Network Lane OOF";
               }
               leaf network-lane-lom {
                 type string;
                 description
                   "Network Lane LOM";
               }
               leaf network-lane-oom {
                 type string;
                 description
                   "Network Lane OOM";
               }
               leaf network-lane-otu-bdi {
                 type string;
                 description
                   "Network Lane OTU BDI";
               }
               leaf lane-rx-fifo-error {
                 type string;
                 description
                   "Lane RX FIFO error";
               }
               leaf tx-reference-clock-fault {
                 type string;
                 description
                   "TX reference clock fault";
               }
               leaf rx-modem-sync-fault {
                 type string;
                 description
                   "Rx modem sync fault";
               }
               leaf rx-modem-loss-of-lock {
                 type string;
                 description
                   "RX modem loss of lock";
               }
               leaf rx-loss-of-alignment {
                 type string;
                 description
                   "RX loss of alignment";
               }
               leaf rx-out-of-alignment {
                 type string;
                 description
                   "RX out of alignment";
               }
               leaf rx-timing-fault {
                 type string;
                 description
                   "Rx timing fault";
               }
               leaf link-msg-data-available {
                 type string;
                 description
                   "Link msg data available";
               }
               leaf modulator-bias-control-loop-fail {
                 type string;
                 description
                   "Modulator Bias Control Loop Fail";
               }
               leaf itla-fault {
                 type string;
                 description
                   "ITLA fault";
               }
               leaf dac-calib-fault {
                 type string;
                 description
                   "DAC calib fault";
               }
               leaf adc-calib-fault {
                 type string;
                 description
                   "ADC calib fault";
               }
               leaf prom-fault {
                 type string;
                 description
                   "PROM fault";
               }
               leaf tx-mod-bias-voa-ctrl-loop-high-alarm {
                 type string;
                 description
                   "TX mod bias VOA ctrl loop high alarm";
               }
               leaf tx-mod-bias-voa-ctrl-loop-low-alarm {
                 type string;
                 description
                   "TX mod bias VOA ctrl loop low alarm";
               }
               leaf rx-phase-control-loop-high-alarm {
                 type string;
                 description
                   "RX phase control loop high alarm";
               }
               leaf rx-phase-control-loop-low-alarm {
                 type string;
                 description
                   "RX phase control loop low alarm";
               }
               leaf rx-phase-control-loop-high-warning {
                 type string;
                 description
                   "RX phase control loop high warning";
               }
               leaf rx-phase-control-loop-low-warning {
                 type string;
                 description
                   "RX phase control loop low warning";
               }
               leaf oa-pump-bias-current-high-alarm {
                 type string;
                 description
                   "OA pump bias current high alarm";
               }
               leaf oa-pump-bias-current-low-alarm {
                 type string;
                 description
                   "OA pump bias current low alarm";
               }
               leaf oa-pump-bias-current-high-warning {
                 type string;
                 description
                   "OA pump bias current high warning";
               }
               leaf oa-pump-bias-current-low-warning {
                 type string;
                 description
                   "OA pump bias current low warning";
               }
               leaf tx-jitter-pll-lol-input-nw-lane {
                 type string;
                 description
                   "Tx jitter PLL LOL i/p nw lane";
               }
               leaf tx-out-of-alignment {
                 type string;
                 description
                   "TX out of alignment";
               }
               leaf tx-cmu-lock-fault {
                 type string;
                 description
                   "Tx CMU lock fault";
               }
               leaf adc-signal-below-threshold {
                 type string;
                 description
                   "ADC signal below threshold";
               }
               leaf tx-output-power-adjustment-fault {
                 type string;
                 description
                   "Tx output power adjustment fault";
               }
               leaf tx-output-mod-converge-fault {
                 type string;
                 description
                   "TX output mod converge fault";
               }
               leaf tx-laser-ready-fault {
                 type string;
                 description
                   "Tx laser ready fault";
               }
               leaf tx-laser-ready-off-fault {
                 type string;
                 description
                   "Tx laser ready off fault";
               }
               leaf tx-asic-ready-fault {
                 type string;
                 description
                   "Tx asic ready fault";
               }
               leaf tx-initialization-fault {
                 type string;
                 description
                   "Tx initialization fault";
               }
               leaf rx-demodulator-lock-fault {
                 type string;
                 description
                   "Rx demodulator lock fault";
               }
               leaf rx-dispersion-lock-fault {
                 type string;
                 description
                   "Rx dispersion lock fault";
               }
               leaf rx-adc-output-fault {
                 type string;
                 description
                   "Rx ADC output fault";
               }
               leaf rx-optical-input-fault {
                 type string;
                 description
                   "Rx optical input fault";
               }
               leaf rx-asic-ready-fault {
                 type string;
                 description
                   "Rx asic ready fault";
               }
               leaf rx-initialization-fault {
                 type string;
                 description
                   "Rx initialization fault";
               }
               leaf tx-mod-bias-high-alarm {
                 type string;
                 description
                   "TX modulator bias high alarm";
               }
               leaf tx-mod-bias-low-alarm {
                 type string;
                 description
                   "TX modulator bias low alarm";
               }
               leaf tx-mod-bias-high-warning {
                 type string;
                 description
                   "TX modulator bias high warning";
               }
               leaf tx-mod-bias-low-warning {
                 type string;
                 description
                   "TX modulator bias low warning";
               }
               leaf rx-pwr-high-alarm {
                 type string;
                 description
                   "RX power high alarm";
               }
               leaf rx-pwr-low-alarm {
                 type string;
                 description
                   "RX power low alarm";
               }
               leaf rx-pwr-high-warn {
                 type string;
                 description
                   "RX power high warning";
               }
               leaf rx-pwr-low-warn {
                 type string;
                 description
                   "RX power low warning";
               }
               leaf tx-laser-power-high-alarm {
                 type string;
                 description
                   "TX laser power high alarm";
               }
               leaf tx-laser-power-low-alarm {
                 type string;
                 description
                   "TX laser power low alarm";
               }
               leaf tx-laser-power-high-warn {
                 type string;
                 description
                   "TX laser power high warning";
               }
               leaf tx-laser-power-low-warn {
                 type string;
                 description
                   "TX laser power low warning";
               }
               leaf tx-bias-high-alarm {
                 type string;
                 description
                   "TX laser current high alarm";
               }
               leaf tx-bias-low-alarm {
                 type string;
                 description
                   "TX laser current low alarm";
               }
               leaf tx-bias-high-warn {
                 type string;
                 description
                   "TX laser current high warning";
               }
               leaf tx-bias-low-warn {
                 type string;
                 description
                   "TX laser current low warning";
               }
               leaf tx-laser-temp-high-alarm {
                 type string;
                 description
                   "TX laser temperature high alarm";
               }
               leaf tx-laser-temp-low-alarm {
                 type string;
                 description
                   "TX laser temperature low alarm";
               }
               leaf tx-laser-temp-high-warn {
                 type string;
                 description
                   "TX laser temperature high warning";
               }
               leaf tx-laser-temp-low-warn {
                 type string;
                 description
                   "TX laser temperature low warning";
               }
             }
             list optics-diagnostics-lane-values {
               key "lane-index";
               leaf lane-index {
                 type int32;
               }
               leaf laser-bias-current {
                 type string;
                 description
                   "Laser bias current (milliamperes)";
               }
               leaf laser-bias-current-not-available {
                 type string;
                 description
                   "Laser bias current measurement not available";
               }
               leaf laser-output-power {
                 type string;
                 description
                   "Laser output power (milliwatts)";
               }
               leaf laser-output-power-dbm {
                 type string;
                 description
                   "Laser output power (dBm)";
               }
               leaf output-power {
                 type string;
                 description
                   "Output power (milliwatts)";
               }
               leaf output-power-dbm {
                 type string;
                 description
                   "Output power (dBm)";
               }
               leaf laser-temperature {
                 type string;
                 description
                   "Laser temperature";
               }
               leaf laser-module-temperature {
                 type string;
                 description
                   "Module temperature";
               }
               leaf laser-tx-optical-power {
                 type string;
                 description
                   "Laser transmitter optical power (milliwatts)";
               }
               leaf laser-tx-optical-power-dbm {
                 type string;
                 description
                   "Laser transmitter optical power (dBm)";
               }
               leaf laser-rx-optical-power {
                 type string;
                 description
                   "Laser receiver optical power (milliwatts)";
               }
               leaf laser-rx-optical-power-dbm {
                 type string;
                 description
                   "Laser receiver optical power (dBm)";
               }
               leaf input-power {
                 type string;
                 description
                   "Input power (milliwatts)";
               }
               leaf input-power-dbm {
                 type string;
                 description
                   "Input power (dBm)";
               }
               leaf input-total-power {
                 type string;
                 description
                   "Input power (total) (milliwatts)";
               }
               leaf input-total-power-dbm {
                 type string;
                 description
                   "Input power (dBm)";
               }
               leaf per-wave-rx-optical-power {
                 type string;
                 description
                   "Per-wavelength receiver optical power (milliwatts)";
               }
               leaf per-wave-rx-optical-power-dbm {
                 type string;
                 description
                   "Per-wavelength receiver optical power (dBm)";
               }
               leaf lane-configured-cd {
                 type string;
                 description
                   "Lane configured chromatic dispersion (ps/nm)";
               }
               leaf lane-chromatic-dispersion {
                 type string;
                 description
                   "Lane chromatic dispersion (ps/nm)";
               }
               leaf lane-avg-chromatic-dispersion {
                 type string;
                 description
                   "Lane avg chromatic dispersion (ps/nm)";
               }
               leaf lane-min-chromatic-dispersion {
                 type string;
                 description
                   "Lane min chromatic dispersion (ps/nm)";
               }
               leaf lane-max-chromatic-dispersion {
                 type string;
                 description
                   "Lane max chromatic dispersion (ps/nm)";
               }
               leaf lane-differential-group-delay {
                 type string;
                 description
                   "Lane differential group delay (ps)";
               }
               leaf lane-avg-differential-group-delay {
                 type string;
                 description
                   "Lane avg differential group delay (ps)";
               }
               leaf lane-min-differential-group-delay {
                 type string;
                 description
                   "Lane min differential group delay (ps)";
               }
               leaf lane-max-differential-group-delay {
                 type string;
                 description
                   "Lane max differential group delay (ps)";
               }
               leaf lane-sopmd {
                 type string;
                 description
                   "Lane sopmd";
               }
               leaf lane-avg-sopmd {
                 type string;
                 description
                   "Lane avg sopmd";
               }
               leaf lane-min-sopmd {
                 type string;
                 description
                   "Lane min sopmd";
               }
               leaf lane-max-sopmd {
                 type string;
                 description
                   "Lane max sopmd";
               }
               leaf q-factor {
                 type string;
                 description
                   "Lane q-factor";
               }
               leaf q-factor-not-available {
                 type string;
                 description
                   "Lane q-factor not available";
               }
               leaf q-margin {
                 type string;
                 description
                   "Lane q-margin";
               }
               leaf q-margin-not-available {
                 type string;
                 description
                   "Lane q-margin not available";
               }
               leaf lane-state-of-polarization {
                 type string;
                 description
                   "Lane state of polarization (rad/s)";
               }
               leaf lane-avg-state-of-polarization {
                 type string;
                 description
                   "Lane avg state of polarization (rad/s)";
               }
               leaf lane-min-state-of-polarization {
                 type string;
                 description
                   "Lane min state of polarization (rad/s)";
               }
               leaf lane-max-state-of-polarization {
                 type string;
                 description
                   "Lane max state of polarization (rad/s)";
               }
               leaf lane-polarization-dependent-loss {
                 type string;
                 description
                   "Lane polarization dependent loss (dB)";
               }
               leaf lane-avg-polarization-dependent-loss {
                 type string;
                 description
                   "Lane avg polarization dependent loss (dB)";
               }
               leaf lane-min-polarization-dependent-loss {
                 type string;
                 description
                   "Lane min polarization dependent loss (dB)";
               }
               leaf lane-max-polarization-dependent-loss {
                 type string;
                 description
                   "Lane max polarization dependent loss (dB)";
               }
               leaf lane-q2-factor {
                 type string;
                 description
                   "Lane Q2 factor (dB)";
               }
               leaf lane-q-value {
                 type string;
                 description
                   "Lane q value (dB)";
               }
               leaf lane-avg-q-value {
                 type string;
                 description
                   "Lane avg q value (dB)";
               }
               leaf lane-min-q-value {
                 type string;
                 description
                   "Lane min q value (dB)";
               }
               leaf lane-max-q-value {
                 type string;
                 description
                   "Lane max q value (dB)";
               }
               leaf lane-carrier-frequency-offset {
                 type string;
                 description
                   "Lane carrier frequency offset (MHz)";
               }
               leaf lane-avg-carrier-frequency-offset {
                 type string;
                 description
                   "Lane avg carrier frequency offset (MHz)";
               }
               leaf lane-min-carrier-frequency-offset {
                 type string;
                 description
                   "Lane min carrier frequency offset (MHz)";
               }
               leaf lane-max-carrier-frequency-offset {
                 type string;
                 description
                   "Lane max carrier frequency offset (MHz)";
               }
               leaf lane-electrical-snr {
                 type string;
                 description
                   "Lane electrical SNR (dB)";
               }
               leaf lane-snr {
                 type string;
                 description
                   "Lane snr (dB)";
               }
               leaf lane-avg-snr {
                 type string;
                 description
                   "Lane avg snr (dB)";
               }
               leaf lane-min-snr {
                 type string;
                 description
                   "Lane min snr (dB)";
               }
               leaf lane-max-snr {
                 type string;
                 description
                   "Lane max snr (dB)";
               }
               leaf lane-rx-laser-bias {
                 type string;
                 description
                   "Lane rx laser bias (mA)";
               }
               leaf lane-rx-laser-power {
                 type string;
                 description
                   "Lane rx laser power (dBm)";
               }
               leaf lane-rx-laser-temp {
                 type string;
                 description
                   "Lane rx laser temp (C)";
               }
               leaf lane-tx-modulator-bias-x-i {
                 type string;
                 description
                   "Lane tx modulator bias x i (mV)";
               }
               leaf lane-tx-modulator-bias-x-q {
                 type string;
                 description
                   "Lane tx modulator bias x q (mV)";
               }
               leaf lane-tx-modulator-bias-y-i {
                 type string;
                 description
                   "Lane tx modulator bias y i (mV)";
               }
               leaf lane-tx-modulator-bias-y-q {
                 type string;
                 description
                   "Lane tx modulator bias y q (mV)";
               }
               leaf lane-tx-modulator-bias-x-phase {
                 type string;
                 description
                   "Lane tx modulator bias x phase (mV)";
               }
               leaf lane-tx-modulator-bias-y-phase {
                 type string;
                 description
                   "Lane tx modulator bias y phase (mV)";
               }
               leaf tx-input-equalization {
                 type string;
                 description
                   "Tx input equalization";
               }
               leaf rx-output-amplitude {
                 type string;
                 description
                   "Rx output amplitude";
               }
               leaf rx-output-pre-emphasis {
                 type string;
                 description
                   "Rx output pre epmhasis";
               }
               leaf lane-laser-frequency-error {
                 type string;
                 description
                   "Lane laser frequency error (MHz)";
               }
               leaf tec-current {
                 type string;
                 description
                   "Tec current";
               }
               leaf residual-isi {
                 type string;
                 description
                   "Residual ISI";
               }
               leaf pam-histogram {
                 type string;
                 description
                   "PAM histogram";
               }
               leaf laser-bias-current-high-alarm {
                 type string;
                 description
                   "Laser bias current high alarm";
               }
               leaf laser-bias-current-low-alarm {
                 type string;
                 description
                   "Laser bias current low alarm";
               }
               leaf laser-bias-current-high-warn {
                 type string;
                 description
                   "Laser bias current high warning";
               }
               leaf laser-bias-current-low-warn {
                 type string;
                 description
                   "Laser bias current low warning";
               }
               leaf laser-tx-power-high-alarm {
                 type string;
                 description
                   "Laser output power high alarm";
               }
               leaf laser-tx-power-low-alarm {
                 type string;
                 description
                   "Laser output power low alarm";
               }
               leaf laser-tx-power-high-warn {
                 type string;
                 description
                   "Laser output power high warning";
               }
               leaf laser-tx-power-low-warn {
                 type string;
                 description
                   "Laser output power low warning";
               }
               leaf tx-power-high-alarm {
                 type string;
                 description
                   "Tx power high alarm";
               }
               leaf tx-power-low-alarm {
                 type string;
                 description
                   "Tx power low alarm";
               }
               leaf tx-power-high-warn {
                 type string;
                 description
                   "Tx power high warning";
               }
               leaf tx-power-low-warn {
                 type string;
                 description
                   "Tx power low warning";
               }
               leaf laser-temp-high-alarm {
                 type string;
                 description
                   "Laser temperature high alarm";
               }
               leaf laser-temp-low-alarm {
                 type string;
                 description
                   "Laser temperature low alarm";
               }
               leaf laser-temp-high-warn {
                 type string;
                 description
                   "Laser temperature high warning";
               }
               leaf laser-temp-low-warn {
                 type string;
                 description
                   "Laser temperature low warning";
               }
               leaf laser-rx-power-high-alarm {
                 type string;
                 description
                   "Laser receiver power high alarm";
               }
               leaf laser-rx-power-low-alarm {
                 type string;
                 description
                   "Laser receiver power low alarm";
               }
               leaf laser-rx-power-high-warn {
                 type string;
                 description
                   "Laser receiver power high warning";
               }
               leaf laser-rx-power-low-warn {
                 type string;
                 description
                   "Laser receiver power low warning";
               }
               leaf rx-power-high-alarm {
                 type string;
                 description
                   "Receiver power high alarm";
               }
               leaf rx-power-low-alarm {
                 type string;
                 description
                   "Receiver power low alarm";
               }
               leaf rx-power-high-warn {
                 type string;
                 description
                   "Receiver power high warning";
               }
               leaf rx-power-low-warn {
                 type string;
                 description
                   "Receiver power low warning";
               }
               leaf tx-loss-of-signal-functionality-alarm {
                 type string;
                 description
                   "Tx loss of signal functionality alarm";
               }
               leaf rx-loss-of-signal-functionality-alarm {
                 type string;
                 description
                   "Rx loss of signal functionality alarm";
               }
               leaf tx-cdr-loss-of-lock-alarm {
                 type string;
                 description
                   "Tx CDR loss of lock alarm";
               }
               leaf tx-loss-of-signal-alarm {
                 type string;
                 description
                   "Transmitter loss of signal alarm";
               }
               leaf rx-loss-of-signal-alarm {
                 type string;
                 description
                   "Receiver loss of signal alarm";
               }
               leaf tx-laser-disabled-alarm {
                 type string;
                 description
                   "Tx laser disabled alarm";
               }
               leaf rx-cdr-loss-of-lock-alarm {
                 type string;
                 description
                   "Receiver CDR loss of lock alarm";
               }
               leaf tec-fault-alarm {
                 type string;
                 description
                   "TEC fault alarm";
               }
               leaf wavelength-unlocked-alarm {
                 type string;
                 description
                   "Wavelength unlocked alarm";
               }
               leaf apd-supply-fault-alarm {
                 type string;
                 description
                   "APD supply fault alarm";
               }
               leaf tx-channel-disabled-alarm {
                 type string;
                 description
                   "Tx channel disabled alarm";
               }
               leaf rx-channel-disabled-alarm {
                 type string;
                 description
                   "Rx channel disabled alarm";
               }
               leaf tx-output-disabled-alarm {
                 type string;
                 description
                   "Rx laser disabled alarm";
               }
               leaf rx-output-disabled-alarm {
                 type string;
                 description
                   "Rx laser disabled alarm";
               }
               leaf tx-squelch-disabled-alarm {
                 type string;
                 description
                   "Tx squelch disabled alarm";
               }
               leaf rx-squelch-disabled-alarm {
                 type string;
                 description
                   "Rx squelch disabled alarm";
               }
               leaf laser-end-of-life-alarm {
                 type string;
                 description
                   "Laser end-of-life alarm";
               }
               leaf lane-cd {
                 type string;
                 description
                   "Lane chromatic dispersion";
               }
               leaf lane-dgd {
                 type string;
                 description
                   "Lane differential group delay";
               }
               leaf lane-cfo {
                 type string;
                 description
                   "Lane carrier frequency offset";
               }
               leaf lane-pdl {
                 type string;
                 description
                   "Lane polarization dependent loss";
               }
               leaf lane-osnr {
                 type string;
                 description
                   "Optical signal-to-noise ratio(dB)";
               }
             }
             leaf optic-diagnostics-not-available {
               type string;
               description
                 "Optical diagnostics not supported by this transceiver";
             }
             leaf laser-bias-current-not-available {
               type string;
               description
                 "Laser bias current measurement not available";
             }
             leaf soa-bias-current-not-available {
               type string;
               description
                 "SOA bias current measurement not available";
             }
             leaf laser-tx-power-not-available {
               type string;
               description
                 "Laser output power measurement not available";
             }
             leaf module-temperature-not-available {
               type string;
               description
                 "Module temperature measurement not available";
             }
             leaf tx-module-temperature-not-available {
               type string;
               description
                 "Tx module temperature measurement not available";
             }
             leaf rx-module-temperature-not-available {
               type string;
               description
                 "Rx module temperature measurement not available";
             }
             leaf laser-rx-power-not-available {
               type string;
               description
                 "Laser receiver optical power measurement not available";
             }
             leaf laser-tx-power-high-alarm-threshold-not-available {
               type string;
               description
                 "Laser output power high alarm threshold not available";
             }
             leaf laser-tx-power-low-alarm-threshold-not-available {
               type string;
               description
                 "Laser output power low alarm threshold not available";
             }
             leaf laser-tx-power-high-warning-threshold-not-available {
               type string;
               description
                 "Laser output power high warning threshold not available";
             }
             leaf laser-tx-power-low-warning-threshold-not-available {
               type string;
               description
                 "Laser output power low warning threshold not available";
             }
             leaf laser-bias-current {
               type string;
               description
                 "Laser bias current (milliamperes)";
             }
             leaf soa-bias-current {
               type string;
               description
                 "SOA bias current (milliamperes)";
             }
             leaf laser-output-power {
               type string;
               description
                 "Laser output power (milliwatts)";
             }
             leaf laser-output-power-dbm {
               type string;
               description
                 "Laser output power (dBm)";
             }
             leaf module-temperature {
               type string;
               description
                 "Module temperature";
             }
             leaf tx-module-temperature {
               type string;
               description
                 "Tx module temperature";
             }
             leaf rx-module-temperature {
               type string;
               description
                 "Rx module temperature";
             }
             leaf module-voltage {
               type string;
               description
                 "Module voltage";
             }
             leaf corrected-error-ratio {
               type string;
               description
                 "Corrected error ratio";
             }
             leaf uncorrected-words-ratio {
               type string;
               description
                 "Uncorrected words ratio";
             }
             leaf tx-module-voltage {
               type string;
               description
                 "Tx module voltage";
             }
             leaf rx-module-voltage {
               type string;
               description
                 "Rx module voltage";
             }
             leaf rx-signal-avg-optical-power {
               type string;
               description
                 "Receiver signal average power (milliwatts)";
             }
             leaf rx-signal-avg-optical-power-dbm {
               type string;
               description
                 "Receiver signal average power (dBm)";
             }
             leaf laser-rx-optical-power {
               type string;
               description
                 "Laser receiver optical power (milliwatts)";
             }
             leaf laser-rx-optical-power-dbm {
               type string;
               description
                 "Laser receiver optical power (dBm)";
             }
             leaf wavelength-channel {
               type string;
               description
                 "Wavelength channel number set";
             }
             leaf wavelength-setpoint {
               type string;
               description
                 "Wavelength point set";
             }
             leaf tx-dither {
               type string;
               description
                 "Tx dither status";
             }
             leaf frequency-error {
               type string;
               description
                 "Frequency error value";
             }
             leaf wavelength-error {
               type string;
               description
                 "Wavelength error value";
             }
             leaf laser-bias-current-high-alarm {
               type string;
               description
                 "Laser bias current high alarm";
             }
             leaf laser-bias-current-low-alarm {
               type string;
               description
                 "Laser bias current low alarm";
             }
             leaf laser-bias-current-high-warn {
               type string;
               description
                 "Laser bias current high warning";
             }
             leaf laser-bias-current-low-warn {
               type string;
               description
                 "Laser bias current low warning";
             }
             leaf soa-bias-current-high-alarm {
               type string;
               description
                 "SOA bias current high alarm";
             }
             leaf soa-bias-current-low-alarm {
               type string;
               description
                 "SOA bias current low alarm";
             }
             leaf soa-bias-current-high-warn {
               type string;
               description
                 "SOA bias current high warning";
             }
             leaf soa-bias-current-low-warn {
               type string;
               description
                 "SOA bias current low warning";
             }
             leaf laser-tx-power-high-alarm {
               type string;
               description
                 "Laser output power high alarm";
             }
             leaf laser-tx-power-low-alarm {
               type string;
               description
                 "Laser output power low alarm";
             }
             leaf laser-tx-power-high-warn {
               type string;
               description
                 "Laser output power high warning";
             }
             leaf laser-tx-power-low-warn {
               type string;
               description
                 "Laser output power low warning";
             }
             leaf tx-power-high-alarm {
               type string;
               description
                 "Tx power high alarm";
             }
             leaf tx-power-low-alarm {
               type string;
               description
                 "Tx power low alarm";
             }
             leaf tx-power-high-warn {
               type string;
               description
                 "Tx power high warning";
             }
             leaf tx-power-low-warn {
               type string;
               description
                 "Tx power low warning";
             }
             leaf module-temperature-high-alarm {
               type string;
               description
                 "Module temperature high alarm";
             }
             leaf module-temperature-low-alarm {
               type string;
               description
                 "Module temperature low alarm";
             }
             leaf module-temperature-high-warn {
               type string;
               description
                 "Module temperature high warning";
             }
             leaf module-temperature-low-warn {
               type string;
               description
                 "Module temperature low warning";
             }
             leaf tx-module-temperature-high-alarm {
               type string;
               description
                 "Tx module temperature high alarm";
             }
             leaf tx-module-temperature-low-alarm {
               type string;
               description
                 "Tx module temperature low alarm";
             }
             leaf rx-module-temperature-high-alarm {
               type string;
               description
                 "Rx module temperature high alarm";
             }
             leaf rx-module-temperature-low-alarm {
               type string;
               description
                 "Rx module temperature low alarm";
             }
             leaf module-voltage-high-alarm {
               type string;
               description
                 "Module voltage high alarm";
             }
             leaf module-voltage-low-alarm {
               type string;
               description
                 "Module voltage low alarm";
             }
             leaf module-voltage-high-warn {
               type string;
               description
                 "Module voltage high warning";
             }
             leaf module-voltage-low-warn {
               type string;
               description
                 "Module voltage low warning";
             }
             leaf tx-module-voltage-high-alarm {
               type string;
               description
                 "Tx module voltage high alarm";
             }
             leaf tx-module-voltage-low-alarm {
               type string;
               description
                 "Tx module voltage low alarm";
             }
             leaf rx-module-voltage-high-alarm {
               type string;
               description
                 "Rx module voltage high alarm";
             }
             leaf rx-module-voltage-low-alarm {
               type string;
               description
                 "Rx module voltage low alarm";
             }
             leaf laser-rx-power-high-alarm {
               type string;
               description
                 "Laser receiver power high alarm";
             }
             leaf laser-rx-power-low-alarm {
               type string;
               description
                 "Laser receiver power low alarm";
             }
             leaf laser-rx-power-high-warn {
               type string;
               description
                 "Laser receiver power high warning";
             }
             leaf laser-rx-power-low-warn {
               type string;
               description
                 "Laser receiver power low warning";
             }
             leaf rx-power-high-alarm {
               type string;
               description
                 "Receiver power high alarm";
             }
             leaf rx-power-low-alarm {
               type string;
               description
                 "Receiver power low alarm";
             }
             leaf rx-power-high-warn {
               type string;
               description
                 "Receiver power high warning";
             }
             leaf rx-power-low-warn {
               type string;
               description
                 "Receiver power low warning";
             }
             leaf laser-end-of-life-alarm {
               type string;
               description
                 "Laser end-of-life alarm";
             }
             leaf laser-wavelength-alarm {
               type string;
               description
                 "Laser wavelength alarm";
             }
             leaf laser-bias-current-alarm {
               type string;
               description
                 "Laser bias current alarm";
             }
             leaf module-temperature-alarm {
               type string;
               description
                 "Module temperature alarm";
             }
             leaf laser-power-alarm {
               type string;
               description
                 "Laser power alarm";
             }
             leaf modulator-temperature-alarm {
               type string;
               description
                 "Modulator temperature alarm";
             }
             leaf modulator-bias-alarm {
               type string;
               description
                 "Modulator bias alarm";
             }
             leaf module-not-ready-alarm {
               type string;
               description
                 "Module not ready alarm";
             }
             leaf module-power-down-alarm {
               type string;
               description
                 "Module power down alarm";
             }
             leaf module-not-init-done-alarm {
               type string;
               description
                 "Module initialization not done alarm";
             }
             leaf module-not-high-power-on-alarm {
               type string;
               description
                 "Module not high powered on alarm";
             }
             leaf module-fault-alarm {
               type string;
               description
                 "Module in fault state alarm";
             }
             leaf pld-flash-init-fault-alarm {
               type string;
               description
                 "PLD or Flash initialization fault alarm";
             }
             leaf power-supply-fault-alarm {
               type string;
               description
                 "Power supply fault alarm";
             }
             leaf checksum-fault-alarm {
               type string;
               description
                 "Checksum fault alarm";
             }
             leaf apd-supply-fault-alarm {
               type string;
               description
                 "APD supply fault alarm";
             }
             leaf tec-fault-alarm {
               type string;
               description
                 "TEC fault alarm";
             }
             leaf wavelength-unlocked-alarm {
               type string;
               description
                 "Wavelength unlocked alarm";
             }
             leaf tx-tune-alarm {
               type string;
               description
                 "Tx tune alarm";
             }
             leaf tx-mux-fifo-error-alarm {
               type string;
               description
                 "Tx multiplexer fifo error alarm";
             }
             leaf tx-loss-of-pll-alarm {
               type string;
               description
                 "Tx loss of PLL alarm";
             }
             leaf tx-data-not-ready-alarm {
               type string;
               description
                 "Tx data not ready alarm";
             }
             leaf tx-not-ready-alarm {
               type string;
               description
                 "Tx not ready alarm";
             }
             leaf tx-laser-fault-alarm {
               type string;
               description
                 "Tx laser fault alarm";
             }
             leaf tx-laser-disabled-alarm {
               type string;
               description
                 "Tx laser disabled alarm";
             }
             leaf tx-loss-of-signal-functionality-alarm {
               type string;
               description
                 "Tx loss of signal functionality alarm";
             }
             leaf tx-cdr-loss-of-lock-alarm {
               type string;
               description
                 "Tx CDR loss of lock alarm";
             }
             leaf rx-loss-avg-opt-power-alarm {
               type string;
               description
                 "Receiver loss of average optical power alarm";
             }
             leaf rx-loss-ac-power-alarm {
               type string;
               description
                 "Receiver loss of AC power alarm";
             }
             leaf rx-loss-of-pll-alarm {
               type string;
               description
                 "Receiver loss of PLL alarm";
             }
             leaf rx-not-ready-alarm {
               type string;
               description
                 "Receiver not ready alarm";
             }
             leaf rx-loss-of-signal-alarm {
               type string;
               description
                 "Receiver loss of signal alarm";
             }
             leaf rx-cdr-loss-of-lock-alarm {
               type string;
               description
                 "Receiver CDR loss of lock alarm";
             }
             leaf laser-bias-current-high-alarm-threshold {
               type string;
               description
                 "Laser bias current high alarm threshold (milliamperes)";
             }
             leaf laser-bias-current-low-alarm-threshold {
               type string;
               description
                 "Laser bias current low alarm threshold (milliamperes)";
             }
             leaf laser-bias-current-high-warn-threshold {
               type string;
               description
                 "Laser bias current high warning threshold (milliamperes)";
             }
             leaf laser-bias-current-low-warn-threshold {
               type string;
               description
                 "Laser bias current low warning threshold (milliamperes)";
             }
             leaf soa-bias-current-high-alarm-threshold {
               type string;
               description
                 "SOA bias current high alarm threshold (milliamperes)";
             }
             leaf soa-bias-current-low-alarm-threshold {
               type string;
               description
                 "SOA bias current low alarm threshold (milliamperes)";
             }
             leaf soa-bias-current-high-warn-threshold {
               type string;
               description
                 "SOA bias current high warning threshold (milliamperes)";
             }
             leaf soa-bias-current-low-warn-threshold {
               type string;
               description
                 "SOA bias current low warning threshold (milliamperes)";
             }
             leaf laser-tx-power-high-alarm-threshold {
               type string;
               description
                 "Laser transmitter power high alarm threshold (milliwatts)";
             }
             leaf laser-tx-power-high-alarm-threshold-dbm {
               type string;
               description
                 "Laser transmitter power high alarm threshold (dBm)";
             }
             leaf laser-tx-power-low-alarm-threshold {
               type string;
               description
                 "Laser transmitter power low alarm threshold (milliwatts)";
             }
             leaf laser-tx-power-low-alarm-threshold-dbm {
               type string;
               description
                 "Laser transmitter power low alarm threshold (dBm)";
             }
             leaf laser-tx-power-high-warn-threshold {
               type string;
               description
                 "Laser transmitter power high warning threshold 
                 (milliwatts)";
             }
             leaf laser-tx-power-high-warn-threshold-dbm {
               type string;
               description
                 "Laser transmitter power high warning threshold (dBm)";
             }
             leaf laser-tx-power-low-warn-threshold {
               type string;
               description
                 "Laser transmitter power low warning threshold (milliwatts)";
             }
             leaf laser-tx-power-low-warn-threshold-dbm {
               type string;
               description
                 "Laser transmitter power low warning threshold (dBm)";
             }
             leaf module-temperature-high-alarm-threshold {
               type string;
               description
                 "Module temperature high alarm threshold";
             }
             leaf module-temperature-low-alarm-threshold {
               type string;
               description
                 "Module temperature low alarm threshold";
             }
             leaf module-temperature-high-warn-threshold {
               type string;
               description
                 "Module temperature high warning threshold";
             }
             leaf module-temperature-low-warn-threshold {
               type string;
               description
                 "Module temperature low warning threshold";
             }
             leaf laser-temperature-high-alarm-threshold {
               type string;
               description
                 "Laser temperature high alarm threshold";
             }
             leaf laser-temperature-low-alarm-threshold {
               type string;
               description
                 "Laser temperature low alarm threshold";
             }
             leaf laser-temperature-high-warn-threshold {
               type string;
               description
                 "Laser temperature high warning threshold";
             }
             leaf laser-temperature-low-warn-threshold {
               type string;
               description
                 "Laser temperature low warning threshold";
             }
             leaf module-voltage-high-alarm-threshold {
               type string;
               description
                 "Module voltage high alarm threshold (volts)";
             }
             leaf module-voltage-low-alarm-threshold {
               type string;
               description
                 "Module voltage low alarm threshold (volts)";
             }
             leaf module-voltage-high-warn-threshold {
               type string;
               description
                 "Module voltage high warning threshold (volts)";
             }
             leaf module-voltage-low-warn-threshold {
               type string;
               description
                 "Module voltage low warning threshold (volts)";
             }
             leaf laser-rx-power-high-alarm-threshold {
               type string;
               description
                 "Laser receiver power high alarm (milliwatts)";
             }
             leaf laser-rx-power-high-alarm-threshold-dbm {
               type string;
               description
                 "Laser receiver power high alarm (dBm)";
             }
             leaf laser-rx-power-low-alarm-threshold {
               type string;
               description
                 "Laser receiver power low alarm (milliwatts)";
             }
             leaf laser-rx-power-low-alarm-threshold-dbm {
               type string;
               description
                 "Laser receiver power low alarm (dBm)";
             }
             leaf laser-rx-power-high-warn-threshold {
               type string;
               description
                 "Laser receiver power high warning (milliwatts)";
             }
             leaf laser-rx-power-high-warn-threshold-dbm {
               type string;
               description
                 "Laser receiver power high warning (dBm)";
             }
             leaf laser-rx-power-low-warn-threshold {
               type string;
               description
                 "Laser receiver power low warning (milliwatts)";
             }
             leaf laser-rx-power-low-warn-threshold-dbm {
               type string;
               description
                 "Laser receiver power low warning (dBm)";
             }
             leaf rx-power-high-alarm-threshold {
               type string;
               description
                 "Receiver power high alarm (milliwatts)";
             }
             leaf rx-power-high-alarm-threshold-dbm {
               type string;
               description
                 "Receiver power high alarm (dBm)";
             }
             leaf rx-power-low-alarm-threshold {
               type string;
               description
                 "Receiver power low alarm (milliwatts)";
             }
             leaf rx-power-low-alarm-threshold-dbm {
               type string;
               description
                 "Receiver power low alarm (dBm)";
             }
             leaf rx-power-high-warning-threshold {
               type string;
               description
                 "Receiver power high warning (milliwatts)";
             }
             leaf rx-power-high-warning-threshold-dbm {
               type string;
               description
                 "Receiver power high warning (dBm)";
             }
             leaf rx-power-low-warning-threshold {
               type string;
               description
                 "Receiver power low warning (milliwatts)";
             }
             leaf rx-power-low-warning-threshold-dbm {
               type string;
               description
                 "Receiver power low warning (dBm)";
             }
             leaf los-alarm-threshold {
               type string;
               description
                 "LOS alarm threshold (milliwatts)";
             }
             leaf los-alarm-threshold-dbm {
               type string;
               description
                 "LOS alarm threshold (dBm)";
             }
             leaf los-warning-threshold {
               type string;
               description
                 "LOS warning threshold (milliwatts)";
             }
             leaf los-warning-threshold-dbm {
               type string;
               description
                 "LOS warning threshold (dBm)";
             }
             leaf dsp-module-state {
               type string;
               description
                 "DSP module state";
             }
           }
           container optics-diagnostics-vendor-extension {
             description
               "Optics diagnostics vendor extension";
             leaf optics-vendor-part-number {
               type string;
               description
                 "Optics component vendor part number";
             }
             leaf optics-vendor-material-number {
               type string;
               description
                 "Optic component vendor material number";
             }
           }
           list optics-chromatics {
             key "optics-chromatic-diagnostics-support";
             leaf optics-chromatic-diagnostics-support {
               type string;
               description
                 "Optics chromatic not supported for interface";
             }
             leaf opticstype {
               type string;
               description
                 "Type of optical module";
             }
             list optics-chromatic {
               key "supported-cd supported-mediaid";
               leaf supported-speed {
                 type string;
                 description
                   "Supported Speed";
               }
               leaf supported-cd {
                 type string;
                 description
                   "Supported Chromatic Dispersion";
               }
               leaf supported-distance {
                 type string;
                 description
                   "Supported Distance";
               }
               leaf supported-mediaid {
                 type string;
                 description
                   "Supported Mediaid";
               }
             }
           }
         }
       }
       container macsec-statistics {
         description
           "MACSec Statistics ";
         leaf macsec-tx-sc-protected {
           type int32;
           description
             "Protected Secure Channel MACSec packets transmitted";
         }
         leaf macsec-tx-sc-encrypted {
           type int32;
           description
             "Encrypted Secure Channel MACSec packets transmitted";
         }
         leaf macsec-tx-sc-protectedbytes {
           type int32;
           description
             "Protected Secure Channel MACSec bytes transmitted";
         }
         leaf macsec-tx-sc-encryptedbytes {
           type int32;
           description
             "Encrypted Secure Channel MACSec bytes transmitted";
         }
         leaf macsec-rx-sc-ok {
           type int32;
           description
             "OK Secure Association MACSec packets received";
         }
         leaf macsec-rx-sc-validatedbytes {
           type int32;
           description
             "Validated Secure Association MACSec bytes received";
         }
         leaf macsec-rx-sc-decryptedbytes {
           type int32;
           description
             "Validated Secure Association MACSec bytes received";
         }
       }
       container peer-configuration-status {
         description
           "Nonmatching DCE end DLCIs";
         leaf peer-nonmatching-dlci {
           type int32;
           description
             "DCE end DLCIs that does not match the DTE";
         }
       }
       container lsi-traffic-statistics {
         leaf input-bytes {
           type int32;
         }
         leaf input-bps {
           type int32;
         }
         leaf input-packets {
           type uint64;
         }
         leaf input-pps {
           type int32;
         }
       }
       container stp-traffic-statistics {
         leaf stp-input-bytes-dropped {
           type int32;
           description
             "Drop statistics due to stp state at ingress in bytes";
         }
         leaf stp-output-bytes-dropped {
           type int32;
           description
             "Drop statistics due to stp state at egress in bytes";
         }
         leaf stp-input-packets-dropped {
           type int32;
           description
             "Drop statistics due to stp state at ingress in packets";
         }
         leaf stp-output-packets-dropped {
           type int32;
           description
             "Drop statistics due to stp state at egress in packets";
         }
       }
       container ethernet-rpf-counter-stats {
         leaf ethernet-rpf-ipv4-rpf-bytes {
           type int32;
           description
             "Counter for ipv4 rpf byptes";
         }
         leaf ethernet-rpf-ipv4-rpf-packets {
           type int32;
           description
             "Counter for ipv4 rpf packets";
         }
         leaf ethernet-rpf-ipv6-rpf-bytes {
           type int32;
           description
             "Counter for ipv6 rpf byptes";
         }
         leaf ethernet-rpf-ipv6-rpf-packets {
           type int32;
           description
             "Counter for ipv6 rpf packets";
         }
       }
       container af-fe-info {
       }
       container af-fe-lb-stats-info {
       }
       container af-fe-q-pkts {
       }
       container af-fe-q-bytes {
       }
       container chassis-queue-counters {
         description
           "Chassis queue counter statistics";
         container interface-chassis-cos-summary {
           description
             "Packet Forwarding Engine chassis forwarding class and queue 
             information for an interface";
           leaf intf-cos-chassis-num-queues-supported {
             type int32;
             description
               "Number of Packet Forwarding Engine chassis queues the 
               interface supports";
           }
           leaf intf-cos-chassis-num-queues-in-use {
             type int32;
             description
               "Number of Packet Forwarding Engine chassis queues in use on 
               the interface";
           }
         }
         list queue {
           key "queue-number";
           description
             "Counters for a single queue";
           leaf queue-number {
             type uint32;
             description
               "Queue number";
           }
           leaf forwarding-class-name {
             type string;
             description
               "Forwarding class name associated with queue";
           }
           leaf queue-counters-queued-packets {
             type int32;
             description
               "Queued packet count";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-queued-packets-na {
             type string;
             description
               "Queued packets not available";
           }
           leaf queue-counters-queued-bytes-na {
             type string;
             description
               "Queued bytes not available";
           }
           leaf queue-counters-trans-packets {
             type int32;
             description
               "Total number of transmitted packets";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets-na {
             type string;
             description
               "Number of packets dropped due to tail drop not available";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of packets dropped at tail drop of the queue";
           }
           leaf queue-counters-tail-drop-bytes-rate {
             type int32;
             description
               "Number of packets dropped at tail drop of the queue";
           }
           leaf queue-counters-ecn-ce-packets {
             type int32;
             description
               "Total number of ECN CE packets";
           }
           leaf queue-counters-ecn-ce-packets-rate {
             type int32;
             description
               "Rate at which ECN CE packets are transmitted";
           }
           leaf queue-counters-ecn-ce-bytes {
             type int32;
             description
               "Total number of ECN CE bytes";
           }
           leaf queue-counters-ecn-ce-bytes-rate {
             type int32;
             description
               "Rate at which ECN CE bytes are transmitted";
           }
           leaf queue-counters-rate-limit-drop-packets-na {
             type string;
             description
               "Number of packets dropped due to rate-limit drop not 
               available";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes-na {
             type string;
             description
               "Number of bytes dropped due to tail drop not available";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets-na {
             type string;
             description
               "Number of packets dropped due to RED not available";
           }
           leaf queue-counters-red-packets {
             type int32;
             description
               "Number of packets dropped due to RED";
           }
           leaf queue-counters-red-packets-rate {
             type int32;
             description
               "Rate at which packets are dropped due to RED";
           }
           leaf queue-counters-red-packets-ln {
             type int32;
             description
               "Number of RED dropped low-loss, non-TCP packets";
           }
           leaf queue-counters-red-packets-rate-ln {
             type int32;
             description
               "RED drop rate for low-loss, non-TCP packets";
           }
           leaf queue-counters-red-packets-lt {
             type int32;
             description
               "Number of RED dropped of low-loss, TCP packets";
           }
           leaf queue-counters-red-packets-rate-lt {
             type int32;
             description
               "RED drop rate for low-loss, TCP packets";
           }
           leaf queue-counters-red-packets-hn {
             type int32;
             description
               "Number of RED dropped high-loss, non-TCP packets";
           }
           leaf queue-counters-red-packets-rate-hn {
             type int32;
             description
               "RED drop rate for high-loss, non-TCP packets";
           }
           leaf queue-counters-red-packets-ht {
             type int32;
             description
               "Number of RED dropped high-loss, TCP packets";
           }
           leaf queue-counters-red-packets-rate-ht {
             type int32;
             description
               "RED drop rate for high-loss, TCP packets";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-medium {
             type int32;
             description
               "Number of RED dropped medium-loss packets";
           }
           leaf queue-counters-red-packets-rate-medium {
             type int32;
             description
               "RED drop rate for medium-loss packets";
           }
           leaf queue-counters-red-packets-high {
             type int32;
             description
               "Number of RED dropped high-loss packets";
           }
           leaf queue-counters-red-packets-rate-high {
             type int32;
             description
               "RED drop rate for high-loss packets";
           }
           leaf queue-counters-red-bytes-na {
             type string;
             description
               "Number of bytes dropped due to RED not available";
           }
           leaf queue-counters-red-bytes {
             type int32;
             description
               "Number of bytes dropped due to RED";
           }
           leaf queue-counters-red-bytes-rate {
             type int32;
             description
               "Rate at which bytes are dropped due to RED";
           }
           leaf queue-counters-red-bytes-ln {
             type int32;
             description
               "Number of RED dropped low-loss, non-TCP bytes";
           }
           leaf queue-counters-red-bytes-rate-ln {
             type int32;
             description
               "RED drop rate for low-loss, non-TCP bytes";
           }
           leaf queue-counters-red-bytes-lt {
             type int32;
             description
               "Number of RED dropped low-loss, TCP bytes";
           }
           leaf queue-counters-red-bytes-rate-lt {
             type int32;
             description
               "RED drop rate for low-loss, TCP bytes";
           }
           leaf queue-counters-red-bytes-hn {
             type int32;
             description
               "Number of RED dropped high-loss, non-TCP bytes";
           }
           leaf queue-counters-red-bytes-rate-hn {
             type int32;
             description
               "RED drop rate for high-loss, non-TCP bytes";
           }
           leaf queue-counters-red-bytes-ht {
             type int32;
             description
               "Number of RED dropped high-loss, TCP bytes";
           }
           leaf queue-counters-red-bytes-rate-ht {
             type int32;
             description
               "RED drop rate for high-loss, TCP bytes";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-medium {
             type int32;
             description
               "Number of RED dropped medium-loss bytes";
           }
           leaf queue-counters-red-bytes-rate-medium {
             type int32;
             description
               "RED drop rate for medium-loss bytes";
           }
           leaf queue-counters-red-bytes-high {
             type int32;
             description
               "Number of RED dropped high-loss bytes";
           }
           leaf queue-counters-red-bytes-rate-high {
             type int32;
             description
               "RED drop rate for high-loss bytes";
           }
           leaf queue-counters-timestamp {
             type int32;
             description
               "Last packet enqueued timestamp";
           }
           leaf queue-counters-total-drop-packets {
             type int32;
             description
               "Number of total packets dropped at the queue";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
           leaf queue-counters-reserved-buffer-packets {
             type int32;
             description
               "Queues's usage of reserved buffer pool in pkts";
           }
           leaf queue-counters-reserved-buffer-bytes {
             type int32;
             description
               "Queues's usage of reserved buffer pool in bytes";
           }
           leaf queue-counters-shared-buffer-packets {
             type int32;
             description
               "Queues's usage of shared buffer pool in pkts";
           }
           leaf queue-counters-shared-buffer-bytes {
             type int32;
             description
               "Queues's usage of shared buffer pool in bytes";
           }
           leaf queue-counters-depth-average {
             type int32;
             description
               "Time averaged queue depth";
           }
           leaf queue-counters-depth-current {
             type int32;
             description
               "Current instantaneous queue depth";
           }
           leaf queue-counters-depth-peak {
             type int32;
             description
               "Peak queue depth";
           }
           leaf queue-counters-depth-max {
             type int32;
             description
               "Maximum queue depth attained";
           }
           leaf queue-counters-srx-reserved-buffer-bytes {
             type int32;
             description
               "Queues's usage of reserved buffer pool in bytes";
           }
           leaf queue-counters-srx-depth-current {
             type int32;
             description
               "Current instantaneous queue depth";
           }
         }
       }
       container ingress-queue-counters {
         description
           "Ingress queue counter statistics";
         list queue {
           key "queue-number";
           description
             "Counters for a single queue";
           leaf queue-number {
             type uint32;
             description
               "Queue number";
           }
           leaf forwarding-class-name {
             type string;
             description
               "Forwarding class name associated with queue";
           }
           leaf queue-counters-queued-packets {
             type int32;
             description
               "Queued packet count";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-queued-packets-na {
             type string;
             description
               "Queued packets not available";
           }
           leaf queue-counters-queued-bytes-na {
             type string;
             description
               "Queued bytes not available";
           }
           leaf queue-counters-trans-packets {
             type int32;
             description
               "Total number of transmitted packets";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets-na {
             type string;
             description
               "Number of packets dropped due to tail drop not available";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of packets dropped at tail drop of the queue";
           }
           leaf queue-counters-tail-drop-bytes-rate {
             type int32;
             description
               "Number of packets dropped at tail drop of the queue";
           }
           leaf queue-counters-ecn-ce-packets {
             type int32;
             description
               "Total number of ECN CE packets";
           }
           leaf queue-counters-ecn-ce-packets-rate {
             type int32;
             description
               "Rate at which ECN CE packets are transmitted";
           }
           leaf queue-counters-ecn-ce-bytes {
             type int32;
             description
               "Total number of ECN CE bytes";
           }
           leaf queue-counters-ecn-ce-bytes-rate {
             type int32;
             description
               "Rate at which ECN CE bytes are transmitted";
           }
           leaf queue-counters-rate-limit-drop-packets-na {
             type string;
             description
               "Number of packets dropped due to rate-limit drop not 
               available";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes-na {
             type string;
             description
               "Number of bytes dropped due to tail drop not available";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets-na {
             type string;
             description
               "Number of packets dropped due to RED not available";
           }
           leaf queue-counters-red-packets {
             type int32;
             description
               "Number of packets dropped due to RED";
           }
           leaf queue-counters-red-packets-rate {
             type int32;
             description
               "Rate at which packets are dropped due to RED";
           }
           leaf queue-counters-red-packets-ln {
             type int32;
             description
               "Number of RED dropped low-loss, non-TCP packets";
           }
           leaf queue-counters-red-packets-rate-ln {
             type int32;
             description
               "RED drop rate for low-loss, non-TCP packets";
           }
           leaf queue-counters-red-packets-lt {
             type int32;
             description
               "Number of RED dropped of low-loss, TCP packets";
           }
           leaf queue-counters-red-packets-rate-lt {
             type int32;
             description
               "RED drop rate for low-loss, TCP packets";
           }
           leaf queue-counters-red-packets-hn {
             type int32;
             description
               "Number of RED dropped high-loss, non-TCP packets";
           }
           leaf queue-counters-red-packets-rate-hn {
             type int32;
             description
               "RED drop rate for high-loss, non-TCP packets";
           }
           leaf queue-counters-red-packets-ht {
             type int32;
             description
               "Number of RED dropped high-loss, TCP packets";
           }
           leaf queue-counters-red-packets-rate-ht {
             type int32;
             description
               "RED drop rate for high-loss, TCP packets";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-medium {
             type int32;
             description
               "Number of RED dropped medium-loss packets";
           }
           leaf queue-counters-red-packets-rate-medium {
             type int32;
             description
               "RED drop rate for medium-loss packets";
           }
           leaf queue-counters-red-packets-high {
             type int32;
             description
               "Number of RED dropped high-loss packets";
           }
           leaf queue-counters-red-packets-rate-high {
             type int32;
             description
               "RED drop rate for high-loss packets";
           }
           leaf queue-counters-red-bytes-na {
             type string;
             description
               "Number of bytes dropped due to RED not available";
           }
           leaf queue-counters-red-bytes {
             type int32;
             description
               "Number of bytes dropped due to RED";
           }
           leaf queue-counters-red-bytes-rate {
             type int32;
             description
               "Rate at which bytes are dropped due to RED";
           }
           leaf queue-counters-red-bytes-ln {
             type int32;
             description
               "Number of RED dropped low-loss, non-TCP bytes";
           }
           leaf queue-counters-red-bytes-rate-ln {
             type int32;
             description
               "RED drop rate for low-loss, non-TCP bytes";
           }
           leaf queue-counters-red-bytes-lt {
             type int32;
             description
               "Number of RED dropped low-loss, TCP bytes";
           }
           leaf queue-counters-red-bytes-rate-lt {
             type int32;
             description
               "RED drop rate for low-loss, TCP bytes";
           }
           leaf queue-counters-red-bytes-hn {
             type int32;
             description
               "Number of RED dropped high-loss, non-TCP bytes";
           }
           leaf queue-counters-red-bytes-rate-hn {
             type int32;
             description
               "RED drop rate for high-loss, non-TCP bytes";
           }
           leaf queue-counters-red-bytes-ht {
             type int32;
             description
               "Number of RED dropped high-loss, TCP bytes";
           }
           leaf queue-counters-red-bytes-rate-ht {
             type int32;
             description
               "RED drop rate for high-loss, TCP bytes";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-medium {
             type int32;
             description
               "Number of RED dropped medium-loss bytes";
           }
           leaf queue-counters-red-bytes-rate-medium {
             type int32;
             description
               "RED drop rate for medium-loss bytes";
           }
           leaf queue-counters-red-bytes-high {
             type int32;
             description
               "Number of RED dropped high-loss bytes";
           }
           leaf queue-counters-red-bytes-rate-high {
             type int32;
             description
               "RED drop rate for high-loss bytes";
           }
           leaf queue-counters-timestamp {
             type int32;
             description
               "Last packet enqueued timestamp";
           }
           leaf queue-counters-total-drop-packets {
             type int32;
             description
               "Number of total packets dropped at the queue";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
           leaf queue-counters-reserved-buffer-packets {
             type int32;
             description
               "Queues's usage of reserved buffer pool in pkts";
           }
           leaf queue-counters-reserved-buffer-bytes {
             type int32;
             description
               "Queues's usage of reserved buffer pool in bytes";
           }
           leaf queue-counters-shared-buffer-packets {
             type int32;
             description
               "Queues's usage of shared buffer pool in pkts";
           }
           leaf queue-counters-shared-buffer-bytes {
             type int32;
             description
               "Queues's usage of shared buffer pool in bytes";
           }
           leaf queue-counters-depth-average {
             type int32;
             description
               "Time averaged queue depth";
           }
           leaf queue-counters-depth-current {
             type int32;
             description
               "Current instantaneous queue depth";
           }
           leaf queue-counters-depth-peak {
             type int32;
             description
               "Peak queue depth";
           }
           leaf queue-counters-depth-max {
             type int32;
             description
               "Maximum queue depth attained";
           }
           leaf queue-counters-srx-reserved-buffer-bytes {
             type int32;
             description
               "Queues's usage of reserved buffer pool in bytes";
           }
           leaf queue-counters-srx-depth-current {
             type int32;
             description
               "Current instantaneous queue depth";
           }
         }
         container interface-cos-summary {
           description
             "Summary of forwarding class and queue information on an 
             interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
           leaf intf-cos-burst-size-for-ifl {
             type int32;
             description
               "Burst size for the logical interface";
           }
         }
         container interface-cos-short-summary {
           description
             "Summary of queue information on an interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
         }
         list queue-num-forwarding-class-name-map {
           key "queue-number";
           leaf queue-number {
             type uint32;
             description
               "Queue number";
           }
           leaf forwarding-class-name {
             type string;
             description
               "Forwarding class name associated with queue";
           }
         }
       }
       container otn-oc-information {
         list media-alarm {
           leaf media-alarm-name {
             type string;
           }
           leaf media-alarm-seconds {
             type int32;
           }
           leaf media-alarm-count {
             type int32;
           }
           leaf media-alarm-state {
             type string;
           }
         }
       }
       container otn-otu-information {
         list media-alarm {
           leaf media-alarm-name {
             type string;
           }
           leaf media-alarm-seconds {
             type int32;
           }
           leaf media-alarm-count {
             type int32;
           }
           leaf media-alarm-state {
             type string;
           }
         }
       }
       container otn-odu-information {
         list media-alarm {
           leaf media-alarm-name {
             type string;
           }
           leaf media-alarm-seconds {
             type int32;
           }
           leaf media-alarm-count {
             type int32;
           }
           leaf media-alarm-state {
             type string;
           }
         }
       }
       container otn-ot-module-information {
         list media-alarm {
           leaf media-alarm-name {
             type string;
           }
           leaf media-alarm-seconds {
             type int32;
           }
           leaf media-alarm-count {
             type int32;
           }
           leaf media-alarm-state {
             type string;
           }
         }
       }
       list otn-odu-tcm-information {
         list media-alarm {
           leaf media-alarm-name {
             type string;
           }
           leaf media-alarm-seconds {
             type int32;
           }
           leaf media-alarm-count {
             type int32;
           }
           leaf media-alarm-state {
             type string;
           }
         }
       }
       container ima-group-information {
         description
           "IMA group alarms";
       }
       container ima-link-information {
         description
           "IMA link alarms";
       }
       list smart-sfp-channel-statistics {
         key "iwf-channel-num";
         description
           "Smart SFP channel IWF statistics";
         leaf iwf-channel-num {
           type uint32;
           description
             "Channel number for IWF stats";
         }
         leaf channel-not-applicable {
           type string;
           description
             "Channelization are not supported";
         }
         container smart-sfp-av-titan-iwf-statistics {
           leaf rx-packets {
             type uint32;
           }
           leaf tx-packets {
             type uint32;
           }
           leaf malformed-packets {
             type uint32;
           }
           leaf reordered-packets {
             type uint32;
           }
           leaf misordered-dropped-packets {
             type uint32;
           }
           leaf missing-packets {
             type uint32;
           }
           leaf played-out-packets {
             type uint32;
           }
           leaf jb-overrun {
             type uint32;
           }
           leaf jb-underrun {
             type uint32;
           }
         }
       }
       list smart-sfp-channel-defects {
         key "defect-channel-num";
         description
           "Smart SFP channel Defects";
         leaf defect-channel-num {
           type uint32;
           description
             "Channel number ";
         }
         leaf sfp-channel-defects {
           type string;
         }
         leaf channel-not-applicable {
           type string;
           description
             "Channelization are not supported";
         }
       }
       container ethernet-mac-pfc-statistics {
         description
           "Ethernet MAC Priority Flow control Statistics";
         leaf mac-pfc-dot1p {
           type int32;
         }
         leaf input-mac-pfc-frames {
           type int32;
         }
         leaf output-mac-pfc-frames {
           type int32;
         }
       }
       container ethernet-pfcwd-statistics {
         description
           "Ethernet MAC Priority Flow control Watchdog Statistics";
         leaf queue-number {
           type uint32;
           description
             "Queue number";
         }
         leaf detected {
           type int32;
         }
         leaf recovered {
           type int32;
         }
         leaf last-count {
           type int32;
         }
         leaf total-count {
           type int32;
         }
       }
       container cos-information {
         description
           "Information about class-of-service configuration";
         list cos-stream-information {
           description
             "Information about the traffic stream";
         }
         container cos-forwarding-class-information {
           container fc-map {
             description
               "Class-of-service forwarding class to queue mapping";
             list fc-map-item {
               leaf fc-name {
                 type string;
                 description
                   "Class-of-service forwarding class name";
               }
               leaf fc-number {
                 type uint32;
                 description
                   "Identifier for Class-of-service forwarding class";
               }
               leaf fc-queue-number {
                 type uint32;
                 description
                   "Class-of-service forwarding class queue number";
               }
               leaf fc-rqueue-number {
                 type uint32;
                 description
                   "Class-of-service forwarding class restricted queue 
                   number";
               }
               leaf fc-priority {
                 type string;
                 description
                   "Class-of-service forwarding class queue priority";
               }
               leaf fc-policing-priority {
                 type string;
                 description
                   "Class-of-service forwarding class policing priority";
               }
               leaf fc-spu-priority {
                 type string;
                 description
                   "Class-of-service forwarding class spu priority";
               }
               leaf fc-no-loss {
                 type string;
                 description
                   "Class-of-service forwarding class no-loss";
               }
               leaf fc-pfc-priority {
                 type string;
                 description
                   "Class-of-service forwarding class pfc-priority";
               }
               leaf fc-multicast {
                 type string;
                 description
                   "Class-of-service forwarding class multicast";
               }
               leaf fc-latency-ecn {
                 type string;
                 description
                   "Class-of-service forwarding class latency ECN";
               }
             }
           }
         }
         container cos-forwarding-class-map-information {
           container fc-map {
             description
               "Class-of-service forwarding class to queue mapping";
             list fc-map-item {
               leaf fc-name {
                 type string;
                 description
                   "Class-of-service forwarding class name";
               }
               leaf fc-number {
                 type uint32;
                 description
                   "Identifier for Class-of-service forwarding class";
               }
               leaf fc-queue-number {
                 type uint32;
                 description
                   "Class-of-service forwarding class queue number";
               }
               leaf fc-rqueue-number {
                 type uint32;
                 description
                   "Class-of-service forwarding class restricted queue 
                   number";
               }
               leaf fc-priority {
                 type string;
                 description
                   "Class-of-service forwarding class queue priority";
               }
               leaf fc-policing-priority {
                 type string;
                 description
                   "Class-of-service forwarding class policing priority";
               }
               leaf fc-spu-priority {
                 type string;
                 description
                   "Class-of-service forwarding class spu priority";
               }
               leaf fc-no-loss {
                 type string;
                 description
                   "Class-of-service forwarding class no-loss";
               }
               leaf fc-pfc-priority {
                 type string;
                 description
                   "Class-of-service forwarding class pfc-priority";
               }
               leaf fc-multicast {
                 type string;
                 description
                   "Class-of-service forwarding class multicast";
               }
               leaf fc-latency-ecn {
                 type string;
                 description
                   "Class-of-service forwarding class latency ECN";
               }
             }
           }
         }
         container cos-classifier-information {
           list classifier {
             description
               "Class-of-service code point classifier";
             leaf classifier-name {
               type string;
               description
                 "Class-of-service classifier name";
             }
             leaf code-point-type {
               type string;
               description
                 "Class-of-service code point type";
             }
             leaf table-index {
               type uint32;
               description
                 "Table index";
             }
             container classifier-map {
               list classifier-map-item {
                 leaf code-point {
                   type string;
                   description
                     "Class-of-service code point alias name or bits";
                 }
                 leaf fc-name {
                   type string;
                   description
                     "Class-of-service forwarding class name";
                 }
                 leaf loss-priority {
                   type string;
                   description
                     "Class-of-service loss priority";
                 }
                 leaf cntag-present {
                   type string;
                   description
                     "Class-of-service cntag present";
                 }
               }
             }
           }
         }
         container cos-loss-priority-map-information {
           list loss-priority-map {
             description
               "Class-of-service code point loss priority map";
             leaf loss-priority-map-name {
               type string;
               description
                 "Name of class-of-service loss priority map";
             }
             leaf code-point-type {
               type string;
               description
                 "Class-of-service code point type";
             }
             leaf table-index {
               type uint32;
               description
                 "Table index";
             }
             list loss-priority-map-table {
               list loss-priority-map-item {
                 leaf code-point {
                   type string;
                   description
                     "Class-of-service code point alias name or bits";
                 }
                 leaf loss-priority {
                   type string;
                   description
                     "Class-of-service loss priority";
                 }
               }
               list loss-priority-map-table-entry {
                 leaf table-index {
                   type uint32;
                   description
                     "Table index";
                 }
                 leaf code-point {
                   type string;
                   description
                     "Class-of-service code point alias name or bits";
                 }
                 leaf loss-priority {
                   type string;
                   description
                     "Class-of-service loss priority";
                 }
               }
             }
           }
         }
         container cos-drop-profile-information {
           list drop-profile {
             description
               "Class-of-service drop profile";
             leaf profile-name {
               type string;
               description
                 "Class-of-service drop profile name";
             }
             leaf profile-type {
               type string;
               description
                 "Class-of-service drop profile type";
             }
             leaf table-index {
               type uint32;
               description
                 "Table index";
             }
             container profile-map {
               list profile-map-item {
                 leaf fill-level {
                   type uint32;
                   description
                     "Class-of-service drop profile fill level value";
                 }
                 leaf probability {
                   type uint32;
                   description
                     "Class-of-service drop profile probability value";
                 }
               }
             }
           }
         }
         container cos-mpls-ecn-map-information {
           list cos-mpls-ecn-map-info {
             description
               "Class-of-service mpls-ecn-map information";
             leaf ecn-capable-exp {
               type int32;
               description
                 "ECN capable exp";
             }
             leaf congestion-experienced-exp {
               type int32;
               description
                 "Congestion Expereienced exp";
             }
           }
         }
         container cos-monitoring-profile-information {
           list monitoring-profile {
             description
               "Class-of-service monitoring profile";
             leaf monitoring-profile-name {
               type string;
               description
                 "Class-of-service monitoring profile name";
             }
             container export-filters {
               container export-filter {
                 leaf filter-name {
                   type string;
                   description
                     "Class-of-service monitoring profile filter name";
                 }
                 leaf monitoring-queue-number {
                   type uint32;
                   description
                     "Class-of-service monitoring profile filter queue value";
                 }
                 leaf peak-queue-length-value {
                   type uint32;
                   description
                     "Class-of-service monitoring profile peak queue length 
                     value";
                 }
               }
             }
           }
         }
         container cos-rewrite-information {
           list rewrite {
             description
               "Class-of-service drop profile";
             leaf rewrite-name {
               type string;
               description
                 "Class-of-service rewrite rule name";
             }
             leaf code-point-type {
               type string;
               description
                 "Class-of-service code point type";
             }
             leaf table-index {
               type uint32;
               description
                 "Table index";
             }
             container rewrite-map {
               list rewrite-map-item {
                 leaf fc-name {
                   type string;
                   description
                     "Class-of-service forwarding class name";
                 }
                 leaf loss-priority {
                   type string;
                   description
                     "Class-of-service loss priority";
                 }
                 leaf code-point {
                   type string;
                   description
                     "Class-of-service code point alias name or bits";
                 }
               }
             }
           }
         }
         container cos-loss-priority-rewrite-information {
           list loss-priority-rewrite {
             description
               "Class-of-service loss priority to code point rewrite";
             leaf loss-priority-rewrite-name {
               type string;
               description
                 "Name of class-of-service loss priority rewrite";
             }
             leaf code-point-type {
               type string;
               description
                 "Class-of-service code point type";
             }
             leaf table-index {
               type uint32;
               description
                 "Table index";
             }
             list loss-priority-rewrite-table {
               list loss-priority-rewrite-item {
                 leaf loss-priority {
                   type string;
                   description
                     "Class-of-service loss priority";
                 }
                 leaf code-point {
                   type string;
                   description
                     "Class-of-service code point alias name or bits";
                 }
               }
               list loss-priority-rewrite-table-entry {
                 leaf table-index {
                   type uint32;
                   description
                     "Table index";
                 }
                 leaf loss-priority {
                   type string;
                   description
                     "Class-of-service loss priority";
                 }
                 leaf code-point {
                   type string;
                   description
                     "Class-of-service code point alias name or bits";
                 }
               }
             }
           }
         }
         container cos-code-point-map-information {
           list code-point-map {
             description
               "Class-of-service code point alias map";
             leaf code-point-type {
               type string;
               description
                 "Class-of-service code point type";
             }
             container alias-map {
               list alias-map-item {
                 leaf code-point-alias {
                   type string;
                   description
                     "Class-of-service code point alias name";
                 }
                 leaf code-point-bits {
                   type string;
                   description
                     "Class-of-service code point bit sequence";
                 }
               }
             }
           }
         }
         container cos-fragmentation-map-information {
           list fragmentation-map {
             description
               "Class-of-service fragmentation map";
             leaf fragmentation-map-name {
               type string;
               description
                 "Class-of-service fragmentation map name";
             }
             leaf fragmentation-map-index {
               type uint32;
               description
                 "Index number for Class-of-service fragmentation map";
             }
             list fragment-map {
               leaf fc-name {
                 type string;
                 description
                   "Class-of-service forwarding class name";
               }
               leaf no-fragmentation {
                 type empty;
                 description
                   "Do not fragment packets of this class";
               }
               leaf fragment-threshold {
                 type string;
                 description
                   "Fragmentation threshold";
               }
               leaf fragment-multilink-class {
                 type int32;
                 description
                   "Identifier for multilink class";
               }
             }
           }
         }
         container cos-translation-table-map-information {
           list translation-table {
             description
               "Class-of-service code point translation table";
             leaf translation-table-name {
               type string;
               description
                 "Class-of-service translation table name";
             }
             leaf translation-table-type {
               type string;
               description
                 "Class-of-service translation table type";
             }
             leaf table-index {
               type uint32;
               description
                 "Table index";
             }
             container translation-table-map {
               container translation-table-map-item {
                 leaf from-code-point {
                   type string;
                   description
                     "Class-of-service code point alias name or bits";
                 }
                 leaf to-code-point {
                   type string;
                   description
                     "Class-of-service code point alias name or bits";
                 }
               }
             }
             list translation-table-entry {
               leaf table-index {
                 type uint32;
                 description
                   "Table index";
               }
               leaf from-code-point {
                 type string;
                 description
                   "Class-of-service code point alias name or bits";
               }
               leaf to-code-point {
                 type string;
                 description
                   "Class-of-service code point alias name or bits";
               }
             }
           }
         }
         container cos-multi-destination-information {
           container sm-md-map {
             leaf scheduler-map-name {
               type string;
               description
                 "Class-of-service scheduler map name";
             }
             leaf scheduler-map-index {
               type uint64;
               description
                 "Class-of-service scheduler map index";
             }
           }
           container fc-md-map {
             leaf fc-name {
               type string;
               description
                 "Class-of-service forwarding class name";
             }
             leaf fc-queue-number {
               type uint32;
               description
                 "Class-of-service forwarding class queue number";
             }
           }
           container cls-md-map {
             leaf multidest-classifier-name {
               type string;
               description
                 "Multi destination classifier name";
             }
             leaf multidest-classifier-type {
               type string;
               description
                 "Multi destination classifier type";
             }
             leaf multidest-classifier-index {
               type uint32;
               description
                 "Multi destination classifier id";
             }
           }
         }
         container cos-forwarding-class-set-information {
           list forwarding-class-set {
             description
               "Class-of-service forwarding class set information";
             list forwarding-class-set-entry {
               leaf forwarding-class-set-name {
                 type string;
                 description
                   "Class-of-service forwarding class set name";
               }
               leaf forwarding-class-set-type {
                 type string;
                 description
                   "Identifier for Class-of-service forwarding class set 
                   type";
               }
               leaf forwarding-class-set-index {
                 type uint32;
                 description
                   "Identifier for Class-of-service forwarding class set";
               }
               container fc-map {
                 description
                   "Class-of-service forwarding class to queue mapping";
                 list fc-map-item {
                   leaf fc-name {
                     type string;
                     description
                       "Class-of-service forwarding class name";
                   }
                   leaf fc-number {
                     type uint32;
                     description
                       "Identifier for Class-of-service forwarding class";
                   }
                   leaf fc-queue-number {
                     type uint32;
                     description
                       "Class-of-service forwarding class queue number";
                   }
                   leaf fc-rqueue-number {
                     type uint32;
                     description
                       "Class-of-service forwarding class restricted queue 
                       number";
                   }
                   leaf fc-priority {
                     type string;
                     description
                       "Class-of-service forwarding class queue priority";
                   }
                   leaf fc-policing-priority {
                     type string;
                     description
                       "Class-of-service forwarding class policing priority";
                   }
                   leaf fc-spu-priority {
                     type string;
                     description
                       "Class-of-service forwarding class spu priority";
                   }
                   leaf fc-no-loss {
                     type string;
                     description
                       "Class-of-service forwarding class no-loss";
                   }
                   leaf fc-pfc-priority {
                     type string;
                     description
                       "Class-of-service forwarding class pfc-priority";
                   }
                   leaf fc-multicast {
                     type string;
                     description
                       "Class-of-service forwarding class multicast";
                   }
                   leaf fc-latency-ecn {
                     type string;
                     description
                       "Class-of-service forwarding class latency ECN";
                   }
                 }
               }
             }
           }
         }
         container cos-policy-map-information {
           list policy-map {
             description
               "Class-of-service Policy-map";
             leaf policy-map-name {
               type string;
               description
                 "Class-of-service Policy-map name";
             }
             leaf table-index {
               type uint32;
               description
                 "Table index";
             }
             leaf policy-map-user-attribute {
               type uint32;
               description
                 "User-defined attribute";
             }
             container policy-map-cp-entries {
               leaf code-point-type {
                 type string;
                 description
                   "Class-of-service code point type";
               }
               leaf code-point {
                 type string;
                 description
                   "Class-of-service code point alias name or bits";
               }
               leaf code-point-option {
                 type string;
                 description
                   "Class-of-service code point option flag";
               }
             }
           }
         }
         container cos-client-info {
           list cos-client {
             description
               "Class-of-service Junos client information";
             leaf cos-client-info-internal-id {
               type uint32;
               description
                 "Junos client internal identifier";
             }
             leaf cos-client-info-requests {
               type uint32;
               description
                 "Number of requests from Junos client";
             }
             leaf cos-client-info-responses {
               type uint32;
               description
                 "Number of responses to Junos client";
             }
             leaf cos-client-info-failures {
               type uint32;
               description
                 "Number of failures while handling Junos client requests";
             }
             leaf cos-client-info-identifier {
               type string;
               description
                 "Junos client identifier";
             }
             leaf cos-client-name {
               type string;
               description
                 "Junos client name";
             }
             leaf cos-client-state {
               type string;
               description
                 "Junos client state information";
             }
             leaf cos-client-internal-name {
               type string;
               description
                 "Junos client internal name";
             }
             leaf cos-client-stats {
               type string;
               description
                 "Junos client statistics";
             }
             leaf cos-client-failure-stats {
               type string;
               description
                 "Junos client failure/error statistics";
             }
             leaf cos-client-validate-failures {
               type uint32;
               description
                 "Junos client request validation failures";
             }
             leaf cos-client-ownership-failures {
               type uint32;
               description
                 "Junos client ownership validation failures";
             }
             leaf cos-client-info-name {
               type string;
               description
                 "CoS client name";
             }
             leaf cos-client-internal-id {
               type uint32;
               description
                 "Junos client internal identifier";
             }
             leaf cos-client-requests {
               type uint64;
               description
                 "Number of requests from Junos client";
             }
             leaf cos-client-responses {
               type uint64;
               description
                 "Number of responses to Junos client";
             }
             leaf cos-client-failures {
               type uint64;
               description
                 "Number of failures while handling Junos client requests";
             }
             leaf cos-client-identifier {
               type string;
               description
                 "Junos client identifier";
             }
             leaf cos-client-status {
               type string;
               description
                 "Junos client status";
             }
             leaf cos-client-connected-time {
               type string;
               description
                 "Junos client time of connect";
             }
             leaf cos-client-reconnected-time {
               type string;
               description
                 "Junos client time of reconnect";
             }
             leaf cos-client-disconnected-time {
               type string;
               description
                 "Junos client time of disconnect";
             }
             leaf cos-client-message-type {
               type string;
               description
                 "Junos client message type";
             }
             leaf cos-client-operation-type {
               type string;
               description
                 "Junos client operation type";
             }
             leaf-list cos-bind-point-type {
               type string;
               description
                 "Class-of-service bind point type";
             }
             leaf-list cos-bind-point-owner-type {
               type string;
               description
                 "Class-of-service bind point owner type";
             }
             leaf-list cos-bind-point-owner-internal-id {
               type uint32;
               description
                 "Junos client internal identifier";
             }
             leaf-list cos-bind-point-name {
               type string;
               description
                 "Class-of-service bind point name";
             }
             leaf cos-bind-point-feature {
               type string;
               description
                 "Class-of-service bind point feature name";
             }
             leaf cos-bind-point-feature-object-name {
               type string;
               description
                 "Class-of-service bind point feature object name";
             }
           }
         }
         container cos-host-outbound-info {
           list cos-host-outbound-traffic-info {
             description
               "Class-of-service host-outbound-traffic information";
             leaf cos-host-outbound-traffic-protocol-name {
               type string;
               description
                 "CoS host outbound traffic protocol name";
             }
             leaf cos-host-outbound-traffic-dscp {
               type string;
               description
                 "CoS host outbound traffic dscp";
             }
             leaf cos-host-outbound-traffic-dot1p {
               type string;
               description
                 "CoS host outbound traffic ieee 802.1p";
             }
             leaf cos-host-outbound-traffic-fc-id {
               type string;
               description
                 "CoS host outbound traffic forwarding class id";
             }
             leaf cos-host-outbound-traffic-queue-id {
               type string;
               description
                 "CoS host outbound traffic queue id";
             }
             leaf cos-host-outbound-traffic-restrict-queue-id {
               type string;
               description
                 "CoS host outbound traffic restrict queue id";
             }
             leaf cos-host-outbound-traffic-override-firewall {
               type string;
               description
                 "CoS host outbound traffic override firwall action";
             }
             leaf cos-host-outbound-traffic-rw-dot1p {
               type string;
               description
                 "CoS host outbound traffic - use ieee 802.1p rewrite rules";
             }
           }
         }
         container cos-drop-congestion-notification-information {
           list cos-drop-congestion-notification-info {
             description
               "Class-of-service drop-congestion-notification information";
             leaf cos-dcn-fc-name {
               type string;
               description
                 "Cos DCN forwarding class";
             }
             leaf cos-dcn-udp-port {
               type int32;
               description
                 "Cos DCN udp port number";
             }
           }
           container cos-drop-congestion-notification-dscp-map {
             list cos-drop-congestion-notification-dscp-map-item {
               leaf trimmable-dscp {
                 type uint32;
                 description
                   "Trimmable DSCP code-point";
               }
               leaf trimmed-dscp {
                 type uint32;
                 description
                   "Trimmed DSCP code-point";
               }
             }
           }
         }
         container cos-dedicated-buffer-profile-information {
           list dedicated-buffer-profile {
             description
               "Class-of-service dedicated buffer profile";
             leaf dedicated-buffer-profile-name {
               type string;
               description
                 "Class-of-service dedicated buffer profile name";
             }
             leaf dedicated-buffer-profile-index {
               type int32;
               description
                 "Class-of-service dedicated buffer profile index";
             }
             leaf ingress-buffer-size {
               type string;
               description
                 "Ingress per port dedicated buffer in cells";
             }
             leaf egress-buffer-size {
               type string;
               description
                 "Egress per port dedicated buffer in cells";
             }
           }
         }
         container cos-dynamic-threshold-profile-information {
           list dynamic-threshold-profile {
             key "dynamic-threshold-profile-name";
             description
               "Class-of-service dynamic threshold profile";
             leaf dynamic-threshold-profile-name {
               type string;
               description
                 "Class-of-service dynamic threshold profile name";
             }
             leaf dynamic-threshold-profile-index {
               type uint64;
               description
                 "Class-of-service dynamic threshold profile index";
             }
             list dynamic-threshold-profile-entry {
               key "dynamic-threshold-profile-priority-group";
               description
                 "Class-of-service dynamic threshold profile entry";
               leaf dynamic-threshold-profile-priority-group {
                 type string;
                 description
                   "Class-of-service dynamic threshold profile priority 
                   group";
               }
               leaf dynamic-threshold-profile-threshold-value {
                 type uint32;
                 description
                   "Class-of-service dynamic threshold profile threshold 
                   value";
               }
             }
           }
         }
         container cos-decn-profile-information {
           list decn-profile {
             description
               "Class-of-service decn profile";
             leaf decn-profile-name {
               type string;
               description
                 "Class-of-service decn profile name";
             }
             leaf decn-profile-index {
               type uint64;
               description
                 "Class-of-service decn profile index";
             }
             list decn-profile-queue {
               description
                 "Class-of-service decn profile queue";
               leaf dynamic-explicit-congestion-notification-queue {
                 type uint32;
                 description
                   "Class-of-service DECN queue";
               }
               leaf dynamic-explicit-congestion-notification-offset {
                 type uint32;
                 description
                   "Class-of-service DECN offset";
               }
               leaf dynamic-explicit-congestion-notification-floor {
                 type uint32;
                 description
                   "Class-of-service DECN floor";
               }
             }
           }
         }
         container cos-scheduler-map-information {
           list scheduler-map {
             description
               "Class-of-service scheduler map";
             leaf scheduler-map-name {
               type string;
               description
                 "Class-of-service scheduler map name";
             }
             leaf scheduler-map-index {
               type uint64;
               description
                 "Class-of-service scheduler map index";
             }
             leaf user-plane-name {
               type string;
               description
                 "Class-of-service user-plane name for XDA";
             }
             list scheduler {
               leaf scheduler-name {
                 type string;
                 description
                   "Class-of-service scheduler name";
               }
               leaf fc-name {
                 type string;
                 description
                   "Class-of-service forwarding class name";
               }
               leaf scheduler-index {
                 type uint64;
                 description
                   "Class of service scheduler index";
               }
               leaf scheduler-tx-rate {
                 type string;
                 description
                   "Class-of-service scheduler transmit rate";
               }
               leaf scheduler-tx-limit {
                 type string;
                 description
                   "Class-of-service scheduler transmit limit";
               }
               leaf scheduler-buffer-size {
                 type string;
                 description
                   "Class-of-service scheduler buffer size";
               }
               leaf scheduler-buffer-multicast-share {
                 type uint32;
                 description
                   "Class-of-service scheduler multicast buffer share";
               }
               leaf scheduler-buffer-limit {
                 type string;
                 description
                   "Class-of-service scheduler buffer limit";
               }
               leaf scheduler-buffer-rate {
                 type string;
                 description
                   "Class-of-service scheduler buffer rate";
               }
               leaf scheduler-shared-buffer-maximum-percentage {
                 type uint32;
                 description
                   "Shared Buffer maximum percentage";
               }
               leaf scheduler-shared-buffer-multicast-maximum-percentage {
                 type uint32;
                 description
                   "Shared Buffer multicast maximum percentage";
               }
               leaf scheduler-buffer-dynamic-threshold {
                 type uint32;
                 description
                   "Queue shared-buffer dynamic threshold";
               }
               leaf scheduler-priority {
                 type string;
                 description
                   "Class-of-service scheduler priority";
               }
               leaf scheduler-shaping-rate {
                 type string;
                 description
                   "Class-of-service scheduler shaping rate";
               }
               leaf scheduler-shaping-rate-burst {
                 type string;
                 description
                   "Class-of-service scheduler shaping rate burst";
               }
               leaf scheduler-adjust-minimum {
                 type int32;
                 description
                   "Class-of-service scheduler adjustment minimum rate";
               }
               leaf scheduler-adjust-percent {
                 type int32;
                 description
                   "Class-of-service scheduler percent adjustment for a 
                   queue";
               }
               leaf scheduler-excess-priority {
                 type string;
                 description
                   "Class-of-service scheduler excess priority";
               }
               leaf scheduler-excess-rate {
                 type string;
                 description
                   "Class-of-service scheduler excess rate";
               }
               leaf scheduler-explicit-congestion-notification {
                 type string;
                 description
                   "Class-of-service ECN status of queue";
               }
               leaf scheduler-ecn-rtlog-rate-limit {
                 type uint32;
                 description
                   "Class-of-service ECN Security Log Rate Limit";
               }
               leaf scheduler-ecn-no-pfc-assist {
                 type string;
                 description
                   "Class-of-service ECN no pfc assist";
               }
               leaf scheduler-latency-ecn {
                 type string;
                 description
                   "Latency based ECN";
               }
               leaf scheduler-latency-ecn-threshold {
                 type uint32;
                 description
                   "Latency threshold";
               }
               leaf scheduler-queue-monitoring {
                 type string;
                 description
                   "Class-of-service queue depth monitoring of queue";
               }
               leaf scheduler-drop-profile-ln-index {
                 type uint32;
                 description
                   "Class-of-service scheduler drop profile index low, 
                   non-TCP";
               }
               leaf scheduler-drop-profile-ln {
                 type string;
                 description
                   "Class-of-service scheduler drop profile low, non-TCP";
               }
               leaf scheduler-drop-profile-lt-index {
                 type uint32;
                 description
                   "Class-of-service scheduler drop profile index low, TCP";
               }
               leaf scheduler-drop-profile-lt {
                 type string;
                 description
                   "Class-of-service scheduler drop profile low, TCP";
               }
               leaf scheduler-drop-profile-hn-index {
                 type uint32;
                 description
                   "Class-of-service scheduler drop profile index high, 
                   non-TCP";
               }
               leaf scheduler-drop-profile-hn {
                 type string;
                 description
                   "Class-of-service scheduler drop profile high, non-TCP";
               }
               leaf scheduler-drop-profile-ht-index {
                 type uint32;
                 description
                   "Class-of-service scheduler drop profile index high, TCP";
               }
               leaf scheduler-drop-profile-ht {
                 type string;
                 description
                   "Class-of-service scheduler drop profile high, TCP";
               }
               leaf scheduler-drop-profile-la-index {
                 type uint32;
                 description
                   "Class-of-service scheduler drop profile index low";
               }
               leaf scheduler-drop-profile-la {
                 type string;
                 description
                   "Class-of-service scheduler drop profile low";
               }
               leaf scheduler-drop-profile-ma-index {
                 type uint32;
                 description
                   "Class-of-service scheduler drop profile index medium";
               }
               leaf scheduler-drop-profile-ma {
                 type string;
                 description
                   "Class-of-service scheduler drop profile medium";
               }
               leaf scheduler-drop-profile-mla-index {
                 type uint32;
                 description
                   "Class-of-service scheduler drop profile index medium-low";
               }
               leaf scheduler-drop-profile-mla {
                 type string;
                 description
                   "Class-of-service scheduler drop profile medium-low";
               }
               leaf scheduler-drop-profile-mha-index {
                 type uint32;
                 description
                   "Class-of-service scheduler drop profile index 
                   medium-high";
               }
               leaf scheduler-drop-profile-mha {
                 type string;
                 description
                   "Class-of-service scheduler drop profile medium-high";
               }
               leaf scheduler-drop-profile-ha-index {
                 type uint32;
                 description
                   "Class-of-service scheduler drop profile index high";
               }
               leaf scheduler-drop-profile-ha {
                 type string;
                 description
                   "Class-of-service scheduler drop profile high";
               }
             }
           }
         }
         container cos-traffic-control-profile-information {
           list traffic-control-profile {
             description
               "Information about one or more traffic control profiles";
             leaf traffic-control-profile-name {
               type string;
               description
                 "Class-of-service traffic control profile name";
             }
             leaf traffic-control-profile-index {
               type uint64;
               description
                 "Index number for Class-of-service traffic control profile";
             }
             leaf user-plane-name {
               type string;
               description
                 "Class-of-service user-plane name for XDA";
             }
             leaf scheduler-map-name {
               type string;
               description
                 "Class-of-service scheduler map name";
             }
             leaf atm-service {
               type string;
               description
                 "Class-of-service traffic control profile atm service";
             }
             leaf shaping-rate {
               type uint64;
               description
                 "Class-of-service shaping rate";
             }
             leaf shaping-rate-burst {
               type uint32;
               description
                 "Class-of-service shaping rate burst, in bytes";
             }
             leaf low-granularity {
               type uint32;
               description
                 "Class-of-service low-granularity mode support";
             }
             leaf queue-mode-4q {
               type uint32;
               description
                 "Class-of-service tcp-voq-mode(4Q) mode support";
             }
             leaf shaping-rate-priority-strict-high {
               type uint64;
               description
                 "Class-of-service shaping rate for priority strict high";
             }
             leaf shaping-rate-priority-strict-high-burst {
               type uint32;
               description
                 "Class-of-service shaping rate burst for priority 
                 strict-high";
             }
             leaf shaping-rate-priority-high {
               type uint64;
               description
                 "Class-of-service shaping rate for priority high";
             }
             leaf shaping-rate-priority-high-burst {
               type uint32;
               description
                 "Class-of-service shaping rate for priority high burst";
             }
             leaf shaping-rate-priority-medium {
               type uint64;
               description
                 "Class-of-service shaping rate for priority medium";
             }
             leaf shaping-rate-priority-medium-burst {
               type uint32;
               description
                 "Class-of-service shaping rate for priority medium burst";
             }
             leaf shaping-rate-priority-medium-low {
               type uint64;
               description
                 "Class-of-service shaping rate for priority medium-low";
             }
             leaf shaping-rate-priority-medium-low-burst {
               type uint32;
               description
                 "Class-of-service shaping rate burst for priority 
                 medium-low";
             }
             leaf shaping-rate-priority-low {
               type uint64;
               description
                 "Class-of-service shaping rate for priority low";
             }
             leaf shaping-rate-priority-low-burst {
               type uint32;
               description
                 "Class-of-service shaping rate for priority low burst";
             }
             leaf shaping-rate-excess-high {
               type uint64;
               description
                 "Class-of-service shaping rate for excess high";
             }
             leaf shaping-rate-excess-high-burst {
               type uint32;
               description
                 "Class-of-service shaping rate for excess high burst";
             }
             leaf shaping-rate-excess-medium-high {
               type uint64;
               description
                 "Class-of-service shaping rate for excess medium-high";
             }
             leaf shaping-rate-excess-medium-high-burst {
               type uint32;
               description
                 "Class-of-service shaping rate burst for excess medium-high";
             }
             leaf shaping-rate-excess-medium-low {
               type uint64;
               description
                 "Class-of-service shaping rate for excess medium-low";
             }
             leaf shaping-rate-excess-medium-low-burst {
               type uint32;
               description
                 "Class-of-service shaping rate burst for excess medium-low";
             }
             leaf shaping-rate-excess-low {
               type uint64;
               description
                 "Class-of-service shaping rate for excess low";
             }
             leaf shaping-rate-excess-low-burst {
               type uint32;
               description
                 "Class-of-service shaping rate for excess low burst";
             }
             leaf guaranteed-rate {
               type uint64;
               description
                 "Class-of-service guaranteed rate";
             }
             leaf guaranteed-rate-burst {
               type uint32;
               description
                 "Class-of-service guaranteed rate burst, in bytes";
             }
             leaf delay-buffer-rate {
               type uint64;
               description
                 "Class-of-service delay buffer rate";
             }
             leaf excess-rate {
               type uint32;
               description
                 "Class-of-service excess rate";
             }
             leaf excess-rate-high {
               type uint32;
               description
                 "Class-of-service excess rate for excess-high priority 
                 traffic";
             }
             leaf excess-rate-medium-high {
               type uint32;
               description
                 "Class-of-service excess rate for excess-medium-high 
                 priority traffic";
             }
             leaf excess-rate-medium-low {
               type uint32;
               description
                 "Class-of-service excess rate for excess-medium-low 
                 priority traffic";
             }
             leaf excess-rate-low {
               type uint32;
               description
                 "Class-of-service excess rate for excess-low priority 
                 traffic";
             }
             leaf adjust-minimum {
               type uint64;
               description
                 "Class-of-service adjustment minimum rate";
             }
             leaf overhead-bytes {
               type int32;
               description
                 "Class-of-service Overhead bytes";
             }
             leaf frame-mode-bytes {
               type int32;
               description
                 "Class-of-service overhead bytes when in frame-mode";
             }
             leaf cell-mode-bytes {
               type int32;
               description
                 "Class-of-service overhead bytes when in cell-mode";
             }
             leaf overhead-accounting-mode {
               type string;
               description
                 "Class-of-service Overhead Accounting Mode";
             }
             list traffic-control-profile-instance {
               description
                 "Class-of-service traffic control profile instance";
               leaf traffic-control-profile-instance-name {
                 type string;
                 description
                   "Class-of-service traffic control profile instance";
               }
               leaf traffic-control-profile-instance-index {
                 type uint32;
                 description
                   "Index number for Class-of-service traffic control 
                   profile instance";
               }
               leaf instance-reference-count {
                 type uint32;
                 description
                   "Instance reference count";
               }
             }
           }
         }
         container cos-routing-instance-information {
           list routing-instance-map {
             description
               "Mapping between class-of-service objects and routing 
               instances";
             leaf routing-instance-name {
               type string;
               description
                 "Name of class-of-service routing instance";
             }
             list i-logical-map {
               leaf i-logical-name {
                 type string;
                 description
                   "Class-of-service logical interface name";
               }
               leaf i-logical-index {
                 type uint32;
                 description
                   "Class-of-service logical interface index";
               }
               leaf monitoring-profile-map-name {
                 type string;
                 description
                   "Monitoring Profile Name";
               }
               list cos-objects {
                 description
                   "Class-of-service object  mappings";
                 leaf cos-object-type {
                   type string;
                   description
                     "Class-of-service object type";
                 }
                 leaf cos-object-name {
                   type string;
                   description
                     "Class-of-service object name";
                 }
                 leaf cos-object-subtype {
                   type string;
                   description
                     "Class-of-service object subtype";
                 }
                 leaf cos-object-index {
                   type uint64;
                   description
                     "Class-of-service object index";
                 }
               }
             }
           }
         }
         container cos-fabric-scheduler-map-information {
           container fabric-scheduler-map {
             list fabric-scheduler {
               leaf fabric-scheduler-name {
                 type string;
                 description
                   "Class-of-service scheduler name";
               }
               leaf fabric-scheduler-index {
                 type uint32;
                 description
                   "Class of service scheduler index";
               }
               leaf fabric-scheduler-drop-profile-ln-index {
                 type uint32;
                 description
                   "Class-of-service scheduler drop profile index low, 
                   non-TCP";
               }
               leaf fabric-scheduler-drop-profile-ln {
                 type string;
                 description
                   "Class-of-service scheduler drop profile low, non-TCP";
               }
               leaf fabric-scheduler-drop-profile-lt-index {
                 type uint32;
                 description
                   "Class-of-service scheduler drop profile index low, TCP";
               }
               leaf fabric-scheduler-drop-profile-lt {
                 type string;
                 description
                   "Class-of-service scheduler drop profile low, TCP";
               }
               leaf fabric-scheduler-drop-profile-hn-index {
                 type uint32;
                 description
                   "Class-of-service scheduler drop profile index high, 
                   non-TCP";
               }
               leaf fabric-scheduler-drop-profile-hn {
                 type string;
                 description
                   "Class-of-service scheduler drop profile high, non-TCP";
               }
               leaf fabric-scheduler-drop-profile-ht-index {
                 type uint32;
                 description
                   "Class-of-service scheduler drop profile index high, TCP";
               }
               leaf fabric-scheduler-drop-profile-ht {
                 type string;
                 description
                   "Class-of-service scheduler drop profile high, TCP";
               }
               leaf fabric-scheduler-priority {
                 type string;
               }
             }
           }
         }
         container cos-tcm-information {
           list tcm {
             description
               "Class-of-service traffic-class-map";
             leaf tcm-name {
               type string;
               description
                 "Class-of-service traffic-class-map name";
             }
             leaf tcm-type {
               type string;
               description
                 "Class-of-service traffic-class-map type";
             }
             leaf table-index {
               type uint32;
               description
                 "Table index";
             }
             container tcm-map {
               list tcm-map-item {
                 leaf code-point {
                   type string;
                   description
                     "Class-of-service code point alias name or bits";
                 }
                 leaf tc-name {
                   type string;
                   description
                     "Class-of-service traffic-class-map traffic-class name";
                 }
               }
             }
           }
         }
         container cos-lecn-profile-information {
           list lecn-profile {
             description
               "Class-of-service lecn profile";
             leaf lecn-profile-name {
               type string;
               description
                 "Class-of-service lecn profile name";
             }
             leaf lecn-profile-index {
               type uint64;
               description
                 "Class-of-service lecn profile index";
             }
             list lecn-profile-queue {
               description
                 "Class-of-service lecn profile queue";
               leaf latency-explicit-congestion-notification-queue {
                 type uint32;
                 description
                   "Class-of-service LECN queue";
               }
               leaf latency-explicit-congestion-notification-latency {
                 type uint32;
                 description
                   "Class-of-service LECN latency";
               }
             }
           }
         }
       }
       container physical-interface-cos-information {
         description
           "Physical interface class-of-service parameters";
       }
       container precl-statistics {
         description
           "Preclassifier Statistics ";
         container precl-information {
           description
             "Preclassifier Statistics";
         }
       }
       container mlfr-uni-nni-traffic-statistics {
         container bundle {
         }
       }
       container lag-traffic-statistics {
         container lag-multicast-statistics {
           leaf lag-multicast-statistics-header {
             type empty;
           }
           container lag-ipv4-multicast-statistics {
             leaf input-packets {
               type uint64;
             }
             leaf input-pps {
               type int32;
             }
             leaf input-bytes {
               type int32;
             }
             leaf input-bps {
               type int32;
             }
             leaf output-packets {
               type uint64;
             }
             leaf output-pps {
               type int32;
             }
             leaf output-bytes {
               type int32;
             }
             leaf output-bps {
               type int32;
             }
           }
           container lag-ipv6-multicast-statistics {
             leaf input-packets {
               type uint64;
             }
             leaf input-pps {
               type int32;
             }
             leaf input-bytes {
               type int32;
             }
             leaf input-bps {
               type int32;
             }
             leaf output-packets {
               type uint64;
             }
             leaf output-pps {
               type int32;
             }
             leaf output-bytes {
               type int32;
             }
             leaf output-bps {
               type int32;
             }
           }
         }
         list if-distribution-list-information {
         }
         container ifd-lag-traffic-statistics {
         }
       }
       container ifd-lag-traffic-statistics {
       }
       container interval-information {
         list interval {
           description
             "Statistics for a single interval";
         }
       }
       container transport-interval-information {
         list transport-interval {
           description
             "Statistics for a single interval";
           list transport-pm-ber {
             leaf transport-pm-ber-thr-max {
               type string;
             }
             leaf transport-pm-ber-tca-max-en {
               type string;
             }
             leaf transport-pm-ber-tca-max {
               type string;
             }
           }
           list transport-pm-ber-cur {
             leaf transport-pm-ber-cur-thr-max {
               type string;
             }
             leaf transport-pm-ber-cur-tca-max-en {
               type string;
             }
             leaf transport-pm-ber-cur-tca-max {
               type string;
             }
           }
         }
       }
     }
     list logical-interface {
       key "name";
       description
         "Information about a single logical interface";
       leaf name {
         type string;
         description
           "Name of this item";
       }
       leaf admin-status {
         type string;
         description
           "Desired state of the interface";
       }
       leaf oper-status {
         type string;
         description
           "Current operational state of the interface";
       }
       leaf logical-interface-zone-name {
         type string;
         description
           "Zone name for this interface";
       }
       leaf subunit {
         type int32;
         description
           "Subunit for this interface";
       }
       leaf dialer-time-to-disconnect {
         type string;
         description
           "Time for dialer to disconnect due to idle timeout";
       }
       leaf lcp-state {
         type string;
         description
           "State of the Line Control Protocol";
       }
       leaf chap-state {
         type string;
         description
           "State of the Challenge Handshake Authentication Protocol";
       }
       leaf pap-state {
         type string;
         description
           "State of the Password Authentication Protocol";
       }
       container pppoe-information {
         description
           "PPPoE information";
         list pppoe-interface {
           leaf state {
             type string;
             description
               "State";
           }
           leaf session-id {
             type string;
             description
               "Session ID";
           }
           leaf ac-name-session {
             type string;
             description
               "Session AC name";
           }
           leaf remote-mac {
             type string;
             description
               "Remote MAC address";
           }
           leaf ac-name-config {
             type string;
             description
               "Configured AC name";
           }
           leaf service-name {
             type string;
             description
               "Service name";
           }
           leaf auto-reconnect {
             type string;
             description
               "Autoreconnect timeout";
           }
           leaf idle-timeout {
             type string;
             description
               "Idle timeout";
           }
           leaf underlying-interface-name {
             type string;
             description
               "Underlying interface name";
           }
           leaf underlying-interface-index {
             type string;
             description
               "Underlying interface index";
           }
           leaf padg-credits {
             type int32;
             description
               "PADG transmit credits";
           }
           leaf pppoe-credit-scale-factor {
             type string;
             description
               "Scaling factor";
           }
           leaf ignore-eol-tag {
             type string;
             description
               "Ignore End-of-List TAG";
           }
           leaf ppp-max-payload-tag {
             type int32;
             description
               "PPP-Max-Payload TAG";
           }
           leaf interface-name {
             type string;
             description
               "Interface name";
           }
           leaf interface-index {
             type string;
             description
               "Index";
           }
           leaf aci-iflset-name {
             type string;
             description
               "ACI Interface Set name";
           }
           leaf aci-iflset-index {
             type string;
             description
               "ACI Interface Set index";
           }
           leaf ifl-type {
             type string;
             description
               "Type";
           }
           leaf session-uptime {
             type string;
             description
               "Duration for which the session has been up";
           }
           leaf dynamic-profile {
             type string;
             description
               "Dynamic Profile name";
           }
           leaf pppoe-credits {
             type string;
             description
               "Forwarding credit balances";
           }
           leaf dynamic-interface-bandwidth {
             type string;
             description
               "Dynamic interface bandwidth";
           }
           leaf agent-circuit-id {
             type string;
             description
               "Agent Circuit ID";
           }
           leaf agent-remote-id {
             type string;
             description
               "Agent Remote ID";
           }
           leaf padm-motm {
             type string;
             description
               "PADM Message of the Moment tag";
           }
           leaf padm-hurl {
             type string;
             description
               "PADM HTTP URL tag";
           }
           leaf pppoe-relay-session-id {
             type string;
             description
               "PPPoE Relay Session ID";
           }
         }
       }
       container pppoe-underlying-information {
         description
           "PPPoE Underlying information";
         list pppoe-underlying-interface {
           leaf dynamic-profile {
             type string;
             description
               "Dynamic Profile name";
           }
           leaf service-name-table {
             type string;
             description
               "Name of Service Name Table";
           }
           leaf max-sessions {
             type int32;
             description
               "Maximum number of PPPoE sessions";
           }
           leaf max-sessions-vsa-ignore {
             type string;
             description
               "Ignore max-sessions VSA";
           }
           leaf duplicate-protection {
             type string;
             description
               "Duplicate protection mode";
           }
           leaf short-cycle-protection {
             type string;
             description
               "Short cycle protection mode";
           }
           leaf direct-connect {
             type string;
             description
               "Direct connect mode";
           }
           leaf ac-name {
             type string;
             description
               "Access Concentrator name";
           }
           leaf underlying-interface-name {
             type string;
             description
               "Underlying interface name";
           }
           leaf underlying-interface-index {
             type string;
             description
               "Underlying interface index";
           }
           leaf encapsulation-type-identifier {
             type string;
             description
               "Encapsulation type identifier";
           }
           leaf state {
             type string;
             description
               "State";
           }
           leaf active-sessions {
             type int32;
             description
               "Number of active PPPoE sessions";
           }
           leaf aci-autosensing {
             type string;
             description
               "ACI VLAN Autosensing mode";
           }
           leaf line-identity-autosensing {
             type string;
             description
               "Line Identity Autosensing mode";
           }
         }
       }
       container aci-vlan-information {
         leaf dynamic-profile {
           type string;
           description
             "Dynamic Profile name";
         }
       }
       container line-identity-information {
         leaf dynamic-profile {
           type string;
           description
             "Dynamic Profile name";
         }
         leaf circuit-id {
           type string;
           description
             "Aci vlan attribute";
         }
         leaf remote-id {
           type string;
           description
             "Aci vlan attribute";
         }
         leaf accept-no-ids {
           type string;
           description
             "Aci vlan attribute";
         }
       }
       container demux-information {
         description
           "Demux information";
         container demux-interface {
           leaf demux-underlying-interface-name {
             type string;
             description
               "Underlying interface name";
           }
           leaf demux-underlying-interface-index {
             type string;
             description
               "Underlying interface index";
           }
           leaf demux-inet-prefix-type {
             type string;
             description
               "Prefix type";
           }
           leaf demux-inet-prefix-count {
             type string;
             description
               "IPv4 Prefix count";
           }
           leaf demux-inet-prefix {
             type string;
             description
               "IPv4 Prefix";
           }
           leaf demux-inet6-prefix-type {
             type string;
             description
               "Prefix type";
           }
           leaf demux-inet6-prefix-count {
             type string;
             description
               "IPv6 Prefix count";
           }
           leaf demux-inet6-prefix {
             type string;
             description
               "IPv6 Prefix";
           }
         }
       }
       container dual-ad-icl-color-information {
         container dual-ad-icl-color-info {
           description
             "Dual-AD ICL Color Information";
           leaf dual-ad-icl-color-type {
             type uint32;
             description
               "Dual-AD ICL Color Type";
           }
           leaf dual-ad-icl-color {
             type uint32;
             description
               "Dual-AD ICL Color";
           }
         }
       }
       container dialer-information {
         description
           "Dialer information";
         leaf dialer-time-to-disconnect {
           type string;
           description
             "Time for dialer to disconnect due to idle timeout";
         }
         container dialer-interface {
           container dialer-interface-flags {
             description
               "Flags indicating interface configuration";
             leaf backup {
               type empty;
               description
                 "Dialer backup";
             }
             leaf multilink {
               type empty;
               description
                 "Dialer multilink";
             }
             leaf watchlist {
               type empty;
               description
                 "Dialer watchlist";
             }
             leaf interesting-detected {
               type empty;
               description
                 "Interesting packet detected";
             }
           }
           list dial-string-list {
             leaf dial-string {
               type string;
               description
                 "Dial string";
             }
           }
           list sub-interface-list {
             leaf sub-interface-name {
               type string;
               description
                 "Subordinate interface name";
             }
           }
           list watch-list {
             leaf watch-route {
               type string;
               description
                 "Watch route";
             }
           }
           leaf dialer-interface-name {
             type string;
             description
               "Interface name";
           }
           leaf dialer-interface-state {
             type string;
             description
               "Dialer interface state";
           }
           leaf pool-id {
             type string;
             description
               "Pool identifier";
           }
           leaf primary-interface {
             type string;
             description
               "Primary interface";
           }
           leaf activation-delay {
             type string;
             description
               "Activation delay";
           }
           leaf deactivation-delay {
             type string;
             description
               "Deactivation delay";
           }
           leaf activation-delay-elapsed {
             type string;
             description
               "Activation delay elapsed";
           }
           leaf deactivation-delay-elapsed {
             type string;
             description
               "Deactivation delay elapsed";
           }
           leaf call-idle-timeout {
             type string;
             description
               "Call idle timeout";
           }
           leaf initial-route-check {
             type string;
             description
               "Initial route check delay";
           }
           leaf redial-delay {
             type string;
             description
               "Delay before dialer dials out again (seconds)";
           }
           leaf callback-wait-period {
             type string;
             description
               "Delay before dialer attempts callback (seconds)";
           }
           leaf callback-wait-period-elapsed {
             type string;
             description
               "Number of seconds in callback wait period that have elapsed";
           }
           leaf load-threshold {
             type string;
             description
               "Load threshold that determines when interfaces are added to 
               bundle";
           }
           leaf load-interval {
             type string;
             description
               "Interval over which average load is calculated";
           }
         }
       }
       container shared-interface-information {
         description
           "Shared interface information";
         container shared-interface-logical-interface {
           description
             "Shared interface logical interface";
           leaf peer-interface-name {
             type string;
             description
               "Peer interface name";
           }
           leaf interface-shared-with {
             type string;
             description
               "Logical interface owner";
           }
           leaf rx-fe {
             type string;
             description
               "Rx tunnel token forwarding element";
           }
           leaf rx-nhid {
             type string;
             description
               "Rx tunnel token next hop index";
           }
           leaf tx-fe {
             type string;
             description
               "Tx tunnel token forwarding element";
           }
           leaf tx-nhid {
             type string;
             description
               "Tx tunnel token next hop index";
           }
         }
       }
       container mac-database {
       }
       container queue-counters {
         description
           "Queue counter statistics";
         leaf queue-counters-error-message {
           type string;
           description
             "Queue statistics not available for this interface";
         }
         container interface-cos-short-summary {
           description
             "Summary of queue information on an interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
         }
         list queue {
           key "queue-number";
           description
             "Counters for a single queue";
           leaf queue-number {
             type uint32;
             description
               "Queue number";
           }
           leaf queue-counters-queued-packets {
             type int32;
             description
               "Queued packet count";
           }
           leaf queue-counters-trans-packets {
             type int32;
             description
               "Total number of transmitted packets";
           }
           leaf queue-counters-total-drop-packets {
             type int32;
             description
               "Number of total packets dropped at the queue";
           }
           leaf forwarding-class-name {
             type string;
             description
               "Forwarding class name associated with queue";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-queued-packets-na {
             type string;
             description
               "Queued packets not available";
           }
           leaf queue-counters-queued-bytes-na {
             type string;
             description
               "Queued bytes not available";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets-na {
             type string;
             description
               "Number of packets dropped due to tail drop not available";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of packets dropped at tail drop of the queue";
           }
           leaf queue-counters-tail-drop-bytes-rate {
             type int32;
             description
               "Number of packets dropped at tail drop of the queue";
           }
           leaf queue-counters-ecn-ce-packets {
             type int32;
             description
               "Total number of ECN CE packets";
           }
           leaf queue-counters-ecn-ce-packets-rate {
             type int32;
             description
               "Rate at which ECN CE packets are transmitted";
           }
           leaf queue-counters-ecn-ce-bytes {
             type int32;
             description
               "Total number of ECN CE bytes";
           }
           leaf queue-counters-ecn-ce-bytes-rate {
             type int32;
             description
               "Rate at which ECN CE bytes are transmitted";
           }
           leaf queue-counters-rate-limit-drop-packets-na {
             type string;
             description
               "Number of packets dropped due to rate-limit drop not 
               available";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes-na {
             type string;
             description
               "Number of bytes dropped due to tail drop not available";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets-na {
             type string;
             description
               "Number of packets dropped due to RED not available";
           }
           leaf queue-counters-red-packets {
             type int32;
             description
               "Number of packets dropped due to RED";
           }
           leaf queue-counters-red-packets-rate {
             type int32;
             description
               "Rate at which packets are dropped due to RED";
           }
           leaf queue-counters-red-packets-ln {
             type int32;
             description
               "Number of RED dropped low-loss, non-TCP packets";
           }
           leaf queue-counters-red-packets-rate-ln {
             type int32;
             description
               "RED drop rate for low-loss, non-TCP packets";
           }
           leaf queue-counters-red-packets-lt {
             type int32;
             description
               "Number of RED dropped of low-loss, TCP packets";
           }
           leaf queue-counters-red-packets-rate-lt {
             type int32;
             description
               "RED drop rate for low-loss, TCP packets";
           }
           leaf queue-counters-red-packets-hn {
             type int32;
             description
               "Number of RED dropped high-loss, non-TCP packets";
           }
           leaf queue-counters-red-packets-rate-hn {
             type int32;
             description
               "RED drop rate for high-loss, non-TCP packets";
           }
           leaf queue-counters-red-packets-ht {
             type int32;
             description
               "Number of RED dropped high-loss, TCP packets";
           }
           leaf queue-counters-red-packets-rate-ht {
             type int32;
             description
               "RED drop rate for high-loss, TCP packets";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-medium {
             type int32;
             description
               "Number of RED dropped medium-loss packets";
           }
           leaf queue-counters-red-packets-rate-medium {
             type int32;
             description
               "RED drop rate for medium-loss packets";
           }
           leaf queue-counters-red-packets-high {
             type int32;
             description
               "Number of RED dropped high-loss packets";
           }
           leaf queue-counters-red-packets-rate-high {
             type int32;
             description
               "RED drop rate for high-loss packets";
           }
           leaf queue-counters-red-bytes-na {
             type string;
             description
               "Number of bytes dropped due to RED not available";
           }
           leaf queue-counters-red-bytes {
             type int32;
             description
               "Number of bytes dropped due to RED";
           }
           leaf queue-counters-red-bytes-rate {
             type int32;
             description
               "Rate at which bytes are dropped due to RED";
           }
           leaf queue-counters-red-bytes-ln {
             type int32;
             description
               "Number of RED dropped low-loss, non-TCP bytes";
           }
           leaf queue-counters-red-bytes-rate-ln {
             type int32;
             description
               "RED drop rate for low-loss, non-TCP bytes";
           }
           leaf queue-counters-red-bytes-lt {
             type int32;
             description
               "Number of RED dropped low-loss, TCP bytes";
           }
           leaf queue-counters-red-bytes-rate-lt {
             type int32;
             description
               "RED drop rate for low-loss, TCP bytes";
           }
           leaf queue-counters-red-bytes-hn {
             type int32;
             description
               "Number of RED dropped high-loss, non-TCP bytes";
           }
           leaf queue-counters-red-bytes-rate-hn {
             type int32;
             description
               "RED drop rate for high-loss, non-TCP bytes";
           }
           leaf queue-counters-red-bytes-ht {
             type int32;
             description
               "Number of RED dropped high-loss, TCP bytes";
           }
           leaf queue-counters-red-bytes-rate-ht {
             type int32;
             description
               "RED drop rate for high-loss, TCP bytes";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-medium {
             type int32;
             description
               "Number of RED dropped medium-loss bytes";
           }
           leaf queue-counters-red-bytes-rate-medium {
             type int32;
             description
               "RED drop rate for medium-loss bytes";
           }
           leaf queue-counters-red-bytes-high {
             type int32;
             description
               "Number of RED dropped high-loss bytes";
           }
           leaf queue-counters-red-bytes-rate-high {
             type int32;
             description
               "RED drop rate for high-loss bytes";
           }
           leaf queue-counters-timestamp {
             type int32;
             description
               "Last packet enqueued timestamp";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
           leaf queue-counters-reserved-buffer-packets {
             type int32;
             description
               "Queues's usage of reserved buffer pool in pkts";
           }
           leaf queue-counters-reserved-buffer-bytes {
             type int32;
             description
               "Queues's usage of reserved buffer pool in bytes";
           }
           leaf queue-counters-shared-buffer-packets {
             type int32;
             description
               "Queues's usage of shared buffer pool in pkts";
           }
           leaf queue-counters-shared-buffer-bytes {
             type int32;
             description
               "Queues's usage of shared buffer pool in bytes";
           }
           leaf queue-counters-depth-average {
             type int32;
             description
               "Time averaged queue depth";
           }
           leaf queue-counters-depth-current {
             type int32;
             description
               "Current instantaneous queue depth";
           }
           leaf queue-counters-depth-peak {
             type int32;
             description
               "Peak queue depth";
           }
           leaf queue-counters-depth-max {
             type int32;
             description
               "Maximum queue depth attained";
           }
           leaf queue-counters-srx-reserved-buffer-bytes {
             type int32;
             description
               "Queues's usage of reserved buffer pool in bytes";
           }
           leaf queue-counters-srx-depth-current {
             type int32;
             description
               "Current instantaneous queue depth";
           }
         }
         container interface-cos-summary {
           description
             "Summary of forwarding class and queue information on an 
             interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
           leaf intf-cos-burst-size-for-ifl {
             type int32;
             description
               "Burst size for the logical interface";
           }
         }
       }
       container voq-counters {
         description
           "VOQ counter statistics";
         leaf voq-counters-error-message {
           type string;
           description
             "VOQ statistics not available for this interface";
         }
         container voq {
           description
             "Counters for a single voq";
           container fpc {
             description
               "Counters for a single FPC";
             leaf fpc-no {
               type int32;
               description
                 "FPC number";
             }
             container pfe {
               description
                 "Counters for a single PFE";
               leaf-list pfe-no {
                 type int32;
                 description
                   "PFE number";
               }
               leaf voq-counters-tail-drop-packets {
                 type int32;
                 description
                   "Tail DROP packet count";
               }
               leaf voq-counters-tail-drop-packets-rate {
                 type int32;
                 description
                   "Rate at which tail packets are dropped";
               }
               leaf voq-counters-tail-drop-bytes {
                 type int32;
                 description
                   "Tail DROP bytes count";
               }
               leaf voq-counters-tail-drop-bytes-rate {
                 type int32;
                 description
                   "Rate at which tail bytes are dropped";
               }
               leaf voq-counters-drop-packets {
                 type int32;
                 description
                   "DROP packet count";
               }
               leaf voq-counters-drop-packets-rate {
                 type int32;
                 description
                   "Rate at which packets are dropped";
               }
               leaf voq-counters-drop-bytes {
                 type int32;
                 description
                   "DROP bytes count";
               }
               leaf voq-counters-drop-bytes-rate {
                 type int32;
                 description
                   "Rate at which bytes are dropped";
               }
               leaf voq-counters-queued-packets {
                 type int32;
                 description
                   "QUEUED packets count";
               }
               leaf voq-counters-queued-packets-rate {
                 type int32;
                 description
                   "Rate at which packets are queued";
               }
               leaf voq-counters-queued-bytes {
                 type int32;
                 description
                   "QUEUED bytes count";
               }
               leaf voq-counters-queued-bytes-rate {
                 type int32;
                 description
                   "Rate at which bytes are queued";
               }
               leaf voq-counters-transmitted-packets {
                 type int32;
                 description
                   "Transmitted packets count";
               }
               leaf voq-counters-transmitted-packets-rate {
                 type int32;
                 description
                   "Rate at which packets are transmitted";
               }
               leaf voq-counters-transmitted-bytes {
                 type int32;
                 description
                   "Transmitted bytes count";
               }
               leaf voq-counters-transmitted-bytes-rate {
                 type int32;
                 description
                   "Rate at which bytes are transmitted";
               }
               leaf voq-counters-queue-depth-bytes-current {
                 type int32;
                 description
                   "Current queue length";
               }
               leaf voq-counters-queue-depth-bytes-peak {
                 type int32;
                 description
                   "Peak queue length";
               }
               leaf voq-counters-queue-depth-bytes-average {
                 type int32;
                 description
                   "Average queue length";
               }
             }
           }
           leaf queue-number {
             type uint32;
             description
               "Queue number";
           }
           leaf forwarding-class-name {
             type string;
             description
               "Forwarding class name associated with queue";
           }
           leaf restricted-forwarding-class-name {
             type string;
           }
         }
       }
       container ingress-queue-counters {
         description
           "Ingress queue counter statistics";
         list queue {
           key "queue-number";
           description
             "Counters for a single queue";
           leaf queue-number {
             type uint32;
             description
               "Queue number";
           }
           leaf forwarding-class-name {
             type string;
             description
               "Forwarding class name associated with queue";
           }
           leaf queue-counters-queued-packets {
             type int32;
             description
               "Queued packet count";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-queued-packets-na {
             type string;
             description
               "Queued packets not available";
           }
           leaf queue-counters-queued-bytes-na {
             type string;
             description
               "Queued bytes not available";
           }
           leaf queue-counters-trans-packets {
             type int32;
             description
               "Total number of transmitted packets";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets-na {
             type string;
             description
               "Number of packets dropped due to tail drop not available";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of packets dropped at tail drop of the queue";
           }
           leaf queue-counters-tail-drop-bytes-rate {
             type int32;
             description
               "Number of packets dropped at tail drop of the queue";
           }
           leaf queue-counters-ecn-ce-packets {
             type int32;
             description
               "Total number of ECN CE packets";
           }
           leaf queue-counters-ecn-ce-packets-rate {
             type int32;
             description
               "Rate at which ECN CE packets are transmitted";
           }
           leaf queue-counters-ecn-ce-bytes {
             type int32;
             description
               "Total number of ECN CE bytes";
           }
           leaf queue-counters-ecn-ce-bytes-rate {
             type int32;
             description
               "Rate at which ECN CE bytes are transmitted";
           }
           leaf queue-counters-rate-limit-drop-packets-na {
             type string;
             description
               "Number of packets dropped due to rate-limit drop not 
               available";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes-na {
             type string;
             description
               "Number of bytes dropped due to tail drop not available";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets-na {
             type string;
             description
               "Number of packets dropped due to RED not available";
           }
           leaf queue-counters-red-packets {
             type int32;
             description
               "Number of packets dropped due to RED";
           }
           leaf queue-counters-red-packets-rate {
             type int32;
             description
               "Rate at which packets are dropped due to RED";
           }
           leaf queue-counters-red-packets-ln {
             type int32;
             description
               "Number of RED dropped low-loss, non-TCP packets";
           }
           leaf queue-counters-red-packets-rate-ln {
             type int32;
             description
               "RED drop rate for low-loss, non-TCP packets";
           }
           leaf queue-counters-red-packets-lt {
             type int32;
             description
               "Number of RED dropped of low-loss, TCP packets";
           }
           leaf queue-counters-red-packets-rate-lt {
             type int32;
             description
               "RED drop rate for low-loss, TCP packets";
           }
           leaf queue-counters-red-packets-hn {
             type int32;
             description
               "Number of RED dropped high-loss, non-TCP packets";
           }
           leaf queue-counters-red-packets-rate-hn {
             type int32;
             description
               "RED drop rate for high-loss, non-TCP packets";
           }
           leaf queue-counters-red-packets-ht {
             type int32;
             description
               "Number of RED dropped high-loss, TCP packets";
           }
           leaf queue-counters-red-packets-rate-ht {
             type int32;
             description
               "RED drop rate for high-loss, TCP packets";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-medium {
             type int32;
             description
               "Number of RED dropped medium-loss packets";
           }
           leaf queue-counters-red-packets-rate-medium {
             type int32;
             description
               "RED drop rate for medium-loss packets";
           }
           leaf queue-counters-red-packets-high {
             type int32;
             description
               "Number of RED dropped high-loss packets";
           }
           leaf queue-counters-red-packets-rate-high {
             type int32;
             description
               "RED drop rate for high-loss packets";
           }
           leaf queue-counters-red-bytes-na {
             type string;
             description
               "Number of bytes dropped due to RED not available";
           }
           leaf queue-counters-red-bytes {
             type int32;
             description
               "Number of bytes dropped due to RED";
           }
           leaf queue-counters-red-bytes-rate {
             type int32;
             description
               "Rate at which bytes are dropped due to RED";
           }
           leaf queue-counters-red-bytes-ln {
             type int32;
             description
               "Number of RED dropped low-loss, non-TCP bytes";
           }
           leaf queue-counters-red-bytes-rate-ln {
             type int32;
             description
               "RED drop rate for low-loss, non-TCP bytes";
           }
           leaf queue-counters-red-bytes-lt {
             type int32;
             description
               "Number of RED dropped low-loss, TCP bytes";
           }
           leaf queue-counters-red-bytes-rate-lt {
             type int32;
             description
               "RED drop rate for low-loss, TCP bytes";
           }
           leaf queue-counters-red-bytes-hn {
             type int32;
             description
               "Number of RED dropped high-loss, non-TCP bytes";
           }
           leaf queue-counters-red-bytes-rate-hn {
             type int32;
             description
               "RED drop rate for high-loss, non-TCP bytes";
           }
           leaf queue-counters-red-bytes-ht {
             type int32;
             description
               "Number of RED dropped high-loss, TCP bytes";
           }
           leaf queue-counters-red-bytes-rate-ht {
             type int32;
             description
               "RED drop rate for high-loss, TCP bytes";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-medium {
             type int32;
             description
               "Number of RED dropped medium-loss bytes";
           }
           leaf queue-counters-red-bytes-rate-medium {
             type int32;
             description
               "RED drop rate for medium-loss bytes";
           }
           leaf queue-counters-red-bytes-high {
             type int32;
             description
               "Number of RED dropped high-loss bytes";
           }
           leaf queue-counters-red-bytes-rate-high {
             type int32;
             description
               "RED drop rate for high-loss bytes";
           }
           leaf queue-counters-timestamp {
             type int32;
             description
               "Last packet enqueued timestamp";
           }
           leaf queue-counters-total-drop-packets {
             type int32;
             description
               "Number of total packets dropped at the queue";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
           leaf queue-counters-reserved-buffer-packets {
             type int32;
             description
               "Queues's usage of reserved buffer pool in pkts";
           }
           leaf queue-counters-reserved-buffer-bytes {
             type int32;
             description
               "Queues's usage of reserved buffer pool in bytes";
           }
           leaf queue-counters-shared-buffer-packets {
             type int32;
             description
               "Queues's usage of shared buffer pool in pkts";
           }
           leaf queue-counters-shared-buffer-bytes {
             type int32;
             description
               "Queues's usage of shared buffer pool in bytes";
           }
           leaf queue-counters-depth-average {
             type int32;
             description
               "Time averaged queue depth";
           }
           leaf queue-counters-depth-current {
             type int32;
             description
               "Current instantaneous queue depth";
           }
           leaf queue-counters-depth-peak {
             type int32;
             description
               "Peak queue depth";
           }
           leaf queue-counters-depth-max {
             type int32;
             description
               "Maximum queue depth attained";
           }
           leaf queue-counters-srx-reserved-buffer-bytes {
             type int32;
             description
               "Queues's usage of reserved buffer pool in bytes";
           }
           leaf queue-counters-srx-depth-current {
             type int32;
             description
               "Current instantaneous queue depth";
           }
         }
         container interface-cos-summary {
           description
             "Summary of forwarding class and queue information on an 
             interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
           leaf intf-cos-burst-size-for-ifl {
             type int32;
             description
               "Burst size for the logical interface";
           }
         }
         container interface-cos-short-summary {
           description
             "Summary of queue information on an interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
         }
         list queue-num-forwarding-class-name-map {
           key "queue-number";
           leaf queue-number {
             type uint32;
             description
               "Queue number";
           }
           leaf forwarding-class-name {
             type string;
             description
               "Forwarding class name associated with queue";
           }
         }
       }
       container forwarding-class-counters {
         description
           "Forwarding-class counter statistics";
         leaf forwarding-class-counters-error-message {
           type string;
           description
             "Forwarding-class statistics not available for this interface";
         }
         container ipv4-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container ipv6-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container mpls-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container layer2-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container other-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container protocol-aggregate-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container forwarding-class-statistics {
           container protocol-aggregate-forwarding-class-counters {
           }
           container ipv4-forwarding-class-counters {
           }
           container ipv6-forwarding-class-counters {
           }
           container mpls-forwarding-class-counters {
           }
           container layer2-forwarding-class-counters {
           }
           container other-forwarding-class-counters {
           }
         }
         container forwarding-class-accounting-parameters {
           leaf forwarding-class-accounting-for-protocol {
             type string;
           }
           leaf forwarding-class-accounting-for-traffic-direction {
             type string;
           }
           leaf forwarding-class-accounting-for-traffic-type {
             type string;
           }
           leaf forwarding-class-accounting-overhead-bytes {
             type uint32;
           }
         }
         container per-forwarding-class-counters {
           leaf fc_name_header {
             type string;
           }
           leaf forwarding-class-name {
             type string;
             description
               "Forwarding class name associated with queue";
           }
           leaf fc-input-bytes {
             type int32;
           }
           leaf fc-input-bytes-rate {
             type int32;
             description
               "Input bytes rate";
           }
           leaf fc-output-bytes {
             type int32;
           }
           leaf fc-output-bytes-rate {
             type int32;
             description
               "Output bytes rate";
           }
           leaf fc-input-packets {
             type int32;
           }
           leaf fc-input-packets-rate {
             type int32;
             description
               "Input packets rate";
           }
           leaf fc-output-packets {
             type int32;
           }
           leaf fc-output-packets-rate {
             type int32;
             description
               "Output packets rate";
           }
           leaf input-unicast-bytes {
             type int32;
           }
           leaf output-unicast-bytes {
             type int32;
           }
           leaf input-unicast-packets {
             type int32;
           }
           leaf output-unicast-packets {
             type int32;
           }
           leaf input-multicast-bytes {
             type int32;
           }
           leaf output-multicast-bytes {
             type int32;
           }
           leaf input-multicast-packets {
             type int32;
           }
           leaf output-multicast-packets {
             type int32;
           }
         }
       }
       container multilink-bundle-options {
         leaf filler-packet-interval {
           type int32;
         }
       }
       container multilink-traffic-statistics {
         container bundle {
         }
         container class {
           description
             "Multilink class traffic statistics";
         }
         container multilink-detail-statistics {
           container bundle-detail {
           }
           container class-detail {
           }
         }
         container crtp {
           container crtp-sessions {
             leaf input-frames {
               type int32;
             }
             leaf output-frames {
               type int32;
             }
           }
           list crtp-statistics {
             key "name";
             leaf name {
               type string;
               description
                 "Name of this item";
             }
             leaf input-frames {
               type int32;
             }
             leaf input-fps {
               type int32;
             }
             leaf input-bytes {
               type int32;
             }
             leaf input-bps {
               type int32;
             }
             leaf output-frames {
               type int32;
             }
             leaf output-fps {
               type int32;
             }
             leaf output-bytes {
               type int32;
             }
             leaf output-bps {
               type int32;
             }
           }
         }
       }
       container traffic-statistics {
         leaf input-bps {
           type int32;
         }
         leaf input-pps {
           type int32;
         }
         leaf output-bps {
           type int32;
         }
         leaf output-pps {
           type int32;
         }
         leaf input-packets {
           type uint64;
         }
         leaf output-packets {
           type uint64;
         }
         container ipv4-traffic-statistics {
           leaf input-bps {
             type int32;
           }
           leaf output-bps {
             type int32;
           }
           leaf input-pps {
             type int32;
           }
           leaf output-pps {
             type int32;
           }
           leaf input-bytes {
             type int32;
           }
           leaf output-bytes {
             type int32;
           }
           leaf input-packets {
             type uint64;
           }
           leaf output-packets {
             type uint64;
           }
         }
         leaf input-bytes {
           type int32;
         }
         leaf output-bytes {
           type int32;
         }
         container ipv6-transit-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-traffic-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-total-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
       }
       container multicast-statistics {
         description
           "Multicast statistics for interface";
         leaf multicast-statistics-header {
           type empty;
         }
         container ipv4-multicast-statistics {
           description
             "IPV4 multicast statistics for interface";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-multicast-statistics {
           description
             "IPV6 multicast statistics for interface";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
       }
       container ingress-traffic-statistics {
         description
           "Traffic statistics at ingress before entering Packet Forwarding 
           Engine";
         leaf input-bps {
           type int32;
         }
         leaf input-pps {
           type int32;
         }
         leaf input-drop-bps {
           type int32;
           description
             "Drop rate at ingress in bits per second ";
         }
         leaf input-drop-pps {
           type int32;
           description
             "Drop rate at ingress in packets per second ";
         }
         leaf input-bytes {
           type int32;
         }
         leaf input-packets {
           type uint64;
         }
         leaf input-drop-bytes {
           type int32;
           description
             "Drop statistics at ingress in bytes";
         }
         leaf input-drop-packets {
           type int32;
           description
             "Drop statistics at ingress in packets";
         }
       }
       container local-traffic-statistics {
         description
           "Statistics for locally originated traffic";
       }
       container transit-traffic-statistics {
         description
           "Statistics for traffic passing through the Packet Forwarding 
           Engine";
       }
       container layer3-statistics {
       }
       container keepalive-statistics {
         description
           "Keepalive statistics for this interface";
         leaf keepalive-lmi-descriptor {
           type string;
         }
         leaf keepalive-input-count {
           type int32;
         }
         leaf keepalive-input-time {
           type string;
         }
         leaf keepalive-output-count {
           type int32;
         }
         leaf keepalive-output-time {
           type string;
         }
       }
       container virtual-circuit-information {
         description
           "Operational information and statistics for a virtual circuit";
         container traffic-statistics {
           leaf input-bps {
             type int32;
           }
           leaf input-pps {
             type int32;
           }
           leaf output-bps {
             type int32;
           }
           leaf output-pps {
             type int32;
           }
           leaf input-packets {
             type uint64;
           }
           leaf output-packets {
             type uint64;
           }
           container ipv4-traffic-statistics {
             leaf input-bps {
               type int32;
             }
             leaf output-bps {
               type int32;
             }
             leaf input-pps {
               type int32;
             }
             leaf output-pps {
               type int32;
             }
             leaf input-bytes {
               type int32;
             }
             leaf output-bytes {
               type int32;
             }
             leaf input-packets {
               type uint64;
             }
             leaf output-packets {
               type uint64;
             }
           }
           leaf input-bytes {
             type int32;
           }
           leaf output-bytes {
             type int32;
           }
           container ipv6-transit-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-traffic-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-total-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
         }
         container atm-cos-information {
           leaf vc-cos-mode {
             type string;
             description
               "Virtual circuit CoS scheduling mode";
           }
           list atm-cos-queue {
             container atm-cos-queue-parameters {
               leaf cos-forwarding-class-name {
                 type string;
                 description
                   "Forwarding class name associated with queue";
               }
               leaf cos-queue-number {
                 type int32;
                 description
                   "Queue number";
               }
               leaf scheduling-priority {
                 type string;
                 description
                   "Scheduling priority";
               }
               leaf transmit-weight-cells {
                 type int32;
                 description
                   "Weight to apply to scheduling as number of cells";
               }
               leaf transmit-weight-percent {
                 type int32;
                 description
                   "Weight to apply to scheduling as fill percentage";
               }
               leaf epd-threshold {
                 type int32;
                 description
                   "Early packet drop threshold";
               }
               leaf epd-threshold-plp0 {
                 type int32;
                 description
                   "Early packet drop threshold for PLP 0";
               }
               leaf epd-threshold-plp1 {
                 type int32;
                 description
                   "Early packet drop threshold for PLP 1";
               }
               container linear-red-drop-profile {
                 leaf queue-depth {
                   type int32;
                   description
                     "Maximum queue depth";
                 }
                 leaf low-red {
                   type int32;
                   description
                     "Fill level percentage when linear RED is applied for 
                     low PLP";
                 }
                 leaf high-red {
                   type int32;
                   description
                     "Fill level percentage when linear RED is applied for 
                     high PLP";
                 }
                 leaf max-low-red {
                   type int32;
                   description
                     "Fill level percentage with 100% packet drop for low 
                     PLP";
                 }
                 leaf max-high-red {
                   type int32;
                   description
                     "Fill level percentage with 100% packet drop for high 
                     PLP";
                 }
               }
             }
             container atm-cos-queue-statistics {
               leaf atm-output-bytes {
                 type int32;
               }
               leaf atm-output-packets {
                 type int32;
               }
               leaf atm-packet-drops {
                 type int32;
               }
             }
             container atm-cos-plp-statistics {
               leaf atm-plp0-output-bytes {
                 type int32;
               }
               leaf atm-plp1-output-bytes {
                 type int32;
               }
               leaf atm-plp0-output-packets {
                 type int32;
               }
               leaf atm-plp1-output-packets {
                 type int32;
               }
               leaf atm-plp0-byte-drops {
                 type int32;
               }
               leaf atm-plp1-byte-drops {
                 type int32;
               }
               leaf atm-plp0-packet-drops {
                 type int32;
               }
               leaf atm-plp1-packet-drops {
                 type int32;
               }
             }
           }
         }
       }
       list filter-information {
         leaf filter-family {
           type string;
           description
             "Protocol family of the filter";
         }
         leaf-list filter-input {
           type string;
           description
             "Name of the input filter";
         }
         leaf-list filter-output {
           type string;
           description
             "Name of the output filter";
         }
       }
       container allowed-host-inbound-traffic {
         description
           "List of allowed system services and protocols";
         leaf inbound-all-protocols {
           type empty;
           description
             "All protocols";
         }
         leaf inbound-any-service {
           type empty;
           description
             "Any service";
         }
         leaf inbound-bootp {
           type empty;
           description
             "Bootp and dhcp relay-agent service";
         }
         leaf inbound-bfd {
           type empty;
           description
             "Bidirectional Forwarding Detection";
         }
         leaf inbound-bgp {
           type empty;
           description
             "Border Gateway Protocol";
         }
         leaf inbound-dns {
           type empty;
           description
             "DNS and DNS-proxy service";
         }
         leaf inbound-dvmrp {
           type empty;
           description
             "Distance Vector Multicast Routing Protocol";
         }
         leaf inbound-igmp {
           type empty;
           description
             "Internet Group Management Protocol";
         }
         leaf inbound-ldp {
           type empty;
           description
             "Label Distribution Protocol";
         }
         leaf inbound-msdp {
           type empty;
           description
             "Multicast Source Discovery Protocol";
         }
         leaf inbound-nhrp {
           type empty;
           description
             "Next Hop Resolution Protocol";
         }
         leaf inbound-ospf {
           type empty;
           description
             "Open Shortest Path First";
         }
         leaf inbound-ospf3 {
           type empty;
           description
             "Open Shortest Path First version 3";
         }
         leaf inbound-pgm {
           type empty;
           description
             "Pragmatic General Multicast";
         }
         leaf inbound-pim {
           type empty;
           description
             "Protocol Independent Multicast";
         }
         leaf inbound-rip {
           type empty;
           description
             "Routing Information Protocol";
         }
         leaf inbound-ripng {
           type empty;
           description
             "Routing Information Protocol next generation";
         }
         leaf inbound-router-discovery {
           type empty;
           description
             "Router Discovery";
         }
         leaf inbound-rsvp {
           type empty;
           description
             "Resource Reservation Protocol";
         }
         leaf inbound-sap {
           type empty;
           description
             "Session Announcement Protocol";
         }
         leaf inbound-vrrp {
           type empty;
           description
             "Virtual Router Redundancy Protocol";
         }
         leaf inbound-all-services {
           type empty;
           description
             "All system services";
         }
         leaf inbound-dhcp {
           type empty;
           description
             "Dynamic Host Configuration Protocol";
         }
         leaf inbound-finger {
           type empty;
           description
             "Finger service";
         }
         leaf inbound-ftp {
           type empty;
           description
             "File Transfer Protocol";
         }
         leaf inbound-tftp {
           type empty;
           description
             "Trivial File Transfer Protocol";
         }
         leaf ident-reset {
           type empty;
           description
             "Send back TCP RST to IDENT request for port 113";
         }
         leaf inbound-http {
           type empty;
           description
             "Web management service using HTTP";
         }
         leaf inbound-https {
           type empty;
           description
             "Web management service using HTTP secured by SSL";
         }
         leaf inbound-ike {
           type empty;
           description
             "Internet Key Exchange";
         }
         leaf inbound-netconf {
           type empty;
           description
             "NETCONF service";
         }
         leaf inbound-ping {
           type empty;
           description
             "Internet Control Message Protocol echo requests";
         }
         leaf inbound-reverse-telnet {
           type empty;
           description
             "Reverse telnet service";
         }
         leaf inbound-reverse-ssh {
           type empty;
           description
             "Reverse SSH service";
         }
         leaf inbound-rlogin {
           type empty;
           description
             "Rlogin service";
         }
         leaf inbound-rpm {
           type empty;
           description
             "Real-time performance monitoring";
         }
         leaf inbound-rsh {
           type empty;
           description
             "Rsh service";
         }
         leaf inbound-snmp {
           type empty;
           description
             "Simple Network Management Protocol service";
         }
         leaf inbound-snmp-trap {
           type empty;
           description
             "Simple Network Management Protocol traps";
         }
         leaf inbound-ssh {
           type empty;
           description
             "SSH service";
         }
         leaf inbound-telnet {
           type empty;
           description
             "Telnet service";
         }
         leaf inbound-traceroute {
           type empty;
           description
             "Traceroute service";
         }
         leaf inbound-xnm-clear-text {
           type empty;
           description
             "JUNOScript API for unencrypted traffic over TCP";
         }
         leaf inbound-xnm-ssl {
           type empty;
           description
             "JUNOScript API service over SSL";
         }
         leaf inbound-lsping {
           type empty;
           description
             "Label Switched Path ping service";
         }
         leaf inbound-lsselfping {
           type empty;
           description
             "Label Switched Path self ping service";
         }
         leaf inbound-ntp {
           type empty;
           description
             "Network Time Protocol service";
         }
         leaf inbound-sip {
           type empty;
           description
             "Session Initiation Protocol service";
         }
         leaf inbound-dhcpv6 {
           type empty;
           description
             "Dynamic Host Configuration Protocol for IPv6 service";
         }
         leaf inbound-r2cp {
           type empty;
           description
             "Radio Router Control Protocol service";
         }
         leaf inbound-webapi-clear-text {
           type empty;
           description
             "Webapi service using http";
         }
         leaf inbound-webapi-ssl {
           type empty;
           description
             "Webapi service using HTTP secured by SSL";
         }
         leaf inbound-tcp-encap {
           type empty;
           description
             "Tcp encapsulation service";
         }
         leaf inbound-sdwan-appqoe {
           type empty;
           description
             "Sdwan Appqoe service";
         }
         leaf inbound-high-availability {
           type empty;
           description
             "High Availability  service";
         }
       }
       list address-family {
         container pppoe-underlying-information {
           description
             "PPPoE Underlying information";
           list pppoe-underlying-interface {
             leaf dynamic-profile {
               type string;
               description
                 "Dynamic Profile name";
             }
             leaf service-name-table {
               type string;
               description
                 "Name of Service Name Table";
             }
             leaf max-sessions {
               type int32;
               description
                 "Maximum number of PPPoE sessions";
             }
             leaf max-sessions-vsa-ignore {
               type string;
               description
                 "Ignore max-sessions VSA";
             }
             leaf duplicate-protection {
               type string;
               description
                 "Duplicate protection mode";
             }
             leaf short-cycle-protection {
               type string;
               description
                 "Short cycle protection mode";
             }
             leaf direct-connect {
               type string;
               description
                 "Direct connect mode";
             }
             leaf ac-name {
               type string;
               description
                 "Access Concentrator name";
             }
             leaf underlying-interface-name {
               type string;
               description
                 "Underlying interface name";
             }
             leaf underlying-interface-index {
               type string;
               description
                 "Underlying interface index";
             }
             leaf encapsulation-type-identifier {
               type string;
               description
                 "Encapsulation type identifier";
             }
             leaf state {
               type string;
               description
                 "State";
             }
             leaf active-sessions {
               type int32;
               description
                 "Number of active PPPoE sessions";
             }
             leaf aci-autosensing {
               type string;
               description
                 "ACI VLAN Autosensing mode";
             }
             leaf line-identity-autosensing {
               type string;
               description
                 "Line Identity Autosensing mode";
             }
           }
         }
         list interface-address {
         }
         container destination-class-statistics {
           description
             "Destination class usage (DCU) statistics";
         }
         container source-class-statistics {
           description
             "Source class usage (SCU) statistics";
         }
         list local-bias-information {
           leaf local-bias-vtep-ifl-name {
             type string;
             description
               "Interface name";
           }
           leaf local-bias-vtep-ifl-index {
             type uint32;
             description
               "Interface index";
           }
           leaf local-bias-vtep-address {
             type string;
             description
               "Protocol address of the connection";
           }
         }
         leaf ft-iff-dest-port {
           type uint32;
           description
             "Destination UDP port to be used for this family";
         }
       }
       list bridge-iff-properties {
         description
           "Information about Ethernet-switching address family";
       }
       container l2circuit-info {
         leaf out-of-sequence {
           type int32;
         }
         leaf denied-packets {
           type int32;
         }
         leaf cell-bundle-size {
           type int32;
         }
         leaf cell-bundle-timeout {
           type int32;
         }
         leaf cell-timeout-count {
           type int32;
         }
       }
       container media-information {
         description
           "Information about media alarms";
         leaf media-type {
           type string;
           description
             "Type of media this information is for";
         }
         list media-alarm {
           leaf media-alarm-name {
             type string;
           }
           leaf media-alarm-count {
             type int32;
           }
           leaf media-alarm-seconds {
             type int32;
           }
           leaf media-alarm-state {
             type string;
           }
           leaf ce-counter-name {
             type string;
             description
               "Circuit Emulation counter information";
           }
           leaf ce-counter-packets {
             type int32;
             description
               "Circuit Emulation number of packets";
           }
           leaf ce-counter-bytes {
             type int32;
             description
               "Circuit Emulation number of bytes";
           }
           leaf ce-counter-count {
             type int32;
             description
               "Circuit Emulation number of event occurrences";
           }
         }
         leaf ds1-timeslots {
           type string;
         }
         leaf ds1-line-encoding {
           type string;
         }
         leaf ds1-byte-encoding {
           type string;
         }
         leaf ds1-data-inversion {
           type string;
         }
         leaf idle-cycle-flag {
           type string;
         }
         leaf start-end-flag {
           type string;
         }
         leaf ds0-byte-encoding {
           type string;
         }
         leaf ds0-data-inversion {
           type string;
         }
         leaf e3-data-inversion {
           type string;
         }
         leaf ds1-buildout {
           type string;
           description
             "Number of feet";
         }
       }
       container macsec-statistics {
         description
           "MACSec Statistics ";
         leaf macsec-tx-sc-protected {
           type int32;
           description
             "Protected Secure Channel MACSec packets transmitted";
         }
         leaf macsec-tx-sc-encrypted {
           type int32;
           description
             "Encrypted Secure Channel MACSec packets transmitted";
         }
         leaf macsec-tx-sc-protectedbytes {
           type int32;
           description
             "Protected Secure Channel MACSec bytes transmitted";
         }
         leaf macsec-tx-sc-encryptedbytes {
           type int32;
           description
             "Encrypted Secure Channel MACSec bytes transmitted";
         }
         leaf macsec-rx-sc-ok {
           type int32;
           description
             "OK Secure Association MACSec packets received";
         }
         leaf macsec-rx-sc-validatedbytes {
           type int32;
           description
             "Validated Secure Association MACSec bytes received";
         }
         leaf macsec-rx-sc-decryptedbytes {
           type int32;
           description
             "Validated Secure Association MACSec bytes received";
         }
         leaf interface-name {
           type string;
           description
             "Class-of-service interface name";
         }
         leaf encrypted-packets {
           type uint64;
           description
             "Macsec encrypted packets sent";
         }
         leaf encrypted-bytes {
           type uint64;
           description
             "Macsec encrypted bytes sent";
         }
         leaf protected-packets {
           type uint64;
           description
             "Macsec packets sent with only integrity protection";
         }
         leaf protected-bytes {
           type uint64;
           description
             "Macsec bytes sent with only integrity protection";
         }
         leaf ok-packets {
           type uint64;
           description
             "Macsec packets accepted";
         }
         leaf decrypted-bytes {
           type uint64;
           description
             "Macsec received bytes decrypted";
         }
         leaf decrypted-packets {
           type uint64;
           description
             "Macsec received packets decrypted";
         }
         leaf validated-packets {
           type uint64;
           description
             "Macsec received packets validated";
         }
         leaf validated-bytes {
           type uint64;
           description
             "Macsec received bytes validated";
         }
         leaf untagged-packets {
           type uint64;
           description
             "Macsec untagged packets";
         }
         leaf toolong-packets {
           type uint64;
           description
             "Macsec too long packets transmitted on a secure channel";
         }
         leaf control-packets {
           type uint64;
           description
             "Macsec control packets received on a secure channel";
         }
         leaf tagged-miss-packets {
           type uint64;
           description
             "Macsec tagged miss packets received on a secure channel";
         }
         leaf untagged-hit-packets {
           type uint64;
           description
             "Macsec untagged hit packets received on a secure channel";
         }
         leaf notag-packets {
           type uint64;
           description
             "Macsec no tag packets received on a secure channel";
         }
         leaf badtag-packets {
           type uint64;
           description
             "Macsec bad tag packets received on a secure channel";
         }
         leaf unknown-sci-packets {
           type uint64;
           description
             "Macsec unknown sci packets received on a secure channel";
         }
         leaf no-sci-packets {
           type uint64;
           description
             "Macsec no sci packets received on a secure channel";
         }
         leaf control-pass-packets {
           type uint64;
           description
             "Macsec allowed control packets received on a secure channel";
         }
         leaf uncontrol-pass-packets {
           type uint64;
           description
             "Macsec allowed uncontrol packets received on a secure channel";
         }
         leaf control-fail-packets {
           type uint64;
           description
             "Macsec dropped control packets received on a secure channel";
         }
         leaf uncontrol-fail-packets {
           type uint64;
           description
             "Macsec dropped uncontrol packets received on a secure channel";
         }
         leaf hit-dropped-packets {
           type uint64;
           description
             "Macsec hit dropped packets received on a security channel";
         }
         leaf notusing-sa-packets {
           type uint64;
           description
             "Macsec not using sa packets received on a security channel";
         }
         leaf unused-sa-packets {
           type uint64;
           description
             "Macsec unused sa packets received on a security channel";
         }
         leaf late-packets {
           type uint64;
           description
             "Macsec late packets dropped on a security channel";
         }
         leaf delayed-packets {
           type uint64;
           description
             "Macsec delayed packets accepted on a security channel";
         }
         leaf unchecked-packets {
           type uint64;
           description
             "Macsec unchecked packets accepted on a security channel";
         }
         leaf notvalid-packets {
           type uint64;
           description
             "Macsec not valid packets dropped on a security channel";
         }
         leaf invalid-packets {
           type uint64;
           description
             "Macsec invalid packets accepted on a security channel";
         }
         list secure-channel-sent {
           leaf encrypted-packets {
             type uint64;
             description
               "Macsec encrypted packets sent";
           }
           leaf encrypted-bytes {
             type uint64;
             description
               "Macsec encrypted bytes sent";
           }
           leaf protected-packets {
             type uint64;
             description
               "Macsec packets sent with only integrity protection";
           }
           leaf protected-bytes {
             type uint64;
             description
               "Macsec bytes sent with only integrity protection";
           }
         }
         list secure-association-sent {
           leaf encrypted-packets {
             type uint64;
             description
               "Macsec encrypted packets sent";
           }
           leaf encrypted-bytes {
             type uint64;
             description
               "Macsec encrypted bytes sent";
           }
           leaf protected-packets {
             type uint64;
             description
               "Macsec packets sent with only integrity protection";
           }
           leaf protected-bytes {
             type uint64;
             description
               "Macsec bytes sent with only integrity protection";
           }
         }
         list secure-channel-received {
           leaf ok-packets {
             type uint64;
             description
               "Macsec packets accepted";
           }
           leaf decrypted-packets {
             type uint64;
             description
               "Macsec received packets decrypted";
           }
           leaf decrypted-bytes {
             type uint64;
             description
               "Macsec received bytes decrypted";
           }
           leaf validated-packets {
             type uint64;
             description
               "Macsec received packets validated";
           }
           leaf validated-bytes {
             type uint64;
             description
               "Macsec received bytes validated";
           }
         }
         list secure-association-received {
           leaf ok-packets {
             type uint64;
             description
               "Macsec packets accepted";
           }
           leaf decrypted-packets {
             type uint64;
             description
               "Macsec received packets decrypted";
           }
           leaf decrypted-bytes {
             type uint64;
             description
               "Macsec received bytes decrypted";
           }
           leaf validated-packets {
             type uint64;
             description
               "Macsec received packets validated";
           }
           leaf validated-bytes {
             type uint64;
             description
               "Macsec received bytes validated";
           }
         }
         list macsec-error-information {
           list secure-channel-sent-errors {
             leaf untagged-packets {
               type uint64;
               description
                 "Macsec untagged packets";
             }
             leaf toolong-packets {
               type uint64;
               description
                 "Macsec too long packets transmitted on a secure channel";
             }
           }
           list secure-channel-received-errors {
             leaf control-packets {
               type uint64;
               description
                 "Macsec control packets received on a secure channel";
             }
             leaf tagged-miss-packets {
               type uint64;
               description
                 "Macsec tagged miss packets received on a secure channel";
             }
             leaf untagged-hit-packets {
               type uint64;
               description
                 "Macsec untagged hit packets received on a secure channel";
             }
             leaf untagged-packets {
               type uint64;
               description
                 "Macsec untagged packets";
             }
             leaf notag-packets {
               type uint64;
               description
                 "Macsec no tag packets received on a secure channel";
             }
             leaf badtag-packets {
               type uint64;
               description
                 "Macsec bad tag packets received on a secure channel";
             }
             leaf unknown-sci-packets {
               type uint64;
               description
                 "Macsec unknown sci packets received on a secure channel";
             }
             leaf no-sci-packets {
               type uint64;
               description
                 "Macsec no sci packets received on a secure channel";
             }
             leaf control-pass-packets {
               type uint64;
               description
                 "Macsec allowed control packets received on a secure 
                 channel";
             }
             leaf control-fail-packets {
               type uint64;
               description
                 "Macsec dropped control packets received on a secure 
                 channel";
             }
             leaf uncontrol-pass-packets {
               type uint64;
               description
                 "Macsec allowed uncontrol packets received on a secure 
                 channel";
             }
             leaf uncontrol-fail-packets {
               type uint64;
               description
                 "Macsec dropped uncontrol packets received on a secure 
                 channel";
             }
           }
           list secure-channel-received-extended {
             leaf hit-dropped-packets {
               type uint64;
               description
                 "Macsec hit dropped packets received on a security channel";
             }
             leaf invalid-packets {
               type uint64;
               description
                 "Macsec invalid packets accepted on a security channel";
             }
             leaf late-packets {
               type uint64;
               description
                 "Macsec late packets dropped on a security channel";
             }
             leaf delayed-packets {
               type uint64;
               description
                 "Macsec delayed packets accepted on a security channel";
             }
             leaf unchecked-packets {
               type uint64;
               description
                 "Macsec unchecked packets accepted on a security channel";
             }
             leaf notvalid-packets {
               type uint64;
               description
                 "Macsec not valid packets dropped on a security channel";
             }
             leaf notusing-sa-packets {
               type uint64;
               description
                 "Macsec not using sa packets received on a security channel";
             }
             leaf unused-sa-packets {
               type uint64;
               description
                 "Macsec unused sa packets received on a security channel";
             }
             leaf untagged-hit-packets {
               type uint64;
               description
                 "Macsec untagged hit packets received on a secure channel";
             }
           }
         }
       }
       container security-input-flow-statistics {
         description
           "Flow input statistics for the interface";
         leaf flow-input-self-packets {
           type int32;
           description
             "Input Self packets";
         }
         leaf flow-input-icmp-packets {
           type int32;
           description
             "Input ICMP packets";
         }
         leaf flow-input-vpn-packets {
           type int32;
           description
             "Input VPN packets";
         }
         leaf flow-input-multicast-packets {
           type int32;
           description
             "Input multicast packets";
         }
         leaf flow-input-policy-bytes {
           type int32;
           description
             "Input policy bytes";
         }
         leaf flow-input-connections {
           type int32;
           description
             "Input connections";
         }
       }
       container security-output-flow-statistics {
         description
           "Flow output statistics for the interface";
         leaf flow-output-multicast-packets {
           type int32;
           description
             "Output multicast packets";
         }
         leaf flow-output-policy-bytes {
           type int32;
           description
             "Output bytes permitted by policy";
         }
       }
       container security-error-flow-statistics {
         description
           "Flow error statistics for the interface";
         leaf flow-error-policy-denied {
           type int32;
           description
             "Policy denied";
         }
         leaf flow-error-no-gate-parent {
           type int32;
           description
             "No parent for gate";
         }
         leaf flow-error-syn-protection {
           type int32;
           description
             "Syn-attack protection";
         }
         leaf flow-error-incoming-nat {
           type int32;
           description
             "Incoming NAT errors";
         }
         leaf flow-error-no-tunnel {
           type int32;
           description
             "No tunnel found";
         }
         leaf flow-error-no-more-session {
           type int32;
           description
             "No more sessions";
         }
         leaf flow-error-invalid-zone {
           type int32;
           description
             "Invalid zone received packet";
         }
         leaf flow-error-user-authentication {
           type int32;
           description
             "User authentication errors";
         }
         leaf flow-error-multiple-auth {
           type int32;
           description
             "Multiple user authentications";
         }
         leaf flow-error-multiple-incoming-nat {
           type int32;
           description
             "Multiple incoming NAT";
         }
         leaf flow-error-address-spoofing {
           type int32;
           description
             "Address spoofing";
         }
         leaf flow-error-null-zone {
           type int32;
           description
             "No zone or NULL zone binding";
         }
         leaf flow-error-no-nat-gate {
           type int32;
           description
             "No NAT gate";
         }
         leaf flow-error-no-minor-session {
           type int32;
           description
             "No minor session";
         }
         leaf flow-error-no-session-gate {
           type int32;
           description
             "No session for a gate";
         }
         leaf flow-error-seq-outside-window {
           type int32;
           description
             "TCP sequence number out of window";
         }
         leaf flow-error-no-route-present {
           type int32;
           description
             "No route present";
         }
         leaf flow-error-authentication-failed {
           type int32;
           description
             "Authentication failed";
         }
         leaf flow-error-security-association-missing {
           type int32;
           description
             "Security association not active";
         }
         leaf flow-error-no-sa-for-spi {
           type int32;
           description
             "No SA for incoming SPI";
         }
         leaf flow-error-no-interest-self-packet {
           type int32;
           description
             "No one interested in self packets";
         }
       }
       container lag-traffic-statistics {
         container lag-multicast-statistics {
           leaf lag-multicast-statistics-header {
             type empty;
           }
           container lag-ipv4-multicast-statistics {
             leaf input-packets {
               type uint64;
             }
             leaf input-pps {
               type int32;
             }
             leaf input-bytes {
               type int32;
             }
             leaf input-bps {
               type int32;
             }
             leaf output-packets {
               type uint64;
             }
             leaf output-pps {
               type int32;
             }
             leaf output-bytes {
               type int32;
             }
             leaf output-bps {
               type int32;
             }
           }
           container lag-ipv6-multicast-statistics {
             leaf input-packets {
               type uint64;
             }
             leaf input-pps {
               type int32;
             }
             leaf input-bytes {
               type int32;
             }
             leaf input-bps {
               type int32;
             }
             leaf output-packets {
               type uint64;
             }
             leaf output-pps {
               type int32;
             }
             leaf output-bytes {
               type int32;
             }
             leaf output-bps {
               type int32;
             }
           }
         }
         list if-distribution-list-information {
         }
         container ifd-lag-traffic-statistics {
         }
       }
       container ifd-lag-traffic-statistics {
       }
       container layer2-input-policer-statistics {
         description
           "Layer 2 input policer statistics for interface";
         leaf policer-medium-low-frames {
           type int32;
           description
             "Number of loss priority medium low frames";
         }
         leaf policer-medium-low-bytes {
           type int32;
           description
             "Number of loss priority medium low bytes";
         }
         leaf policer-medium-low-rate {
           type int32;
           description
             "Rate of loss priority medium low pkts";
         }
       }
       container layer2-output-policer-statistics {
         description
           "Layer 2 output policer statistics for interface";
         leaf policer-medium-low-frames {
           type int32;
           description
             "Number of loss priority medium low frames";
         }
         leaf policer-medium-low-bytes {
           type int32;
           description
             "Number of loss priority medium low bytes";
         }
         leaf policer-medium-low-rate {
           type int32;
           description
             "Rate of loss priority medium low pkts";
         }
       }
       container mac-policer-information {
         container ether-policer-list {
         }
       }
       leaf vrfname {
         type string;
         description
           "Routing instance name";
       }
       leaf zonename {
         type string;
         description
           "Zone name";
       }
     }
   }
   grouping interface-policer-information-block {
     list physical-interface {
       key "name";
       description
         "Information about a single physical interface";
       leaf name {
         type string;
         description
           "Name of this item";
       }
       leaf admin-status {
         type string;
         description
           "Desired state of the interface";
       }
       leaf oper-status {
         type string;
         description
           "Current operational state of the interface";
       }
       leaf esi-source-bmac {
         type jt:mac-addr;
         description
           "Ethernet segment source B-MAC for this interface";
       }
       leaf sonet-payload-pointer-curptr {
         type string;
         description
           "Value of the SONET/SDH payload pointer, derived from the H1 and 
           H2 overhead bytes";
       }
       leaf sonet-payload-pointer-ptrinc-count {
         type string;
         description
           "Number of times the value of the SONET/SDH payload pointer had 
           positive justification";
       }
       leaf sonet-payload-pointer-ptrdec-count {
         type string;
         description
           "Number of times the value of the SONET/SDH payload pointer had 
           negative justification";
       }
       leaf sonet-payload-pointer-newptr-ndf-count {
         type string;
         description
           "Number of times a new payload pointer was created with the New 
           Data Found flag set";
       }
       leaf link-partner-status {
         type string;
         description
           "Auto-negotiation status of link partner";
       }
       container optics-diagnostics {
         description
           "Optics diagnostics";
         leaf optic-diagnostics-not-available {
           type string;
           description
             "Optical diagnostics not supported by this transceiver";
         }
         leaf laser-bias-current-not-available {
           type string;
           description
             "Laser bias current measurement not available";
         }
         leaf soa-bias-current-not-available {
           type string;
           description
             "SOA bias current measurement not available";
         }
         leaf laser-tx-power-not-available {
           type string;
           description
             "Laser output power measurement not available";
         }
         leaf module-temperature-not-available {
           type string;
           description
             "Module temperature measurement not available";
         }
         leaf tx-module-temperature-not-available {
           type string;
           description
             "Tx module temperature measurement not available";
         }
         leaf rx-module-temperature-not-available {
           type string;
           description
             "Rx module temperature measurement not available";
         }
         leaf laser-rx-power-not-available {
           type string;
           description
             "Laser receiver optical power measurement not available";
         }
         leaf laser-tx-power-high-alarm-threshold-not-available {
           type string;
           description
             "Laser output power high alarm threshold not available";
         }
         leaf laser-tx-power-low-alarm-threshold-not-available {
           type string;
           description
             "Laser output power low alarm threshold not available";
         }
         leaf laser-tx-power-high-warning-threshold-not-available {
           type string;
           description
             "Laser output power high warning threshold not available";
         }
         leaf laser-tx-power-low-warning-threshold-not-available {
           type string;
           description
             "Laser output power low warning threshold not available";
         }
         leaf laser-bias-current-high-alarm-threshold-not-available {
           type string;
           description
             "Laser bias current high alarm threshold not available";
         }
         leaf laser-bias-current-low-alarm-threshold-not-available {
           type string;
           description
             "Laser bias current low alarm threshold not available";
         }
         leaf laser-bias-current-high-warning-threshold-not-available {
           type string;
           description
             "Laser bias current high warning threshold not available";
         }
         leaf laser-bias-current-low-warning-threshold-not-available {
           type string;
           description
             "Laser bias current low warning threshold not available";
         }
         leaf laser-bias-current {
           type string;
           description
             "Laser bias current (milliamperes)";
         }
         leaf soa-bias-current {
           type string;
           description
             "SOA bias current (milliamperes)";
         }
         leaf laser-output-power {
           type string;
           description
             "Laser output power (milliwatts)";
         }
         leaf laser-output-power-dbm {
           type string;
           description
             "Laser output power (dBm)";
         }
         leaf module-temperature {
           type string;
           description
             "Module temperature";
         }
         leaf tx-module-temperature {
           type string;
           description
             "Tx module temperature";
         }
         leaf rx-module-temperature {
           type string;
           description
             "Rx module temperature";
         }
         leaf host-id {
           type uint32;
           description
             "Host code of this interface";
         }
         leaf media-id {
           type uint32;
           description
             "Media code of this interface";
         }
         leaf host-code-desc {
           type string;
           description
             "Current optics host code";
         }
         leaf media-code-desc {
           type string;
           description
             "Current optics media code";
         }
         leaf module-voltage {
           type string;
           description
             "Module voltage";
         }
         leaf module-max-power {
           type string;
           description
             "Module max power";
         }
         leaf corrected-error-ratio {
           type string;
           description
             "Corrected error ratio";
         }
         leaf uncorrected-words-ratio {
           type string;
           description
             "Uncorrected words ratio";
         }
         leaf tx-module-voltage {
           type string;
           description
             "Tx module voltage";
         }
         leaf rx-module-voltage {
           type string;
           description
             "Rx module voltage";
         }
         leaf rx-signal-avg-optical-power {
           type string;
           description
             "Receiver signal average power (milliwatts)";
         }
         leaf rx-signal-avg-optical-power-dbm {
           type string;
           description
             "Receiver signal average power (dBm)";
         }
         leaf laser-rx-optical-power {
           type string;
           description
             "Laser receiver optical power (milliwatts)";
         }
         leaf laser-rx-optical-power-dbm {
           type string;
           description
             "Laser receiver optical power (dBm)";
         }
         leaf wavelength-channel {
           type string;
           description
             "Wavelength channel number set";
         }
         leaf wavelength-setpoint {
           type string;
           description
             "Wavelength point set";
         }
         leaf tx-dither {
           type string;
           description
             "Tx dither status";
         }
         leaf frequency-error {
           type string;
           description
             "Frequency error value";
         }
         leaf wavelength-error {
           type string;
           description
             "Wavelength error value";
         }
         leaf laser-bias-current-high-alarm {
           type string;
           description
             "Laser bias current high alarm";
         }
         leaf laser-bias-current-low-alarm {
           type string;
           description
             "Laser bias current low alarm";
         }
         leaf laser-bias-current-high-warn {
           type string;
           description
             "Laser bias current high warning";
         }
         leaf laser-bias-current-low-warn {
           type string;
           description
             "Laser bias current low warning";
         }
         leaf soa-bias-current-high-alarm {
           type string;
           description
             "SOA bias current high alarm";
         }
         leaf soa-bias-current-low-alarm {
           type string;
           description
             "SOA bias current low alarm";
         }
         leaf soa-bias-current-high-warn {
           type string;
           description
             "SOA bias current high warning";
         }
         leaf soa-bias-current-low-warn {
           type string;
           description
             "SOA bias current low warning";
         }
         leaf laser-tx-power-high-alarm {
           type string;
           description
             "Laser output power high alarm";
         }
         leaf laser-tx-power-low-alarm {
           type string;
           description
             "Laser output power low alarm";
         }
         leaf laser-tx-power-high-warn {
           type string;
           description
             "Laser output power high warning";
         }
         leaf laser-tx-power-low-warn {
           type string;
           description
             "Laser output power low warning";
         }
         leaf tx-power-high-alarm {
           type string;
           description
             "Tx power high alarm";
         }
         leaf tx-power-low-alarm {
           type string;
           description
             "Tx power low alarm";
         }
         leaf tx-power-high-warn {
           type string;
           description
             "Tx power high warning";
         }
         leaf tx-power-low-warn {
           type string;
           description
             "Tx power low warning";
         }
         leaf module-temperature-high-alarm {
           type string;
           description
             "Module temperature high alarm";
         }
         leaf module-temperature-low-alarm {
           type string;
           description
             "Module temperature low alarm";
         }
         leaf module-temperature-high-warn {
           type string;
           description
             "Module temperature high warning";
         }
         leaf module-temperature-low-warn {
           type string;
           description
             "Module temperature low warning";
         }
         leaf tx-module-temperature-high-alarm {
           type string;
           description
             "Tx module temperature high alarm";
         }
         leaf tx-module-temperature-low-alarm {
           type string;
           description
             "Tx module temperature low alarm";
         }
         leaf rx-module-temperature-high-alarm {
           type string;
           description
             "Rx module temperature high alarm";
         }
         leaf rx-module-temperature-low-alarm {
           type string;
           description
             "Rx module temperature low alarm";
         }
         leaf module-voltage-high-alarm {
           type string;
           description
             "Module voltage high alarm";
         }
         leaf module-voltage-low-alarm {
           type string;
           description
             "Module voltage low alarm";
         }
         leaf module-voltage-high-warn {
           type string;
           description
             "Module voltage high warning";
         }
         leaf module-voltage-low-warn {
           type string;
           description
             "Module voltage low warning";
         }
         leaf tx-module-voltage-high-alarm {
           type string;
           description
             "Tx module voltage high alarm";
         }
         leaf tx-module-voltage-low-alarm {
           type string;
           description
             "Tx module voltage low alarm";
         }
         leaf rx-module-voltage-high-alarm {
           type string;
           description
             "Rx module voltage high alarm";
         }
         leaf rx-module-voltage-low-alarm {
           type string;
           description
             "Rx module voltage low alarm";
         }
         leaf laser-rx-power-high-alarm {
           type string;
           description
             "Laser receiver power high alarm";
         }
         leaf laser-rx-power-low-alarm {
           type string;
           description
             "Laser receiver power low alarm";
         }
         leaf laser-rx-power-high-warn {
           type string;
           description
             "Laser receiver power high warning";
         }
         leaf laser-rx-power-low-warn {
           type string;
           description
             "Laser receiver power low warning";
         }
         leaf rx-power-high-alarm {
           type string;
           description
             "Receiver power high alarm";
         }
         leaf rx-power-low-alarm {
           type string;
           description
             "Receiver power low alarm";
         }
         leaf rx-power-high-warn {
           type string;
           description
             "Receiver power high warning";
         }
         leaf rx-power-low-warn {
           type string;
           description
             "Receiver power low warning";
         }
         leaf laser-end-of-life-alarm {
           type string;
           description
             "Laser end-of-life alarm";
         }
         leaf laser-wavelength-alarm {
           type string;
           description
             "Laser wavelength alarm";
         }
         leaf laser-bias-current-alarm {
           type string;
           description
             "Laser bias current alarm";
         }
         leaf module-temperature-alarm {
           type string;
           description
             "Module temperature alarm";
         }
         leaf laser-power-alarm {
           type string;
           description
             "Laser power alarm";
         }
         leaf modulator-temperature-alarm {
           type string;
           description
             "Modulator temperature alarm";
         }
         leaf modulator-bias-alarm {
           type string;
           description
             "Modulator bias alarm";
         }
         leaf module-not-ready-alarm {
           type string;
           description
             "Module not ready alarm";
         }
         leaf module-power-down-alarm {
           type string;
           description
             "Module power down alarm";
         }
         leaf module-not-init-done-alarm {
           type string;
           description
             "Module initialization not done alarm";
         }
         leaf module-not-high-power-on-alarm {
           type string;
           description
             "Module not high powered on alarm";
         }
         leaf module-fault-alarm {
           type string;
           description
             "Module in fault state alarm";
         }
         leaf pld-flash-init-fault-alarm {
           type string;
           description
             "PLD or Flash initialization fault alarm";
         }
         leaf power-supply-fault-alarm {
           type string;
           description
             "Power supply fault alarm";
         }
         leaf checksum-fault-alarm {
           type string;
           description
             "Checksum fault alarm";
         }
         leaf apd-supply-fault-alarm {
           type string;
           description
             "APD supply fault alarm";
         }
         leaf tec-fault-alarm {
           type string;
           description
             "TEC fault alarm";
         }
         leaf wavelength-unlocked-alarm {
           type string;
           description
             "Wavelength unlocked alarm";
         }
         leaf tx-tune-alarm {
           type string;
           description
             "Tx tune alarm";
         }
         leaf tx-mux-fifo-error-alarm {
           type string;
           description
             "Tx multiplexer fifo error alarm";
         }
         leaf tx-loss-of-pll-alarm {
           type string;
           description
             "Tx loss of PLL alarm";
         }
         leaf tx-data-not-ready-alarm {
           type string;
           description
             "Tx data not ready alarm";
         }
         leaf tx-not-ready-alarm {
           type string;
           description
             "Tx not ready alarm";
         }
         leaf tx-laser-fault-alarm {
           type string;
           description
             "Tx laser fault alarm";
         }
         leaf tx-laser-disabled-alarm {
           type string;
           description
             "Tx laser disabled alarm";
         }
         leaf tx-loss-of-signal-functionality-alarm {
           type string;
           description
             "Tx loss of signal functionality alarm";
         }
         leaf tx-cdr-loss-of-lock-alarm {
           type string;
           description
             "Tx CDR loss of lock alarm";
         }
         leaf rx-loss-avg-opt-power-alarm {
           type string;
           description
             "Receiver loss of average optical power alarm";
         }
         leaf rx-loss-ac-power-alarm {
           type string;
           description
             "Receiver loss of AC power alarm";
         }
         leaf rx-loss-of-pll-alarm {
           type string;
           description
             "Receiver loss of PLL alarm";
         }
         leaf rx-not-ready-alarm {
           type string;
           description
             "Receiver not ready alarm";
         }
         leaf rx-loss-of-signal-alarm {
           type string;
           description
             "Receiver loss of signal alarm";
         }
         leaf rx-cdr-loss-of-lock-alarm {
           type string;
           description
             "Receiver CDR loss of lock alarm";
         }
         leaf laser-bias-current-high-alarm-threshold {
           type string;
           description
             "Laser bias current high alarm threshold (milliamperes)";
         }
         leaf laser-bias-current-low-alarm-threshold {
           type string;
           description
             "Laser bias current low alarm threshold (milliamperes)";
         }
         leaf laser-bias-current-high-warn-threshold {
           type string;
           description
             "Laser bias current high warning threshold (milliamperes)";
         }
         leaf laser-bias-current-low-warn-threshold {
           type string;
           description
             "Laser bias current low warning threshold (milliamperes)";
         }
         leaf soa-bias-current-high-alarm-threshold {
           type string;
           description
             "SOA bias current high alarm threshold (milliamperes)";
         }
         leaf soa-bias-current-low-alarm-threshold {
           type string;
           description
             "SOA bias current low alarm threshold (milliamperes)";
         }
         leaf soa-bias-current-high-warn-threshold {
           type string;
           description
             "SOA bias current high warning threshold (milliamperes)";
         }
         leaf soa-bias-current-low-warn-threshold {
           type string;
           description
             "SOA bias current low warning threshold (milliamperes)";
         }
         leaf laser-tx-power-high-alarm-threshold {
           type string;
           description
             "Laser transmitter power high alarm threshold (milliwatts)";
         }
         leaf laser-tx-power-high-alarm-threshold-dbm {
           type string;
           description
             "Laser transmitter power high alarm threshold (dBm)";
         }
         leaf laser-tx-power-low-alarm-threshold {
           type string;
           description
             "Laser transmitter power low alarm threshold (milliwatts)";
         }
         leaf laser-tx-power-low-alarm-threshold-dbm {
           type string;
           description
             "Laser transmitter power low alarm threshold (dBm)";
         }
         leaf laser-tx-power-high-warn-threshold {
           type string;
           description
             "Laser transmitter power high warning threshold (milliwatts)";
         }
         leaf laser-tx-power-high-warn-threshold-dbm {
           type string;
           description
             "Laser transmitter power high warning threshold (dBm)";
         }
         leaf laser-tx-power-low-warn-threshold {
           type string;
           description
             "Laser transmitter power low warning threshold (milliwatts)";
         }
         leaf laser-tx-power-low-warn-threshold-dbm {
           type string;
           description
             "Laser transmitter power low warning threshold (dBm)";
         }
         leaf module-temperature-high-alarm-threshold {
           type string;
           description
             "Module temperature high alarm threshold";
         }
         leaf module-temperature-low-alarm-threshold {
           type string;
           description
             "Module temperature low alarm threshold";
         }
         leaf module-temperature-high-warn-threshold {
           type string;
           description
             "Module temperature high warning threshold";
         }
         leaf module-temperature-low-warn-threshold {
           type string;
           description
             "Module temperature low warning threshold";
         }
         leaf laser-temperature-high-alarm-threshold {
           type string;
           description
             "Laser temperature high alarm threshold";
         }
         leaf laser-temperature-low-alarm-threshold {
           type string;
           description
             "Laser temperature low alarm threshold";
         }
         leaf laser-temperature-high-warn-threshold {
           type string;
           description
             "Laser temperature high warning threshold";
         }
         leaf laser-temperature-low-warn-threshold {
           type string;
           description
             "Laser temperature low warning threshold";
         }
         leaf module-voltage-high-alarm-threshold {
           type string;
           description
             "Module voltage high alarm threshold (volts)";
         }
         leaf module-voltage-low-alarm-threshold {
           type string;
           description
             "Module voltage low alarm threshold (volts)";
         }
         leaf module-voltage-high-warn-threshold {
           type string;
           description
             "Module voltage high warning threshold (volts)";
         }
         leaf module-voltage-low-warn-threshold {
           type string;
           description
             "Module voltage low warning threshold (volts)";
         }
         leaf laser-rx-power-high-alarm-threshold {
           type string;
           description
             "Laser receiver power high alarm (milliwatts)";
         }
         leaf laser-rx-power-high-alarm-threshold-dbm {
           type string;
           description
             "Laser receiver power high alarm (dBm)";
         }
         leaf laser-rx-power-low-alarm-threshold {
           type string;
           description
             "Laser receiver power low alarm (milliwatts)";
         }
         leaf laser-rx-power-low-alarm-threshold-dbm {
           type string;
           description
             "Laser receiver power low alarm (dBm)";
         }
         leaf laser-rx-power-high-warn-threshold {
           type string;
           description
             "Laser receiver power high warning (milliwatts)";
         }
         leaf laser-rx-power-high-warn-threshold-dbm {
           type string;
           description
             "Laser receiver power high warning (dBm)";
         }
         leaf laser-rx-power-low-warn-threshold {
           type string;
           description
             "Laser receiver power low warning (milliwatts)";
         }
         leaf laser-rx-power-low-warn-threshold-dbm {
           type string;
           description
             "Laser receiver power low warning (dBm)";
         }
         leaf rx-power-high-alarm-threshold {
           type string;
           description
             "Receiver power high alarm (milliwatts)";
         }
         leaf rx-power-high-alarm-threshold-dbm {
           type string;
           description
             "Receiver power high alarm (dBm)";
         }
         leaf rx-power-low-alarm-threshold {
           type string;
           description
             "Receiver power low alarm (milliwatts)";
         }
         leaf rx-power-low-alarm-threshold-dbm {
           type string;
           description
             "Receiver power low alarm (dBm)";
         }
         leaf rx-power-high-warning-threshold {
           type string;
           description
             "Receiver power high warning (milliwatts)";
         }
         leaf rx-power-high-warning-threshold-dbm {
           type string;
           description
             "Receiver power high warning (dBm)";
         }
         leaf rx-power-low-warning-threshold {
           type string;
           description
             "Receiver power low warning (milliwatts)";
         }
         leaf rx-power-low-warning-threshold-dbm {
           type string;
           description
             "Receiver power low warning (dBm)";
         }
         leaf los-alarm-threshold {
           type string;
           description
             "LOS alarm threshold (milliwatts)";
         }
         leaf los-alarm-threshold-dbm {
           type string;
           description
             "LOS alarm threshold (dBm)";
         }
         leaf los-warning-threshold {
           type string;
           description
             "LOS warning threshold (milliwatts)";
         }
         leaf los-warning-threshold-dbm {
           type string;
           description
             "LOS warning threshold (dBm)";
         }
         leaf dsp-module-state {
           type string;
           description
             "DSP module state";
         }
         leaf rx-pow-manual-threshold-enabled {
           type string;
           description
             "Manual RX Power High Alarm Threshold";
         }
         leaf rx-pow-high-alarm-threshold-manual {
           type string;
           description
             "Manual RX Power High Alarm Threshold";
         }
         leaf rx-pow-high-warning-threshold-manual {
           type string;
           description
             "Manual RX Power High Warning Threshold";
         }
         leaf rx-pow-low-warning-threshold-manual {
           type string;
           description
             "Manual RX Power Low Warning Threshold";
         }
         leaf rx-pow-low-alarm-threshold-manual {
           type string;
           description
             "Manual RX Power Low Alarm Threshold";
         }
         leaf output-power {
           type string;
           description
             "Output power (milliwatts)";
         }
         leaf output-power-dbm {
           type string;
           description
             "Output power (dBm)";
         }
         leaf input-power {
           type string;
           description
             "Input power (milliwatts)";
         }
         leaf input-power-dbm {
           type string;
           description
             "Input power (dBm)";
         }
         leaf per-wave-rx-optical-power {
           type string;
           description
             "Per-wavelength receiver optical power (milliwatts)";
         }
         leaf per-wave-rx-optical-power-dbm {
           type string;
           description
             "Per-wavelength receiver optical power (dBm)";
         }
         leaf lane-laser-frequency-error {
           type string;
           description
             "Lane laser frequency error (MHz)";
         }
         leaf tec-current {
           type string;
           description
             "Tec current";
         }
         leaf residual-isi {
           type string;
           description
             "Residual ISI";
         }
         container optics-diagnostics-ot {
           description
             "OT interface optics diagnostics";
           leaf module-temp-fault {
             type string;
             description
               "Module temperature fault";
           }
           leaf specific-hw-fault {
             type string;
             description
               "Specific HW fault";
           }
           leaf internal-power-fault {
             type string;
             description
               "Internal power fault";
           }
           leaf post-therm-fault {
             type string;
             description
               "Power thermal fault";
           }
           leaf post-fault {
             type string;
             description
               "Post fault";
           }
           leaf command-error {
             type string;
             description
               "Command error";
           }
           leaf rx-pll-lock {
             type string;
             description
               "RX PLL lock";
           }
           leaf network-lane-los {
             type string;
             description
               "Network Lane LOS";
           }
           leaf network-lane-lof {
             type string;
             description
               "Network Lane LOF";
           }
           leaf network-lane-oof {
             type string;
             description
               "Network Lane OOF";
           }
           leaf network-lane-lom {
             type string;
             description
               "Network Lane LOM";
           }
           leaf network-lane-oom {
             type string;
             description
               "Network Lane OOM";
           }
           leaf network-lane-otu-bdi {
             type string;
             description
               "Network Lane OTU BDI";
           }
           leaf lane-rx-fifo-error {
             type string;
             description
               "Lane RX FIFO error";
           }
           leaf tx-reference-clock-fault {
             type string;
             description
               "TX reference clock fault";
           }
           leaf rx-modem-sync-fault {
             type string;
             description
               "Rx modem sync fault";
           }
           leaf rx-modem-loss-of-lock {
             type string;
             description
               "RX modem loss of lock";
           }
           leaf rx-loss-of-alignment {
             type string;
             description
               "RX loss of alignment";
           }
           leaf rx-out-of-alignment {
             type string;
             description
               "RX out of alignment";
           }
           leaf rx-timing-fault {
             type string;
             description
               "Rx timing fault";
           }
           leaf link-msg-data-available {
             type string;
             description
               "Link msg data available";
           }
           leaf modulator-bias-control-loop-fail {
             type string;
             description
               "Modulator Bias Control Loop Fail";
           }
           leaf itla-fault {
             type string;
             description
               "ITLA fault";
           }
           leaf dac-calib-fault {
             type string;
             description
               "DAC calib fault";
           }
           leaf adc-calib-fault {
             type string;
             description
               "ADC calib fault";
           }
           leaf prom-fault {
             type string;
             description
               "PROM fault";
           }
           leaf tx-mod-bias-voa-ctrl-loop-high-alarm {
             type string;
             description
               "TX mod bias VOA ctrl loop high alarm";
           }
           leaf tx-mod-bias-voa-ctrl-loop-low-alarm {
             type string;
             description
               "TX mod bias VOA ctrl loop low alarm";
           }
           leaf rx-phase-control-loop-high-alarm {
             type string;
             description
               "RX phase control loop high alarm";
           }
           leaf rx-phase-control-loop-low-alarm {
             type string;
             description
               "RX phase control loop low alarm";
           }
           leaf rx-phase-control-loop-high-warning {
             type string;
             description
               "RX phase control loop high warning";
           }
           leaf rx-phase-control-loop-low-warning {
             type string;
             description
               "RX phase control loop low warning";
           }
           leaf oa-pump-bias-current-high-alarm {
             type string;
             description
               "OA pump bias current high alarm";
           }
           leaf oa-pump-bias-current-low-alarm {
             type string;
             description
               "OA pump bias current low alarm";
           }
           leaf oa-pump-bias-current-high-warning {
             type string;
             description
               "OA pump bias current high warning";
           }
           leaf oa-pump-bias-current-low-warning {
             type string;
             description
               "OA pump bias current low warning";
           }
           leaf tx-jitter-pll-lol-input-nw-lane {
             type string;
             description
               "Tx jitter PLL LOL i/p nw lane";
           }
           leaf tx-out-of-alignment {
             type string;
             description
               "TX out of alignment";
           }
           leaf tx-cmu-lock-fault {
             type string;
             description
               "Tx CMU lock fault";
           }
           leaf adc-signal-below-threshold {
             type string;
             description
               "ADC signal below threshold";
           }
           leaf tx-output-power-adjustment-fault {
             type string;
             description
               "Tx output power adjustment fault";
           }
           leaf tx-output-mod-converge-fault {
             type string;
             description
               "TX output mod converge fault";
           }
           leaf tx-laser-ready-fault {
             type string;
             description
               "Tx laser ready fault";
           }
           leaf tx-laser-ready-off-fault {
             type string;
             description
               "Tx laser ready off fault";
           }
           leaf tx-asic-ready-fault {
             type string;
             description
               "Tx asic ready fault";
           }
           leaf tx-initialization-fault {
             type string;
             description
               "Tx initialization fault";
           }
           leaf rx-demodulator-lock-fault {
             type string;
             description
               "Rx demodulator lock fault";
           }
           leaf rx-dispersion-lock-fault {
             type string;
             description
               "Rx dispersion lock fault";
           }
           leaf rx-adc-output-fault {
             type string;
             description
               "Rx ADC output fault";
           }
           leaf rx-optical-input-fault {
             type string;
             description
               "Rx optical input fault";
           }
           leaf rx-asic-ready-fault {
             type string;
             description
               "Rx asic ready fault";
           }
           leaf rx-initialization-fault {
             type string;
             description
               "Rx initialization fault";
           }
           leaf tx-mod-bias-high-alarm {
             type string;
             description
               "TX modulator bias high alarm";
           }
           leaf tx-mod-bias-low-alarm {
             type string;
             description
               "TX modulator bias low alarm";
           }
           leaf tx-mod-bias-high-warning {
             type string;
             description
               "TX modulator bias high warning";
           }
           leaf tx-mod-bias-low-warning {
             type string;
             description
               "TX modulator bias low warning";
           }
           leaf rx-pwr-high-alarm {
             type string;
             description
               "RX power high alarm";
           }
           leaf rx-pwr-low-alarm {
             type string;
             description
               "RX power low alarm";
           }
           leaf rx-pwr-high-warn {
             type string;
             description
               "RX power high warning";
           }
           leaf rx-pwr-low-warn {
             type string;
             description
               "RX power low warning";
           }
           leaf tx-laser-power-high-alarm {
             type string;
             description
               "TX laser power high alarm";
           }
           leaf tx-laser-power-low-alarm {
             type string;
             description
               "TX laser power low alarm";
           }
           leaf tx-laser-power-high-warn {
             type string;
             description
               "TX laser power high warning";
           }
           leaf tx-laser-power-low-warn {
             type string;
             description
               "TX laser power low warning";
           }
           leaf tx-bias-high-alarm {
             type string;
             description
               "TX laser current high alarm";
           }
           leaf tx-bias-low-alarm {
             type string;
             description
               "TX laser current low alarm";
           }
           leaf tx-bias-high-warn {
             type string;
             description
               "TX laser current high warning";
           }
           leaf tx-bias-low-warn {
             type string;
             description
               "TX laser current low warning";
           }
           leaf tx-laser-temp-high-alarm {
             type string;
             description
               "TX laser temperature high alarm";
           }
           leaf tx-laser-temp-low-alarm {
             type string;
             description
               "TX laser temperature low alarm";
           }
           leaf tx-laser-temp-high-warn {
             type string;
             description
               "TX laser temperature high warning";
           }
           leaf tx-laser-temp-low-warn {
             type string;
             description
               "TX laser temperature low warning";
           }
         }
         list optics-diagnostics-lane-values {
           key "lane-index";
           leaf lane-index {
             type int32;
           }
           leaf laser-bias-current {
             type string;
             description
               "Laser bias current (milliamperes)";
           }
           leaf laser-bias-current-not-available {
             type string;
             description
               "Laser bias current measurement not available";
           }
           leaf laser-output-power {
             type string;
             description
               "Laser output power (milliwatts)";
           }
           leaf laser-output-power-dbm {
             type string;
             description
               "Laser output power (dBm)";
           }
           leaf output-power {
             type string;
             description
               "Output power (milliwatts)";
           }
           leaf output-power-dbm {
             type string;
             description
               "Output power (dBm)";
           }
           leaf laser-temperature {
             type string;
             description
               "Laser temperature";
           }
           leaf laser-module-temperature {
             type string;
             description
               "Module temperature";
           }
           leaf laser-tx-optical-power {
             type string;
             description
               "Laser transmitter optical power (milliwatts)";
           }
           leaf laser-tx-optical-power-dbm {
             type string;
             description
               "Laser transmitter optical power (dBm)";
           }
           leaf laser-rx-optical-power {
             type string;
             description
               "Laser receiver optical power (milliwatts)";
           }
           leaf laser-rx-optical-power-dbm {
             type string;
             description
               "Laser receiver optical power (dBm)";
           }
           leaf input-power {
             type string;
             description
               "Input power (milliwatts)";
           }
           leaf input-power-dbm {
             type string;
             description
               "Input power (dBm)";
           }
           leaf input-total-power {
             type string;
             description
               "Input power (total) (milliwatts)";
           }
           leaf input-total-power-dbm {
             type string;
             description
               "Input power (dBm)";
           }
           leaf per-wave-rx-optical-power {
             type string;
             description
               "Per-wavelength receiver optical power (milliwatts)";
           }
           leaf per-wave-rx-optical-power-dbm {
             type string;
             description
               "Per-wavelength receiver optical power (dBm)";
           }
           leaf lane-configured-cd {
             type string;
             description
               "Lane configured chromatic dispersion (ps/nm)";
           }
           leaf lane-chromatic-dispersion {
             type string;
             description
               "Lane chromatic dispersion (ps/nm)";
           }
           leaf lane-avg-chromatic-dispersion {
             type string;
             description
               "Lane avg chromatic dispersion (ps/nm)";
           }
           leaf lane-min-chromatic-dispersion {
             type string;
             description
               "Lane min chromatic dispersion (ps/nm)";
           }
           leaf lane-max-chromatic-dispersion {
             type string;
             description
               "Lane max chromatic dispersion (ps/nm)";
           }
           leaf lane-differential-group-delay {
             type string;
             description
               "Lane differential group delay (ps)";
           }
           leaf lane-avg-differential-group-delay {
             type string;
             description
               "Lane avg differential group delay (ps)";
           }
           leaf lane-min-differential-group-delay {
             type string;
             description
               "Lane min differential group delay (ps)";
           }
           leaf lane-max-differential-group-delay {
             type string;
             description
               "Lane max differential group delay (ps)";
           }
           leaf lane-sopmd {
             type string;
             description
               "Lane sopmd";
           }
           leaf lane-avg-sopmd {
             type string;
             description
               "Lane avg sopmd";
           }
           leaf lane-min-sopmd {
             type string;
             description
               "Lane min sopmd";
           }
           leaf lane-max-sopmd {
             type string;
             description
               "Lane max sopmd";
           }
           leaf q-factor {
             type string;
             description
               "Lane q-factor";
           }
           leaf q-factor-not-available {
             type string;
             description
               "Lane q-factor not available";
           }
           leaf q-margin {
             type string;
             description
               "Lane q-margin";
           }
           leaf q-margin-not-available {
             type string;
             description
               "Lane q-margin not available";
           }
           leaf lane-state-of-polarization {
             type string;
             description
               "Lane state of polarization (rad/s)";
           }
           leaf lane-avg-state-of-polarization {
             type string;
             description
               "Lane avg state of polarization (rad/s)";
           }
           leaf lane-min-state-of-polarization {
             type string;
             description
               "Lane min state of polarization (rad/s)";
           }
           leaf lane-max-state-of-polarization {
             type string;
             description
               "Lane max state of polarization (rad/s)";
           }
           leaf lane-polarization-dependent-loss {
             type string;
             description
               "Lane polarization dependent loss (dB)";
           }
           leaf lane-avg-polarization-dependent-loss {
             type string;
             description
               "Lane avg polarization dependent loss (dB)";
           }
           leaf lane-min-polarization-dependent-loss {
             type string;
             description
               "Lane min polarization dependent loss (dB)";
           }
           leaf lane-max-polarization-dependent-loss {
             type string;
             description
               "Lane max polarization dependent loss (dB)";
           }
           leaf lane-q2-factor {
             type string;
             description
               "Lane Q2 factor (dB)";
           }
           leaf lane-q-value {
             type string;
             description
               "Lane q value (dB)";
           }
           leaf lane-avg-q-value {
             type string;
             description
               "Lane avg q value (dB)";
           }
           leaf lane-min-q-value {
             type string;
             description
               "Lane min q value (dB)";
           }
           leaf lane-max-q-value {
             type string;
             description
               "Lane max q value (dB)";
           }
           leaf lane-carrier-frequency-offset {
             type string;
             description
               "Lane carrier frequency offset (MHz)";
           }
           leaf lane-avg-carrier-frequency-offset {
             type string;
             description
               "Lane avg carrier frequency offset (MHz)";
           }
           leaf lane-min-carrier-frequency-offset {
             type string;
             description
               "Lane min carrier frequency offset (MHz)";
           }
           leaf lane-max-carrier-frequency-offset {
             type string;
             description
               "Lane max carrier frequency offset (MHz)";
           }
           leaf lane-electrical-snr {
             type string;
             description
               "Lane electrical SNR (dB)";
           }
           leaf lane-snr {
             type string;
             description
               "Lane snr (dB)";
           }
           leaf lane-avg-snr {
             type string;
             description
               "Lane avg snr (dB)";
           }
           leaf lane-min-snr {
             type string;
             description
               "Lane min snr (dB)";
           }
           leaf lane-max-snr {
             type string;
             description
               "Lane max snr (dB)";
           }
           leaf lane-rx-laser-bias {
             type string;
             description
               "Lane rx laser bias (mA)";
           }
           leaf lane-rx-laser-power {
             type string;
             description
               "Lane rx laser power (dBm)";
           }
           leaf lane-rx-laser-temp {
             type string;
             description
               "Lane rx laser temp (C)";
           }
           leaf lane-tx-modulator-bias-x-i {
             type string;
             description
               "Lane tx modulator bias x i (mV)";
           }
           leaf lane-tx-modulator-bias-x-q {
             type string;
             description
               "Lane tx modulator bias x q (mV)";
           }
           leaf lane-tx-modulator-bias-y-i {
             type string;
             description
               "Lane tx modulator bias y i (mV)";
           }
           leaf lane-tx-modulator-bias-y-q {
             type string;
             description
               "Lane tx modulator bias y q (mV)";
           }
           leaf lane-tx-modulator-bias-x-phase {
             type string;
             description
               "Lane tx modulator bias x phase (mV)";
           }
           leaf lane-tx-modulator-bias-y-phase {
             type string;
             description
               "Lane tx modulator bias y phase (mV)";
           }
           leaf tx-input-equalization {
             type string;
             description
               "Tx input equalization";
           }
           leaf rx-output-amplitude {
             type string;
             description
               "Rx output amplitude";
           }
           leaf rx-output-pre-emphasis {
             type string;
             description
               "Rx output pre epmhasis";
           }
           leaf lane-laser-frequency-error {
             type string;
             description
               "Lane laser frequency error (MHz)";
           }
           leaf tec-current {
             type string;
             description
               "Tec current";
           }
           leaf residual-isi {
             type string;
             description
               "Residual ISI";
           }
           leaf pam-histogram {
             type string;
             description
               "PAM histogram";
           }
           leaf laser-bias-current-high-alarm {
             type string;
             description
               "Laser bias current high alarm";
           }
           leaf laser-bias-current-low-alarm {
             type string;
             description
               "Laser bias current low alarm";
           }
           leaf laser-bias-current-high-warn {
             type string;
             description
               "Laser bias current high warning";
           }
           leaf laser-bias-current-low-warn {
             type string;
             description
               "Laser bias current low warning";
           }
           leaf laser-tx-power-high-alarm {
             type string;
             description
               "Laser output power high alarm";
           }
           leaf laser-tx-power-low-alarm {
             type string;
             description
               "Laser output power low alarm";
           }
           leaf laser-tx-power-high-warn {
             type string;
             description
               "Laser output power high warning";
           }
           leaf laser-tx-power-low-warn {
             type string;
             description
               "Laser output power low warning";
           }
           leaf tx-power-high-alarm {
             type string;
             description
               "Tx power high alarm";
           }
           leaf tx-power-low-alarm {
             type string;
             description
               "Tx power low alarm";
           }
           leaf tx-power-high-warn {
             type string;
             description
               "Tx power high warning";
           }
           leaf tx-power-low-warn {
             type string;
             description
               "Tx power low warning";
           }
           leaf laser-temp-high-alarm {
             type string;
             description
               "Laser temperature high alarm";
           }
           leaf laser-temp-low-alarm {
             type string;
             description
               "Laser temperature low alarm";
           }
           leaf laser-temp-high-warn {
             type string;
             description
               "Laser temperature high warning";
           }
           leaf laser-temp-low-warn {
             type string;
             description
               "Laser temperature low warning";
           }
           leaf laser-rx-power-high-alarm {
             type string;
             description
               "Laser receiver power high alarm";
           }
           leaf laser-rx-power-low-alarm {
             type string;
             description
               "Laser receiver power low alarm";
           }
           leaf laser-rx-power-high-warn {
             type string;
             description
               "Laser receiver power high warning";
           }
           leaf laser-rx-power-low-warn {
             type string;
             description
               "Laser receiver power low warning";
           }
           leaf rx-power-high-alarm {
             type string;
             description
               "Receiver power high alarm";
           }
           leaf rx-power-low-alarm {
             type string;
             description
               "Receiver power low alarm";
           }
           leaf rx-power-high-warn {
             type string;
             description
               "Receiver power high warning";
           }
           leaf rx-power-low-warn {
             type string;
             description
               "Receiver power low warning";
           }
           leaf tx-loss-of-signal-functionality-alarm {
             type string;
             description
               "Tx loss of signal functionality alarm";
           }
           leaf rx-loss-of-signal-functionality-alarm {
             type string;
             description
               "Rx loss of signal functionality alarm";
           }
           leaf tx-cdr-loss-of-lock-alarm {
             type string;
             description
               "Tx CDR loss of lock alarm";
           }
           leaf tx-loss-of-signal-alarm {
             type string;
             description
               "Transmitter loss of signal alarm";
           }
           leaf rx-loss-of-signal-alarm {
             type string;
             description
               "Receiver loss of signal alarm";
           }
           leaf tx-laser-disabled-alarm {
             type string;
             description
               "Tx laser disabled alarm";
           }
           leaf rx-cdr-loss-of-lock-alarm {
             type string;
             description
               "Receiver CDR loss of lock alarm";
           }
           leaf tec-fault-alarm {
             type string;
             description
               "TEC fault alarm";
           }
           leaf wavelength-unlocked-alarm {
             type string;
             description
               "Wavelength unlocked alarm";
           }
           leaf apd-supply-fault-alarm {
             type string;
             description
               "APD supply fault alarm";
           }
           leaf tx-channel-disabled-alarm {
             type string;
             description
               "Tx channel disabled alarm";
           }
           leaf rx-channel-disabled-alarm {
             type string;
             description
               "Rx channel disabled alarm";
           }
           leaf tx-output-disabled-alarm {
             type string;
             description
               "Rx laser disabled alarm";
           }
           leaf rx-output-disabled-alarm {
             type string;
             description
               "Rx laser disabled alarm";
           }
           leaf tx-squelch-disabled-alarm {
             type string;
             description
               "Tx squelch disabled alarm";
           }
           leaf rx-squelch-disabled-alarm {
             type string;
             description
               "Rx squelch disabled alarm";
           }
           leaf laser-end-of-life-alarm {
             type string;
             description
               "Laser end-of-life alarm";
           }
           leaf lane-cd {
             type string;
             description
               "Lane chromatic dispersion";
           }
           leaf lane-dgd {
             type string;
             description
               "Lane differential group delay";
           }
           leaf lane-cfo {
             type string;
             description
               "Lane carrier frequency offset";
           }
           leaf lane-pdl {
             type string;
             description
               "Lane polarization dependent loss";
           }
           leaf lane-osnr {
             type string;
             description
               "Optical signal-to-noise ratio(dB)";
           }
         }
       }
       container optics-diagnostics-vendor-extension {
         description
           "Optics diagnostics vendor extension";
         leaf optics-vendor-part-number {
           type string;
           description
             "Optics component vendor part number";
         }
         leaf optics-vendor-material-number {
           type string;
           description
             "Optic component vendor material number";
         }
       }
       list optics-chromatics {
         key "optics-chromatic-diagnostics-support";
         leaf optics-chromatic-diagnostics-support {
           type string;
           description
             "Optics chromatic not supported for interface";
         }
         leaf opticstype {
           type string;
           description
             "Type of optical module";
         }
         list optics-chromatic {
           key "supported-cd supported-mediaid";
           leaf supported-speed {
             type string;
             description
               "Supported Speed";
           }
           leaf supported-cd {
             type string;
             description
               "Supported Chromatic Dispersion";
           }
           leaf supported-distance {
             type string;
             description
               "Supported Distance";
           }
           leaf supported-mediaid {
             type string;
             description
               "Supported Mediaid";
           }
         }
       }
       list jrr-optics-diagnostics {
         description
           "Optics diagnostics";
         leaf jrr-optics-diagnostics-not-available {
           type string;
           description
             "Optical diagnostics not available at this time for this 
             transceiver";
         }
         leaf laser-bias-current {
           type string;
           description
             "Laser bias current (milliamperes)";
         }
         leaf laser-output-power {
           type string;
           description
             "Laser output power (milliwatts)";
         }
         leaf module-temperature {
           type string;
           description
             "Module temperature";
         }
         leaf module-voltage {
           type string;
           description
             "Module voltage";
         }
         leaf module-max-power {
           type string;
           description
             "Module max power";
         }
         leaf rx-signal-avg-optical-power {
           type string;
           description
             "Receiver signal average power (milliwatts)";
         }
         leaf laser-bias-current-high-alarm {
           type string;
           description
             "Laser bias current high alarm";
         }
         leaf laser-bias-current-low-alarm {
           type string;
           description
             "Laser bias current low alarm";
         }
         leaf laser-bias-current-high-warn {
           type string;
           description
             "Laser bias current high warning";
         }
         leaf laser-bias-current-low-warn {
           type string;
           description
             "Laser bias current low warning";
         }
         leaf laser-tx-power-high-alarm {
           type string;
           description
             "Laser output power high alarm";
         }
         leaf laser-tx-power-low-alarm {
           type string;
           description
             "Laser output power low alarm";
         }
         leaf laser-tx-power-high-warn {
           type string;
           description
             "Laser output power high warning";
         }
         leaf laser-tx-power-low-warn {
           type string;
           description
             "Laser output power low warning";
         }
         leaf module-temperature-high-alarm {
           type string;
           description
             "Module temperature high alarm";
         }
         leaf module-temperature-low-alarm {
           type string;
           description
             "Module temperature low alarm";
         }
         leaf module-temperature-high-warn {
           type string;
           description
             "Module temperature high warning";
         }
         leaf module-temperature-low-warn {
           type string;
           description
             "Module temperature low warning";
         }
         leaf module-voltage-high-alarm {
           type string;
           description
             "Module voltage high alarm";
         }
         leaf module-voltage-low-alarm {
           type string;
           description
             "Module voltage low alarm";
         }
         leaf module-voltage-high-warn {
           type string;
           description
             "Module voltage high warning";
         }
         leaf module-voltage-low-warn {
           type string;
           description
             "Module voltage low warning";
         }
         leaf laser-rx-power-high-alarm {
           type string;
           description
             "Laser receiver power high alarm";
         }
         leaf laser-rx-power-low-alarm {
           type string;
           description
             "Laser receiver power low alarm";
         }
         leaf laser-rx-power-high-warn {
           type string;
           description
             "Laser receiver power high warning";
         }
         leaf laser-rx-power-low-warn {
           type string;
           description
             "Laser receiver power low warning";
         }
         leaf laser-bias-current-high-alarm-threshold {
           type string;
           description
             "Laser bias current high alarm threshold (milliamperes)";
         }
         leaf laser-bias-current-low-alarm-threshold {
           type string;
           description
             "Laser bias current low alarm threshold (milliamperes)";
         }
         leaf laser-bias-current-high-warn-threshold {
           type string;
           description
             "Laser bias current high warning threshold (milliamperes)";
         }
         leaf laser-bias-current-low-warn-threshold {
           type string;
           description
             "Laser bias current low warning threshold (milliamperes)";
         }
         leaf laser-tx-power-high-alarm-threshold {
           type string;
           description
             "Laser transmitter power high alarm threshold (milliwatts)";
         }
         leaf laser-tx-power-low-alarm-threshold {
           type string;
           description
             "Laser transmitter power low alarm threshold (milliwatts)";
         }
         leaf laser-tx-power-high-warn-threshold {
           type string;
           description
             "Laser transmitter power high warning threshold (milliwatts)";
         }
         leaf laser-tx-power-low-warn-threshold {
           type string;
           description
             "Laser transmitter power low warning threshold (milliwatts)";
         }
         leaf module-temperature-high-alarm-threshold {
           type string;
           description
             "Module temperature high alarm threshold";
         }
         leaf module-temperature-low-alarm-threshold {
           type string;
           description
             "Module temperature low alarm threshold";
         }
         leaf module-temperature-high-warn-threshold {
           type string;
           description
             "Module temperature high warning threshold";
         }
         leaf module-temperature-low-warn-threshold {
           type string;
           description
             "Module temperature low warning threshold";
         }
         leaf module-voltage-high-alarm-threshold {
           type string;
           description
             "Module voltage high alarm threshold (volts)";
         }
         leaf module-voltage-low-alarm-threshold {
           type string;
           description
             "Module voltage low alarm threshold (volts)";
         }
         leaf module-voltage-high-warn-threshold {
           type string;
           description
             "Module voltage high warning threshold (volts)";
         }
         leaf module-voltage-low-warn-threshold {
           type string;
           description
             "Module voltage low warning threshold (volts)";
         }
         leaf laser-rx-power-high-alarm-threshold {
           type string;
           description
             "Laser receiver power high alarm (milliwatts)";
         }
         leaf laser-rx-power-low-alarm-threshold {
           type string;
           description
             "Laser receiver power low alarm (milliwatts)";
         }
         leaf laser-rx-power-high-warn-threshold {
           type string;
           description
             "Laser receiver power high warning (milliwatts)";
         }
         leaf laser-rx-power-low-warn-threshold {
           type string;
           description
             "Laser receiver power low warning (milliwatts)";
         }
       }
       container optics-properties {
         description
           "Optics properties";
         leaf wavelength {
           type string;
           description
             "Wavelength of optics in nanometers";
         }
         leaf frequency {
           type string;
           description
             "Frequency of optics in terahertz";
         }
         leaf optic-loopback {
           type string;
           description
             "Optic loopback status";
         }
         leaf optic-loopback-type {
           type string;
           description
             "Optic loopback type";
         }
         leaf media-code-desc {
           type string;
           description
             "Current optics media code";
         }
         leaf host-code-desc {
           type string;
           description
             "Current optics host code";
         }
       }
       container queue-counters {
         description
           "Queue counter statistics";
         leaf queue-counters-error-message {
           type string;
           description
             "Queue statistics not available for this interface";
         }
         container interface-cos-short-summary {
           description
             "Summary of queue information on an interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
         }
         list queue {
           key "queue-number";
           description
             "Counters for a single queue";
           leaf queue-number {
             type uint32;
             description
               "Queue number";
           }
           leaf queue-counters-queued-packets {
             type int32;
             description
               "Queued packet count";
           }
           leaf queue-counters-trans-packets {
             type int32;
             description
               "Total number of transmitted packets";
           }
           leaf queue-counters-total-drop-packets {
             type int32;
             description
               "Number of total packets dropped at the queue";
           }
           leaf forwarding-class-name {
             type string;
             description
               "Forwarding class name associated with queue";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-queued-packets-na {
             type string;
             description
               "Queued packets not available";
           }
           leaf queue-counters-queued-bytes-na {
             type string;
             description
               "Queued bytes not available";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets-na {
             type string;
             description
               "Number of packets dropped due to tail drop not available";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of packets dropped at tail drop of the queue";
           }
           leaf queue-counters-tail-drop-bytes-rate {
             type int32;
             description
               "Number of packets dropped at tail drop of the queue";
           }
           leaf queue-counters-ecn-ce-packets {
             type int32;
             description
               "Total number of ECN CE packets";
           }
           leaf queue-counters-ecn-ce-packets-rate {
             type int32;
             description
               "Rate at which ECN CE packets are transmitted";
           }
           leaf queue-counters-ecn-ce-bytes {
             type int32;
             description
               "Total number of ECN CE bytes";
           }
           leaf queue-counters-ecn-ce-bytes-rate {
             type int32;
             description
               "Rate at which ECN CE bytes are transmitted";
           }
           leaf queue-counters-rate-limit-drop-packets-na {
             type string;
             description
               "Number of packets dropped due to rate-limit drop not 
               available";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes-na {
             type string;
             description
               "Number of bytes dropped due to tail drop not available";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets-na {
             type string;
             description
               "Number of packets dropped due to RED not available";
           }
           leaf queue-counters-red-packets {
             type int32;
             description
               "Number of packets dropped due to RED";
           }
           leaf queue-counters-red-packets-rate {
             type int32;
             description
               "Rate at which packets are dropped due to RED";
           }
           leaf queue-counters-red-packets-ln {
             type int32;
             description
               "Number of RED dropped low-loss, non-TCP packets";
           }
           leaf queue-counters-red-packets-rate-ln {
             type int32;
             description
               "RED drop rate for low-loss, non-TCP packets";
           }
           leaf queue-counters-red-packets-lt {
             type int32;
             description
               "Number of RED dropped of low-loss, TCP packets";
           }
           leaf queue-counters-red-packets-rate-lt {
             type int32;
             description
               "RED drop rate for low-loss, TCP packets";
           }
           leaf queue-counters-red-packets-hn {
             type int32;
             description
               "Number of RED dropped high-loss, non-TCP packets";
           }
           leaf queue-counters-red-packets-rate-hn {
             type int32;
             description
               "RED drop rate for high-loss, non-TCP packets";
           }
           leaf queue-counters-red-packets-ht {
             type int32;
             description
               "Number of RED dropped high-loss, TCP packets";
           }
           leaf queue-counters-red-packets-rate-ht {
             type int32;
             description
               "RED drop rate for high-loss, TCP packets";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-medium {
             type int32;
             description
               "Number of RED dropped medium-loss packets";
           }
           leaf queue-counters-red-packets-rate-medium {
             type int32;
             description
               "RED drop rate for medium-loss packets";
           }
           leaf queue-counters-red-packets-high {
             type int32;
             description
               "Number of RED dropped high-loss packets";
           }
           leaf queue-counters-red-packets-rate-high {
             type int32;
             description
               "RED drop rate for high-loss packets";
           }
           leaf queue-counters-red-bytes-na {
             type string;
             description
               "Number of bytes dropped due to RED not available";
           }
           leaf queue-counters-red-bytes {
             type int32;
             description
               "Number of bytes dropped due to RED";
           }
           leaf queue-counters-red-bytes-rate {
             type int32;
             description
               "Rate at which bytes are dropped due to RED";
           }
           leaf queue-counters-red-bytes-ln {
             type int32;
             description
               "Number of RED dropped low-loss, non-TCP bytes";
           }
           leaf queue-counters-red-bytes-rate-ln {
             type int32;
             description
               "RED drop rate for low-loss, non-TCP bytes";
           }
           leaf queue-counters-red-bytes-lt {
             type int32;
             description
               "Number of RED dropped low-loss, TCP bytes";
           }
           leaf queue-counters-red-bytes-rate-lt {
             type int32;
             description
               "RED drop rate for low-loss, TCP bytes";
           }
           leaf queue-counters-red-bytes-hn {
             type int32;
             description
               "Number of RED dropped high-loss, non-TCP bytes";
           }
           leaf queue-counters-red-bytes-rate-hn {
             type int32;
             description
               "RED drop rate for high-loss, non-TCP bytes";
           }
           leaf queue-counters-red-bytes-ht {
             type int32;
             description
               "Number of RED dropped high-loss, TCP bytes";
           }
           leaf queue-counters-red-bytes-rate-ht {
             type int32;
             description
               "RED drop rate for high-loss, TCP bytes";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-medium {
             type int32;
             description
               "Number of RED dropped medium-loss bytes";
           }
           leaf queue-counters-red-bytes-rate-medium {
             type int32;
             description
               "RED drop rate for medium-loss bytes";
           }
           leaf queue-counters-red-bytes-high {
             type int32;
             description
               "Number of RED dropped high-loss bytes";
           }
           leaf queue-counters-red-bytes-rate-high {
             type int32;
             description
               "RED drop rate for high-loss bytes";
           }
           leaf queue-counters-timestamp {
             type int32;
             description
               "Last packet enqueued timestamp";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
           leaf queue-counters-reserved-buffer-packets {
             type int32;
             description
               "Queues's usage of reserved buffer pool in pkts";
           }
           leaf queue-counters-reserved-buffer-bytes {
             type int32;
             description
               "Queues's usage of reserved buffer pool in bytes";
           }
           leaf queue-counters-shared-buffer-packets {
             type int32;
             description
               "Queues's usage of shared buffer pool in pkts";
           }
           leaf queue-counters-shared-buffer-bytes {
             type int32;
             description
               "Queues's usage of shared buffer pool in bytes";
           }
           leaf queue-counters-depth-average {
             type int32;
             description
               "Time averaged queue depth";
           }
           leaf queue-counters-depth-current {
             type int32;
             description
               "Current instantaneous queue depth";
           }
           leaf queue-counters-depth-peak {
             type int32;
             description
               "Peak queue depth";
           }
           leaf queue-counters-depth-max {
             type int32;
             description
               "Maximum queue depth attained";
           }
           leaf queue-counters-srx-reserved-buffer-bytes {
             type int32;
             description
               "Queues's usage of reserved buffer pool in bytes";
           }
           leaf queue-counters-srx-depth-current {
             type int32;
             description
               "Current instantaneous queue depth";
           }
         }
         container interface-cos-summary {
           description
             "Summary of forwarding class and queue information on an 
             interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
           leaf intf-cos-burst-size-for-ifl {
             type int32;
             description
               "Burst size for the logical interface";
           }
         }
       }
       container voq-counters {
         description
           "VOQ counter statistics";
         leaf voq-counters-error-message {
           type string;
           description
             "VOQ statistics not available for this interface";
         }
         container voq {
           description
             "Counters for a single voq";
           container fpc {
             description
               "Counters for a single FPC";
             leaf fpc-no {
               type int32;
               description
                 "FPC number";
             }
             container pfe {
               description
                 "Counters for a single PFE";
               leaf-list pfe-no {
                 type int32;
                 description
                   "PFE number";
               }
               leaf voq-counters-tail-drop-packets {
                 type int32;
                 description
                   "Tail DROP packet count";
               }
               leaf voq-counters-tail-drop-packets-rate {
                 type int32;
                 description
                   "Rate at which tail packets are dropped";
               }
               leaf voq-counters-tail-drop-bytes {
                 type int32;
                 description
                   "Tail DROP bytes count";
               }
               leaf voq-counters-tail-drop-bytes-rate {
                 type int32;
                 description
                   "Rate at which tail bytes are dropped";
               }
               leaf voq-counters-drop-packets {
                 type int32;
                 description
                   "DROP packet count";
               }
               leaf voq-counters-drop-packets-rate {
                 type int32;
                 description
                   "Rate at which packets are dropped";
               }
               leaf voq-counters-drop-bytes {
                 type int32;
                 description
                   "DROP bytes count";
               }
               leaf voq-counters-drop-bytes-rate {
                 type int32;
                 description
                   "Rate at which bytes are dropped";
               }
               leaf voq-counters-queued-packets {
                 type int32;
                 description
                   "QUEUED packets count";
               }
               leaf voq-counters-queued-packets-rate {
                 type int32;
                 description
                   "Rate at which packets are queued";
               }
               leaf voq-counters-queued-bytes {
                 type int32;
                 description
                   "QUEUED bytes count";
               }
               leaf voq-counters-queued-bytes-rate {
                 type int32;
                 description
                   "Rate at which bytes are queued";
               }
               leaf voq-counters-transmitted-packets {
                 type int32;
                 description
                   "Transmitted packets count";
               }
               leaf voq-counters-transmitted-packets-rate {
                 type int32;
                 description
                   "Rate at which packets are transmitted";
               }
               leaf voq-counters-transmitted-bytes {
                 type int32;
                 description
                   "Transmitted bytes count";
               }
               leaf voq-counters-transmitted-bytes-rate {
                 type int32;
                 description
                   "Rate at which bytes are transmitted";
               }
               leaf voq-counters-queue-depth-bytes-current {
                 type int32;
                 description
                   "Current queue length";
               }
               leaf voq-counters-queue-depth-bytes-peak {
                 type int32;
                 description
                   "Peak queue length";
               }
               leaf voq-counters-queue-depth-bytes-average {
                 type int32;
                 description
                   "Average queue length";
               }
             }
           }
           leaf queue-number {
             type uint32;
             description
               "Queue number";
           }
           leaf forwarding-class-name {
             type string;
             description
               "Forwarding class name associated with queue";
           }
           leaf restricted-forwarding-class-name {
             type string;
           }
         }
       }
       container smart-sfp-av-titan-statistics {
         description
           "AimValley Smart SFP statistics";
         leaf smart-sfp-av-titan-error-message {
           type string;
           description
             "AV Smart SFP un-available";
         }
         container smart-sfp-av-titan-eth-port-statistics {
           leaf rx-crct-frames {
             type uint32;
           }
           leaf rx-crct-bytes {
             type uint32;
           }
           leaf rx-fragments {
             type uint32;
           }
           leaf rx-crct-unicast-frames {
             type uint32;
           }
           leaf rx-crct-multicast-frames {
             type uint32;
           }
           leaf rx-crct-broadcast-frames {
             type uint32;
           }
           leaf rx-err-fcs-frames {
             type uint32;
           }
           leaf rx-len-err-frames {
             type uint32;
           }
           leaf rx-undersize-frames {
             type uint32;
           }
           leaf rx-oversize-frames {
             type uint32;
           }
           leaf rx-inv-vlan-mismatch-frames {
             type uint32;
           }
           leaf rx-discarded-frames {
             type uint32;
           }
           leaf rx-dropped-q-overflow-frames {
             type uint32;
           }
           leaf tx-frames {
             type uint32;
           }
           leaf tx-bytes {
             type uint32;
           }
           leaf tx-unicast-frames {
             type uint32;
           }
           leaf tx-multicast-frames {
             type uint32;
           }
           leaf tx-broadcast-frames {
             type uint32;
           }
         }
         container smart-sfp-av-titan-iwf-statistics {
           leaf rx-packets {
             type uint32;
           }
           leaf tx-packets {
             type uint32;
           }
           leaf malformed-packets {
             type uint32;
           }
           leaf reordered-packets {
             type uint32;
           }
           leaf misordered-dropped-packets {
             type uint32;
           }
           leaf missing-packets {
             type uint32;
           }
           leaf played-out-packets {
             type uint32;
           }
           leaf jb-overrun {
             type uint32;
           }
           leaf jb-underrun {
             type uint32;
           }
         }
         container smart-sfp-av-titan-ds3-statistics {
           leaf rx-bpvexzerrors {
             type uint32;
           }
           leaf rx-cvperrors {
             type uint32;
           }
           leaf b3-errors {
             type uint32;
           }
         }
         container smart-sfp-av-titan-stm-statistics {
           leaf rx-b1-errors {
             type uint32;
           }
           leaf tx-b1-errors {
             type uint32;
           }
         }
       }
       container smart-sfp-av-titan-defects {
         description
           "AimValley Smart SFP defects";
         container smart-sfp-av-titan-defect-list {
           leaf sfp-tdm-defects {
             type string;
           }
           leaf sfp-system-defects {
             type string;
           }
         }
       }
       container forwarding-class-counters {
         description
           "Forwarding-class counter statistics";
         leaf forwarding-class-counters-error-message {
           type string;
           description
             "Forwarding-class statistics not available for this interface";
         }
         container ipv4-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container ipv6-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container mpls-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container layer2-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container other-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container protocol-aggregate-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container forwarding-class-statistics {
           container protocol-aggregate-forwarding-class-counters {
           }
           container ipv4-forwarding-class-counters {
           }
           container ipv6-forwarding-class-counters {
           }
           container mpls-forwarding-class-counters {
           }
           container layer2-forwarding-class-counters {
           }
           container other-forwarding-class-counters {
           }
         }
         container forwarding-class-accounting-parameters {
           leaf forwarding-class-accounting-for-protocol {
             type string;
           }
           leaf forwarding-class-accounting-for-traffic-direction {
             type string;
           }
           leaf forwarding-class-accounting-for-traffic-type {
             type string;
           }
           leaf forwarding-class-accounting-overhead-bytes {
             type uint32;
           }
         }
         container per-forwarding-class-counters {
           leaf fc_name_header {
             type string;
           }
           leaf forwarding-class-name {
             type string;
             description
               "Forwarding class name associated with queue";
           }
           leaf fc-input-bytes {
             type int32;
           }
           leaf fc-input-bytes-rate {
             type int32;
             description
               "Input bytes rate";
           }
           leaf fc-output-bytes {
             type int32;
           }
           leaf fc-output-bytes-rate {
             type int32;
             description
               "Output bytes rate";
           }
           leaf fc-input-packets {
             type int32;
           }
           leaf fc-input-packets-rate {
             type int32;
             description
               "Input packets rate";
           }
           leaf fc-output-packets {
             type int32;
           }
           leaf fc-output-packets-rate {
             type int32;
             description
               "Output packets rate";
           }
           leaf input-unicast-bytes {
             type int32;
           }
           leaf output-unicast-bytes {
             type int32;
           }
           leaf input-unicast-packets {
             type int32;
           }
           leaf output-unicast-packets {
             type int32;
           }
           leaf input-multicast-bytes {
             type int32;
           }
           leaf output-multicast-bytes {
             type int32;
           }
           leaf input-multicast-packets {
             type int32;
           }
           leaf output-multicast-packets {
             type int32;
           }
         }
       }
       container keepalive-statistics {
         description
           "Keepalive statistics for this interface";
         leaf keepalive-lmi-descriptor {
           type string;
         }
         leaf keepalive-input-count {
           type int32;
         }
         leaf keepalive-input-time {
           type string;
         }
         leaf keepalive-output-count {
           type int32;
         }
         leaf keepalive-output-time {
           type string;
         }
       }
       container optics-bit-rate {
         leaf bit-rate {
           type string;
           description
             " Optics Bit Rate";
         }
       }
       container optics-fec-statistics {
         leaf fec-corrected-errors {
           type int32;
         }
         leaf fec-valid-time {
           type int32;
         }
         leaf fec-corrected-error-ratio {
           type int32;
         }
         leaf fec-uncorrected-words {
           type int32;
         }
       }
       container optic-fec-mode {
         leaf fec-mode {
           type string;
           description
             "Optics FEC mode";
         }
       }
       container optic-fec-statistics {
         leaf fec-corrected-errors {
           type int32;
         }
         leaf fec-uncorrected-words {
           type int32;
         }
         leaf fec-corrected-error-rate {
           type int32;
         }
         leaf fec-uncorrected-error-rate {
           type int32;
         }
         leaf optic-fec-uncorrected-error-ratio {
           type string;
         }
         leaf fec-valid-time {
           type int32;
         }
         leaf optic-fec-corrected-error-ratio {
           type string;
         }
       }
       container ngpe-ep-vxlan-info {
         leaf ngpe-ep-vtep-address-family {
           type uint32;
           description
             "NGPE EP VxLAN Endpoint IP Address Familiy";
         }
       }
       container traffic-statistics {
         leaf input-bps {
           type int32;
         }
         leaf input-pps {
           type int32;
         }
         leaf output-bps {
           type int32;
         }
         leaf output-pps {
           type int32;
         }
         leaf input-packets {
           type uint64;
         }
         leaf output-packets {
           type uint64;
         }
         container ipv4-traffic-statistics {
           leaf input-bps {
             type int32;
           }
           leaf output-bps {
             type int32;
           }
           leaf input-pps {
             type int32;
           }
           leaf output-pps {
             type int32;
           }
           leaf input-bytes {
             type int32;
           }
           leaf output-bytes {
             type int32;
           }
           leaf input-packets {
             type uint64;
           }
           leaf output-packets {
             type uint64;
           }
         }
         leaf input-bytes {
           type int32;
         }
         leaf output-bytes {
           type int32;
         }
         container ipv6-transit-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-traffic-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-total-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
       }
       container multicast-statistics {
         description
           "Multicast statistics for interface";
         leaf multicast-statistics-header {
           type empty;
         }
         container ipv4-multicast-statistics {
           description
             "IPV4 multicast statistics for interface";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-multicast-statistics {
           description
             "IPV6 multicast statistics for interface";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
       }
       container ingress-traffic-statistics {
         description
           "Traffic statistics at ingress before entering Packet Forwarding 
           Engine";
         leaf input-bps {
           type int32;
         }
         leaf input-pps {
           type int32;
         }
         leaf input-drop-bps {
           type int32;
           description
             "Drop rate at ingress in bits per second ";
         }
         leaf input-drop-pps {
           type int32;
           description
             "Drop rate at ingress in packets per second ";
         }
         leaf input-bytes {
           type int32;
         }
         leaf input-packets {
           type uint64;
         }
         leaf input-drop-bytes {
           type int32;
           description
             "Drop statistics at ingress in bytes";
         }
         leaf input-drop-packets {
           type int32;
           description
             "Drop statistics at ingress in packets";
         }
       }
       container active-alarms {
       }
       container active-defects {
       }
       container media-state-information {
       }
       container sonet-errors {
         list media-alarm {
           leaf media-alarm-name {
             type string;
           }
           leaf media-alarm-count {
             type int32;
           }
         }
       }
       container sonet-physical-information {
         list media-alarm {
           leaf media-alarm-name {
             type string;
           }
           leaf media-alarm-seconds {
             type int32;
           }
           leaf media-alarm-count {
             type int32;
           }
           leaf media-alarm-state {
             type string;
           }
         }
       }
       container sonet-section-information {
         list media-alarm {
           leaf media-alarm-name {
             type string;
           }
           leaf media-alarm-seconds {
             type int32;
           }
           leaf media-alarm-count {
             type int32;
           }
           leaf media-alarm-state {
             type string;
           }
         }
       }
       container sonet-line-information {
         list media-alarm {
           leaf media-alarm-name {
             type string;
           }
           leaf media-alarm-seconds {
             type int32;
           }
           leaf media-alarm-count {
             type int32;
           }
           leaf media-alarm-state {
             type string;
           }
         }
       }
       container sonet-path-information {
         list media-alarm {
           leaf media-alarm-name {
             type string;
           }
           leaf media-alarm-seconds {
             type int32;
           }
           leaf media-alarm-count {
             type int32;
           }
           leaf media-alarm-state {
             type string;
           }
         }
       }
       container sonet-vt-information {
         list media-alarm {
           leaf media-alarm-name {
             type string;
           }
           leaf media-alarm-seconds {
             type int32;
           }
           leaf media-alarm-count {
             type int32;
           }
           leaf media-alarm-state {
             type string;
           }
         }
       }
       container otn-errors {
         list media-alarm {
           leaf media-alarm-name {
             type string;
           }
           leaf media-alarm-count {
             type int32;
           }
         }
       }
       container otn-fec-statistics {
         leaf fec-corrected-errors {
           type int32;
         }
         leaf fec-valid-time {
           type int32;
         }
         leaf fec-corrected-error-ratio {
           type int32;
         }
         leaf fec-uncorrected-words {
           type int32;
         }
       }
       container otn-fec-alarms {
         description
           "OTN degraded and excessive FEC error rates";
         list media-alarm {
           leaf media-alarm-name {
             type string;
           }
           leaf media-alarm-seconds {
             type int32;
           }
           leaf media-alarm-count {
             type int32;
           }
           leaf media-alarm-state {
             type string;
           }
         }
       }
       container otn-fec-mode {
         leaf fec-mode {
           type string;
           description
             "Optics FEC mode";
         }
       }
       container otn-otn-mode {
         leaf otn-mode {
           type string;
         }
       }
       container otn-otn-rate {
         leaf otn-rate {
           type string;
         }
       }
       container otn-otn-loopback {
         leaf otn-loopback {
           type string;
         }
       }
       container otn-local-loopback {
         leaf local-loopback {
           type string;
         }
       }
       container otn-payload-prbs {
         leaf payload-prbs {
           type string;
         }
       }
       container otn-laser-enable {
         leaf laser-enable {
           type string;
           description
             "Optics laser status";
         }
       }
       container media-information {
         description
           "Information about media alarms";
         leaf media-type {
           type string;
           description
             "Type of media this information is for";
         }
         list media-alarm {
           leaf media-alarm-name {
             type string;
           }
           leaf media-alarm-count {
             type int32;
           }
           leaf media-alarm-seconds {
             type int32;
           }
           leaf media-alarm-state {
             type string;
           }
           leaf ce-counter-name {
             type string;
             description
               "Circuit Emulation counter information";
           }
           leaf ce-counter-packets {
             type int32;
             description
               "Circuit Emulation number of packets";
           }
           leaf ce-counter-bytes {
             type int32;
             description
               "Circuit Emulation number of bytes";
           }
           leaf ce-counter-count {
             type int32;
             description
               "Circuit Emulation number of event occurrences";
           }
         }
         leaf ds1-timeslots {
           type string;
         }
         leaf ds1-line-encoding {
           type string;
         }
         leaf ds1-byte-encoding {
           type string;
         }
         leaf ds1-data-inversion {
           type string;
         }
         leaf idle-cycle-flag {
           type string;
         }
         leaf start-end-flag {
           type string;
         }
         leaf ds0-byte-encoding {
           type string;
         }
         leaf ds0-data-inversion {
           type string;
         }
         leaf e3-data-inversion {
           type string;
         }
         leaf ds1-buildout {
           type string;
           description
             "Number of feet";
         }
       }
       container ethernet-pcs-statistics {
         description
           "Ethernet PCS statistics";
         leaf bit-error-seconds {
           type int32;
           description
             "Bit error duration";
         }
         leaf errored-blocks-seconds {
           type int32;
           description
             "Errored blocks duration";
         }
       }
       container ethernet-fec-mode {
         description
           "Ethernet FEC Mode";
         leaf enabled_fec_mode {
           type string;
           description
             "Enabled FEC mode: <NONE/FEC74/FEC91/FEC108/FEC161>";
         }
         leaf fec_codeword_size {
           type uint32;
           description
             "FEC Codeword size";
         }
         leaf fec_codeword_rate {
           type jt:unsigned-float;
           description
             "FEC Codeword rate";
         }
       }
       container ethernet-fec-statistics {
         description
           "Ethernet FEC statistics";
         leaf fec_ccw_count {
           type int32;
           description
             "FEC Corrected Error Count";
         }
         leaf fec_nccw_count {
           type int32;
           description
             "FEC Uncorrected Error Count";
         }
         leaf fec_ccw_error_rate {
           type int32;
           description
             "FEC Corrected Error Rate (errors/sec)";
         }
         leaf fec_nccw_error_rate {
           type int32;
           description
             "FEC Uncorrected Error Rate (errors/sec)";
         }
         leaf pre-fec-ber {
           type jt:unsigned-float;
           description
             "PRE_FEC BER";
         }
       }
       container ethernet-fechistogram-statistics {
         description
           "Ethernet Fec Histogram stats";
         leaf bin-num {
           type int32;
           description
             "Bin number";
         }
         leaf sym-live-err {
           type int32;
           description
             "Sym Live Err";
         }
         leaf sym-harvest-err {
           type int32;
           description
             "Sym harvested Err";
         }
         leaf sym-harvest-last-update {
           type string;
           description
             "Sym harvested last update";
         }
       }
       container ctle {
         description
           "Ctle ";
         leaf ctle_value {
           type int32;
           description
             "Ctle value";
         }
       }
       container pre-emphasis {
         description
           "Pre-emphasis ";
         leaf pre_emphasis_value {
           type int32;
           description
             "Pre-emphasis value";
         }
       }
       container differential-amplitude {
         description
           "Differential-amplitude ";
         leaf differential_amplitude_value {
           type int32;
           description
             "Differential-amplitude value";
         }
       }
       container ethernet-mac-statistics {
         description
           "Ethernet MAC statistics";
         leaf input-bytes {
           type int32;
         }
         leaf input-packets {
           type uint64;
         }
         leaf output-bytes {
           type int32;
         }
         leaf output-packets {
           type uint64;
         }
         leaf input-undersized-frames {
           type int32;
         }
         leaf input-unicasts {
           type int32;
         }
         leaf output-unicasts {
           type int32;
         }
         leaf input-broadcasts {
           type int32;
         }
         leaf output-broadcasts {
           type int32;
         }
         leaf input-multicasts {
           type int32;
         }
         leaf output-multicasts {
           type int32;
         }
         leaf input-crc-errors {
           type int32;
         }
         leaf output-crc-errors {
           type int32;
         }
         leaf input-fifo-errors {
           type int32;
         }
         leaf output-fifo-errors {
           type int32;
         }
         leaf input-dma-errors {
           type int32;
         }
         leaf output-dma-errors {
           type int32;
         }
         leaf input-mac-control-frames {
           type int32;
         }
         leaf output-mac-control-frames {
           type int32;
         }
         leaf input-mac-pause-frames {
           type int32;
         }
         leaf output-mac-pause-frames {
           type int32;
         }
         leaf input-oversized-frames {
           type int32;
         }
         leaf input-jabber-frames {
           type int32;
         }
         leaf input-fragment-frames {
           type int32;
         }
         leaf input-vlan-tagged-frames {
           type int32;
         }
         leaf input-code-violations {
           type int32;
         }
         leaf input-total-errors {
           type int32;
         }
         leaf output-total-errors {
           type int32;
         }
         leaf input-policer-frame-drops {
           type int32;
         }
         leaf input-policer-byte-drops {
           type int32;
         }
       }
       container ethernet-prbs-mode {
         description
           "PRBS Mode";
         leaf prbs-mode {
           type string;
           description
             "PRBS Mode: <Enabled/Disabled>";
         }
       }
       container ethernet-prbs-pattern {
         description
           "PRBS Pattern";
         leaf prbs-pattern {
           type int32;
           description
             "PRBS Pattern";
         }
       }
       container ethernet-prbs-statistics {
         description
           "Ethernet PRBS statistics";
         leaf prbs-lane {
           type int32;
           description
             "PRBS Lane";
         }
         leaf prbs-error-count {
           type int32;
           description
             "PRBS Error Count";
         }
         leaf prbs-loop-count {
           type int32;
           description
             "PRBS Loop Count";
         }
         leaf prbs-ber-sec {
           type int32;
           description
             "PRBS BER seconds";
         }
         leaf prbs-bits {
           type int32;
           description
             "PRBS Bits";
         }
         leaf prbs-run-sec {
           type int32;
           description
             "PRBS Run seconds";
         }
         leaf prbs-state {
           type string;
           description
             "PRBS State";
         }
         leaf prbs-ber-rate {
           type string;
           description
             "PRBS BER rate";
         }
       }
       container smart-sfp-configurable-type {
         leaf smart-sfp-tdm-management {
           type string;
         }
         leaf smart-sfp-mac {
           type jt:mac-addr;
         }
       }
       container smart-sfp-type {
         leaf smart-sfp-module-type {
           type string;
         }
         leaf smart-sfp-present {
           type string;
         }
       }
       container smart-sfp-config {
         leaf tdm-loopback {
           type string;
         }
         leaf dmac-check-enable {
           type string;
         }
         leaf encap-ecid {
           type int32;
         }
         leaf decap-ecid {
           type int32;
         }
         leaf vlan-id-1 {
           type int32;
         }
         leaf vlan-id-2 {
           type int32;
         }
         leaf mode {
           type string;
         }
         leaf chan-dmac {
           type jt:mac-addr;
         }
         leaf ces-psn-port-channel-id-state {
           type string;
         }
         leaf tdm-intf-signal {
           type string;
         }
       }
       list smart-sfp-channel-config {
         key "channel-num";
         description
           "Smart SFP channel config";
         leaf channel-num {
           type uint32;
           description
             "Channel number";
         }
         leaf channel-klm {
           type string;
           description
             "K (TUG3), L (TUG2), M (TU-12/VC-12/E1) Mapping";
         }
         leaf encap-ecid {
           type int32;
         }
         leaf encap-rtp-freq {
           type string;
         }
         leaf decap-ecid {
           type int32;
         }
         leaf decap-timing {
           type string;
         }
         leaf decap-rtp-freq {
           type string;
         }
         leaf ces-psn-mode {
           type string;
         }
         leaf ces-psn-dmac {
           type jt:mac-addr;
         }
         leaf ces-psn-vlan-1 {
           type int32;
         }
         leaf ces-psn-vlan-2 {
           type int32;
         }
         leaf encap-rtphdr-insert {
           type string;
         }
         leaf decap-rtphdr {
           type string;
         }
       }
       container smart-sfp-oc3-statistics {
         leaf fcs-error-count {
           type uint32;
         }
         leaf sec-sefs {
           type uint32;
         }
         leaf sec-es {
           type uint32;
         }
         leaf sec-es-min15 {
           type uint32;
         }
         leaf sec-ses {
           type uint32;
         }
         leaf sec-ses-min15 {
           type uint32;
         }
         leaf sec-cv {
           type uint32;
         }
         leaf sec-cv-min15 {
           type uint32;
         }
         leaf line-es {
           type uint32;
         }
         leaf line-es-min15 {
           type uint32;
         }
         leaf line-ses {
           type uint32;
         }
         leaf line-ses-min15 {
           type uint32;
         }
         leaf line-cv {
           type uint32;
         }
         leaf line-cv-min15 {
           type uint32;
         }
         leaf line-uas {
           type uint32;
         }
         leaf line-uas-min15 {
           type uint32;
         }
         leaf path-es {
           type uint32;
         }
         leaf path-es-min15 {
           type uint32;
         }
         leaf path-ses {
           type uint32;
         }
         leaf path-ses-min15 {
           type uint32;
         }
         leaf path-cv {
           type uint32;
         }
         leaf path-cv-min15 {
           type uint32;
         }
         leaf path-uas {
           type uint32;
         }
         leaf path-uas-min15 {
           type uint32;
         }
       }
       container smart-sfp-e1t1-statistics {
         leaf e1t1-es {
           type uint32;
         }
         leaf e1t1-es-min15 {
           type uint32;
         }
         leaf e1t1-ses {
           type uint32;
         }
         leaf e1t1-ses-min15 {
           type uint32;
         }
         leaf e1t1-uas {
           type uint32;
         }
         leaf e1t1-uas-min15 {
           type uint32;
         }
         leaf e1t1-bes {
           type uint32;
         }
         leaf e1t1-bes-min15 {
           type uint32;
         }
         leaf e1t1-les {
           type uint32;
         }
         leaf e1t1-les-min15 {
           type uint32;
         }
         leaf e1t1-pes {
           type uint32;
         }
         leaf e1t1-pes-min15 {
           type uint32;
         }
         leaf e1t1-psess {
           type uint32;
         }
         leaf e1t1-psess-min15 {
           type uint32;
         }
         leaf e1t1-ces {
           type uint32;
         }
         leaf e1t1-ces-min15 {
           type uint32;
         }
         leaf e1t1-cses {
           type uint32;
         }
         leaf e1t1-cses-min15 {
           type uint32;
         }
         leaf e1t1-sefs {
           type uint32;
         }
         leaf e1t1-sefs-min15 {
           type uint32;
         }
       }
       container smart-sfp-e3t3-statistics {
         leaf e3t3-les {
           type uint32;
         }
         leaf e3t3-les-min15 {
           type uint32;
         }
         leaf e3t3-pes {
           type uint32;
         }
         leaf e3t3-pes-min15 {
           type uint32;
         }
         leaf e3t3-psess {
           type uint32;
         }
         leaf e3t3-psess-min15 {
           type uint32;
         }
         leaf e3t3-ces {
           type uint32;
         }
         leaf e3t3-ces-min15 {
           type uint32;
         }
         leaf e3t3-cses {
           type uint32;
         }
         leaf e3t3-cses-min15 {
           type uint32;
         }
         leaf e3t3-sefs {
           type uint32;
         }
         leaf e3t3-sefs-min15 {
           type uint32;
         }
         leaf e3t3-uas {
           type uint32;
         }
         leaf e3t3-uas-min15 {
           type uint32;
         }
       }
       container fibrechannel-port-flow-control {
         description
           "Fibre Channel interface flow control";
         leaf fibrechannel-port-flow-control-mode {
           type string;
         }
         list fibrechannel-port-flow-control-credits {
           description
             "Generic flow control credits";
           leaf fibrechannel-port-flow-control-credits-subject {
             type string;
           }
           leaf fibrechannel-port-flow-control-credits-assigned {
             type uint64;
           }
           leaf fibrechannel-port-flow-control-credits-available {
             type uint64;
           }
         }
       }
       container fibrechannel-mac-statistics {
         description
           "Fibre Channel MAC statistics";
         container fibrechannel-mac-statistics-generic {
           leaf link-failures {
             type uint64;
           }
           leaf loss-of-sync {
             type uint64;
           }
           leaf loss-of-signal {
             type uint64;
           }
           leaf sw-link-resets {
             type uint64;
           }
           leaf buffer-to-buffer-credit-recovery-lost-frames {
             type uint64;
           }
           leaf buffer-to-buffer-credit-recovery-lost-rrdys {
             type uint64;
           }
         }
         container fibrechannel-mac-statistics-received {
           leaf rx-class-2-frames {
             type uint64;
           }
           leaf rx-class-2-octets {
             type uint64;
           }
           leaf rx-class-3-frames {
             type uint64;
           }
           leaf rx-class-3-octets {
             type uint64;
           }
           leaf rx-class-f-frames {
             type uint64;
           }
           leaf rx-class-f-octets {
             type uint64;
           }
           leaf class-2-discards {
             type uint64;
           }
           leaf class-3-discards {
             type uint64;
           }
           leaf class-f-discards {
             type uint64;
           }
           leaf rx-frames-too-long {
             type uint64;
           }
           leaf rx-frames-too-short {
             type uint64;
           }
           leaf rx-missing-eof {
             type uint64;
           }
           leaf rx-invalid-crcs {
             type uint64;
           }
           leaf rx-link-resets {
             type uint64;
           }
           leaf rx-link-reset-responses {
             type uint64;
           }
           leaf rx-offlines {
             type uint64;
           }
           leaf rx-not-operationals {
             type uint64;
           }
           leaf rx-invalid-tx-words {
             type uint64;
           }
           leaf rx-encoding-disparity-errors {
             type uint64;
           }
           leaf rx-delimiter-errors {
             type uint64;
           }
           leaf rx-input-buffers-full {
             type uint64;
           }
           leaf rx-invalid-ordered-sets {
             type uint64;
           }
           leaf rx-prim-seq-protocol-errors {
             type uint64;
           }
           leaf rx-other-errors {
             type uint64;
           }
         }
         container fibrechannel-mac-statistics-transmitted {
           leaf tx-class-2-frames {
             type uint64;
           }
           leaf tx-class-2-octets {
             type uint64;
           }
           leaf tx-class-3-frames {
             type uint64;
           }
           leaf tx-class-3-octets {
             type uint64;
           }
           leaf tx-class-f-frames {
             type uint64;
           }
           leaf tx-class-f-octets {
             type uint64;
           }
           leaf tx-link-resets {
             type uint64;
           }
           leaf tx-link-reset-responses {
             type uint64;
           }
           leaf tx-offlines {
             type uint64;
           }
           leaf tx-not-operationals {
             type uint64;
           }
           leaf tx-bb-credit-zeroes {
             type uint64;
           }
           leaf tx-other-errors {
             type uint64;
           }
         }
       }
       container ethernet-filter-statistics {
         description
           "Ethernet filter statistics";
         leaf input-reject-count {
           type int32;
         }
         leaf output-packet-pad-count {
           type int32;
         }
         leaf output-packet-error-count {
           type int32;
         }
         leaf input-packets {
           type uint64;
         }
         leaf input-reject-destination-address-count {
           type int32;
         }
         leaf input-reject-source-address-count {
           type int32;
         }
         leaf output-packets {
           type uint64;
         }
         leaf cam-destination-filter-count {
           type int32;
         }
         leaf cam-source-filter-count {
           type int32;
         }
       }
       container ethernet-autonegotiation {
         description
           "Ethernet autonegotiation information";
       }
       container mac-database {
       }
       container dsl-information {
         description
           "Operational information and statistics for ADSL interfaces";
         container dsl-statistics {
           leaf interleaved-rx-cells {
             type int32;
             description
               "Interleaved receiver cells";
           }
           leaf fast-rx-cells {
             type int32;
             description
               "Fast receiver cells";
           }
           leaf interleaved-tx-cells {
             type int32;
             description
               "Interleaved transmitter cells";
           }
           leaf fast-tx-cells {
             type int32;
             description
               "Fast transmitter cells";
           }
         }
       }
       container vdsl-information {
         description
           "Operational information and statistics for VDSL interfaces";
       }
       container dsl-sfp-information {
         description
           "Operational information and statistics for DSL SFP interfaces";
       }
       container shdsl-information {
         description
           "Operational information and statistics for SHDSL interfaces";
       }
       container efm-information {
         description
           "Operational information and statistics for EFM interfaces";
         container efm-line-statistics {
           container active-alarms-efm {
           }
           container active-defects-efm {
           }
           container media-information {
             description
               "Information about media alarms";
             leaf media-type {
               type string;
               description
                 "Type of media this information is for";
             }
             list media-alarm {
               leaf media-alarm-name {
                 type string;
               }
               leaf media-alarm-count {
                 type int32;
               }
               leaf media-alarm-seconds {
                 type int32;
               }
               leaf media-alarm-state {
                 type string;
               }
               leaf ce-counter-name {
                 type string;
                 description
                   "Circuit Emulation counter information";
               }
               leaf ce-counter-packets {
                 type int32;
                 description
                   "Circuit Emulation number of packets";
               }
               leaf ce-counter-bytes {
                 type int32;
                 description
                   "Circuit Emulation number of bytes";
               }
               leaf ce-counter-count {
                 type int32;
                 description
                   "Circuit Emulation number of event occurrences";
               }
             }
             leaf ds1-timeslots {
               type string;
             }
             leaf ds1-line-encoding {
               type string;
             }
             leaf ds1-byte-encoding {
               type string;
             }
             leaf ds1-data-inversion {
               type string;
             }
             leaf idle-cycle-flag {
               type string;
             }
             leaf start-end-flag {
               type string;
             }
             leaf ds0-byte-encoding {
               type string;
             }
             leaf ds0-data-inversion {
               type string;
             }
             leaf e3-data-inversion {
               type string;
             }
             leaf ds1-buildout {
               type string;
               description
                 "Number of feet";
             }
           }
           container shdsl-information {
             description
               "Operational information and statistics for SHDSL interfaces";
           }
         }
       }
       container atm-information {
         description
           "Operational information and statistics for ATM interfaces";
         container plcp-defects {
         }
         container atm-defects {
         }
       }
       container serial-information {
         description
           "Serial interfaces information and statistics";
         leaf dce-loopback-override {
           type string;
         }
         container eia530-control-signal {
         }
       }
       container virtual-path-information {
         description
           "Operational information and statistics for a virtual path";
         leaf cdvt {
           type int32;
         }
         container traffic-statistics {
           leaf input-bps {
             type int32;
           }
           leaf input-pps {
             type int32;
           }
           leaf output-bps {
             type int32;
           }
           leaf output-pps {
             type int32;
           }
           leaf input-packets {
             type uint64;
           }
           leaf output-packets {
             type uint64;
           }
           container ipv4-traffic-statistics {
             leaf input-bps {
               type int32;
             }
             leaf output-bps {
               type int32;
             }
             leaf input-pps {
               type int32;
             }
             leaf output-pps {
               type int32;
             }
             leaf input-bytes {
               type int32;
             }
             leaf output-bytes {
               type int32;
             }
             leaf input-packets {
               type uint64;
             }
             leaf output-packets {
               type uint64;
             }
           }
           leaf input-bytes {
             type int32;
           }
           leaf output-bytes {
             type int32;
           }
           container ipv6-transit-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-traffic-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-total-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
         }
       }
       container ct3-information {
         list interface-tx-queue {
           leaf output-drops-bytes {
             type int32;
           }
         }
       }
       container cds1-information {
         list interface-tx-queue {
           leaf output-drops-bytes {
             type int32;
           }
         }
       }
       container nxds0-information {
         list interface-tx-queue {
           leaf output-drops-bytes {
             type int32;
           }
         }
       }
       list logical-interface {
         key "name";
         description
           "Information about a single logical interface";
         leaf name {
           type string;
           description
             "Name of this item";
         }
         leaf admin-status {
           type string;
           description
             "Desired state of the interface";
         }
         leaf oper-status {
           type string;
           description
             "Current operational state of the interface";
         }
         leaf logical-interface-zone-name {
           type string;
           description
             "Zone name for this interface";
         }
         leaf subunit {
           type int32;
           description
             "Subunit for this interface";
         }
         leaf dialer-time-to-disconnect {
           type string;
           description
             "Time for dialer to disconnect due to idle timeout";
         }
         leaf lcp-state {
           type string;
           description
             "State of the Line Control Protocol";
         }
         leaf chap-state {
           type string;
           description
             "State of the Challenge Handshake Authentication Protocol";
         }
         leaf pap-state {
           type string;
           description
             "State of the Password Authentication Protocol";
         }
         container layer2-input-policer-information {
           description
             "Information about Layer 2 input policer for interface";
           leaf layer2-input-policer {
             type string;
             description
               "Name of the Layer 2 input policer";
           }
         }
         container layer2-output-policer-information {
           description
             "Information about Layer 2 output policer for interface";
           leaf layer2-output-policer {
             type string;
             description
               "Name of the Layer 2 output policer";
           }
         }
         container pppoe-information {
           description
             "PPPoE information";
           list pppoe-interface {
             leaf state {
               type string;
               description
                 "State";
             }
             leaf session-id {
               type string;
               description
                 "Session ID";
             }
             leaf ac-name-session {
               type string;
               description
                 "Session AC name";
             }
             leaf remote-mac {
               type string;
               description
                 "Remote MAC address";
             }
             leaf ac-name-config {
               type string;
               description
                 "Configured AC name";
             }
             leaf service-name {
               type string;
               description
                 "Service name";
             }
             leaf auto-reconnect {
               type string;
               description
                 "Autoreconnect timeout";
             }
             leaf idle-timeout {
               type string;
               description
                 "Idle timeout";
             }
             leaf underlying-interface-name {
               type string;
               description
                 "Underlying interface name";
             }
             leaf underlying-interface-index {
               type string;
               description
                 "Underlying interface index";
             }
             leaf padg-credits {
               type int32;
               description
                 "PADG transmit credits";
             }
             leaf pppoe-credit-scale-factor {
               type string;
               description
                 "Scaling factor";
             }
             leaf ignore-eol-tag {
               type string;
               description
                 "Ignore End-of-List TAG";
             }
             leaf ppp-max-payload-tag {
               type int32;
               description
                 "PPP-Max-Payload TAG";
             }
             leaf interface-name {
               type string;
               description
                 "Interface name";
             }
             leaf interface-index {
               type string;
               description
                 "Index";
             }
             leaf aci-iflset-name {
               type string;
               description
                 "ACI Interface Set name";
             }
             leaf aci-iflset-index {
               type string;
               description
                 "ACI Interface Set index";
             }
             leaf ifl-type {
               type string;
               description
                 "Type";
             }
             leaf session-uptime {
               type string;
               description
                 "Duration for which the session has been up";
             }
             leaf dynamic-profile {
               type string;
               description
                 "Dynamic Profile name";
             }
             leaf pppoe-credits {
               type string;
               description
                 "Forwarding credit balances";
             }
             leaf dynamic-interface-bandwidth {
               type string;
               description
                 "Dynamic interface bandwidth";
             }
             leaf agent-circuit-id {
               type string;
               description
                 "Agent Circuit ID";
             }
             leaf agent-remote-id {
               type string;
               description
                 "Agent Remote ID";
             }
             leaf padm-motm {
               type string;
               description
                 "PADM Message of the Moment tag";
             }
             leaf padm-hurl {
               type string;
               description
                 "PADM HTTP URL tag";
             }
             leaf pppoe-relay-session-id {
               type string;
               description
                 "PPPoE Relay Session ID";
             }
           }
         }
         container pppoe-underlying-information {
           description
             "PPPoE Underlying information";
           list pppoe-underlying-interface {
             leaf dynamic-profile {
               type string;
               description
                 "Dynamic Profile name";
             }
             leaf service-name-table {
               type string;
               description
                 "Name of Service Name Table";
             }
             leaf max-sessions {
               type int32;
               description
                 "Maximum number of PPPoE sessions";
             }
             leaf max-sessions-vsa-ignore {
               type string;
               description
                 "Ignore max-sessions VSA";
             }
             leaf duplicate-protection {
               type string;
               description
                 "Duplicate protection mode";
             }
             leaf short-cycle-protection {
               type string;
               description
                 "Short cycle protection mode";
             }
             leaf direct-connect {
               type string;
               description
                 "Direct connect mode";
             }
             leaf ac-name {
               type string;
               description
                 "Access Concentrator name";
             }
             leaf underlying-interface-name {
               type string;
               description
                 "Underlying interface name";
             }
             leaf underlying-interface-index {
               type string;
               description
                 "Underlying interface index";
             }
             leaf encapsulation-type-identifier {
               type string;
               description
                 "Encapsulation type identifier";
             }
             leaf state {
               type string;
               description
                 "State";
             }
             leaf active-sessions {
               type int32;
               description
                 "Number of active PPPoE sessions";
             }
             leaf aci-autosensing {
               type string;
               description
                 "ACI VLAN Autosensing mode";
             }
             leaf line-identity-autosensing {
               type string;
               description
                 "Line Identity Autosensing mode";
             }
           }
         }
         container aci-vlan-information {
           leaf dynamic-profile {
             type string;
             description
               "Dynamic Profile name";
           }
         }
         container line-identity-information {
           leaf dynamic-profile {
             type string;
             description
               "Dynamic Profile name";
           }
           leaf circuit-id {
             type string;
             description
               "Aci vlan attribute";
           }
           leaf remote-id {
             type string;
             description
               "Aci vlan attribute";
           }
           leaf accept-no-ids {
             type string;
             description
               "Aci vlan attribute";
           }
         }
         container demux-information {
           description
             "Demux information";
           container demux-interface {
             leaf demux-underlying-interface-name {
               type string;
               description
                 "Underlying interface name";
             }
             leaf demux-underlying-interface-index {
               type string;
               description
                 "Underlying interface index";
             }
             leaf demux-inet-prefix-type {
               type string;
               description
                 "Prefix type";
             }
             leaf demux-inet-prefix-count {
               type string;
               description
                 "IPv4 Prefix count";
             }
             leaf demux-inet-prefix {
               type string;
               description
                 "IPv4 Prefix";
             }
             leaf demux-inet6-prefix-type {
               type string;
               description
                 "Prefix type";
             }
             leaf demux-inet6-prefix-count {
               type string;
               description
                 "IPv6 Prefix count";
             }
             leaf demux-inet6-prefix {
               type string;
               description
                 "IPv6 Prefix";
             }
           }
         }
         container dual-ad-icl-color-information {
           container dual-ad-icl-color-info {
             description
               "Dual-AD ICL Color Information";
             leaf dual-ad-icl-color-type {
               type uint32;
               description
                 "Dual-AD ICL Color Type";
             }
             leaf dual-ad-icl-color {
               type uint32;
               description
                 "Dual-AD ICL Color";
             }
           }
         }
         container dialer-information {
           description
             "Dialer information";
           leaf dialer-time-to-disconnect {
             type string;
             description
               "Time for dialer to disconnect due to idle timeout";
           }
           container dialer-interface {
             container dialer-interface-flags {
               description
                 "Flags indicating interface configuration";
               leaf backup {
                 type empty;
                 description
                   "Dialer backup";
               }
               leaf multilink {
                 type empty;
                 description
                   "Dialer multilink";
               }
               leaf watchlist {
                 type empty;
                 description
                   "Dialer watchlist";
               }
               leaf interesting-detected {
                 type empty;
                 description
                   "Interesting packet detected";
               }
             }
             list dial-string-list {
               leaf dial-string {
                 type string;
                 description
                   "Dial string";
               }
             }
             list sub-interface-list {
               leaf sub-interface-name {
                 type string;
                 description
                   "Subordinate interface name";
               }
             }
             list watch-list {
               leaf watch-route {
                 type string;
                 description
                   "Watch route";
               }
             }
             leaf dialer-interface-name {
               type string;
               description
                 "Interface name";
             }
             leaf dialer-interface-state {
               type string;
               description
                 "Dialer interface state";
             }
             leaf pool-id {
               type string;
               description
                 "Pool identifier";
             }
             leaf primary-interface {
               type string;
               description
                 "Primary interface";
             }
             leaf activation-delay {
               type string;
               description
                 "Activation delay";
             }
             leaf deactivation-delay {
               type string;
               description
                 "Deactivation delay";
             }
             leaf activation-delay-elapsed {
               type string;
               description
                 "Activation delay elapsed";
             }
             leaf deactivation-delay-elapsed {
               type string;
               description
                 "Deactivation delay elapsed";
             }
             leaf call-idle-timeout {
               type string;
               description
                 "Call idle timeout";
             }
             leaf initial-route-check {
               type string;
               description
                 "Initial route check delay";
             }
             leaf redial-delay {
               type string;
               description
                 "Delay before dialer dials out again (seconds)";
             }
             leaf callback-wait-period {
               type string;
               description
                 "Delay before dialer attempts callback (seconds)";
             }
             leaf callback-wait-period-elapsed {
               type string;
               description
                 "Number of seconds in callback wait period that have 
                 elapsed";
             }
             leaf load-threshold {
               type string;
               description
                 "Load threshold that determines when interfaces are added 
                 to bundle";
             }
             leaf load-interval {
               type string;
               description
                 "Interval over which average load is calculated";
             }
           }
         }
         container shared-interface-information {
           description
             "Shared interface information";
           container shared-interface-logical-interface {
             description
               "Shared interface logical interface";
             leaf peer-interface-name {
               type string;
               description
                 "Peer interface name";
             }
             leaf interface-shared-with {
               type string;
               description
                 "Logical interface owner";
             }
             leaf rx-fe {
               type string;
               description
                 "Rx tunnel token forwarding element";
             }
             leaf rx-nhid {
               type string;
               description
                 "Rx tunnel token next hop index";
             }
             leaf tx-fe {
               type string;
               description
                 "Tx tunnel token forwarding element";
             }
             leaf tx-nhid {
               type string;
               description
                 "Tx tunnel token next hop index";
             }
           }
         }
         container mac-database {
         }
         container queue-counters {
           description
             "Queue counter statistics";
           leaf queue-counters-error-message {
             type string;
             description
               "Queue statistics not available for this interface";
           }
           container interface-cos-short-summary {
             description
               "Summary of queue information on an interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           list queue {
             key "queue-number";
             description
               "Counters for a single queue";
             leaf queue-number {
               type uint32;
               description
                 "Queue number";
             }
             leaf queue-counters-queued-packets {
               type int32;
               description
                 "Queued packet count";
             }
             leaf queue-counters-trans-packets {
               type int32;
               description
                 "Total number of transmitted packets";
             }
             leaf queue-counters-total-drop-packets {
               type int32;
               description
                 "Number of total packets dropped at the queue";
             }
             leaf forwarding-class-name {
               type string;
               description
                 "Forwarding class name associated with queue";
             }
             leaf queue-counters-queued-packets-rate {
               type int32;
               description
                 "Rate at which packets are queued";
             }
             leaf queue-counters-queued-bytes {
               type int32;
               description
                 "Queued bytes count";
             }
             leaf queue-counters-queued-bytes-rate {
               type int32;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets-rate {
               type int32;
               description
                 "Rate at which packets are transmitted";
             }
             leaf queue-counters-trans-bytes {
               type int32;
               description
                 "Total number of transmitted bytes";
             }
             leaf queue-counters-trans-bytes-rate {
               type int32;
               description
                 "Rate at which bytes are transmitted";
             }
             leaf queue-counters-tail-drop-packets-na {
               type string;
               description
                 "Number of packets dropped due to tail drop not available";
             }
             leaf queue-counters-tail-drop-packets {
               type int32;
               description
                 "Number of packets dropped at the tail of the queue";
             }
             leaf queue-counters-tail-drop-packets-rate {
               type int32;
               description
                 "Rate at which packets are dropped at tail of queue";
             }
             leaf queue-counters-tail-drop-bytes {
               type int32;
               description
                 "Number of packets dropped at tail drop of the queue";
             }
             leaf queue-counters-tail-drop-bytes-rate {
               type int32;
               description
                 "Number of packets dropped at tail drop of the queue";
             }
             leaf queue-counters-ecn-ce-packets {
               type int32;
               description
                 "Total number of ECN CE packets";
             }
             leaf queue-counters-ecn-ce-packets-rate {
               type int32;
               description
                 "Rate at which ECN CE packets are transmitted";
             }
             leaf queue-counters-ecn-ce-bytes {
               type int32;
               description
                 "Total number of ECN CE bytes";
             }
             leaf queue-counters-ecn-ce-bytes-rate {
               type int32;
               description
                 "Rate at which ECN CE bytes are transmitted";
             }
             leaf queue-counters-rate-limit-drop-packets-na {
               type string;
               description
                 "Number of packets dropped due to rate-limit drop not 
                 available";
             }
             leaf queue-counters-rate-limit-drop-packets {
               type int32;
               description
                 "Number of packets dropped by rate-limit for the queue";
             }
             leaf queue-counters-rate-limit-drop-packets-rate {
               type int32;
               description
                 "Rate at which packets are dropped by rate-limit for the 
                 queue";
             }
             leaf queue-counters-rate-limit-drop-bytes-na {
               type string;
               description
                 "Number of bytes dropped due to tail drop not available";
             }
             leaf queue-counters-rate-limit-drop-bytes {
               type int32;
               description
                 "Number of bytes dropped at the tail of the queue";
             }
             leaf queue-counters-rate-limit-drop-bytes-rate {
               type int32;
               description
                 "Rate at which bytes are dropped at the tail of the queue";
             }
             leaf queue-counters-red-packets-na {
               type string;
               description
                 "Number of packets dropped due to RED not available";
             }
             leaf queue-counters-red-packets {
               type int32;
               description
                 "Number of packets dropped due to RED";
             }
             leaf queue-counters-red-packets-rate {
               type int32;
               description
                 "Rate at which packets are dropped due to RED";
             }
             leaf queue-counters-red-packets-ln {
               type int32;
               description
                 "Number of RED dropped low-loss, non-TCP packets";
             }
             leaf queue-counters-red-packets-rate-ln {
               type int32;
               description
                 "RED drop rate for low-loss, non-TCP packets";
             }
             leaf queue-counters-red-packets-lt {
               type int32;
               description
                 "Number of RED dropped of low-loss, TCP packets";
             }
             leaf queue-counters-red-packets-rate-lt {
               type int32;
               description
                 "RED drop rate for low-loss, TCP packets";
             }
             leaf queue-counters-red-packets-hn {
               type int32;
               description
                 "Number of RED dropped high-loss, non-TCP packets";
             }
             leaf queue-counters-red-packets-rate-hn {
               type int32;
               description
                 "RED drop rate for high-loss, non-TCP packets";
             }
             leaf queue-counters-red-packets-ht {
               type int32;
               description
                 "Number of RED dropped high-loss, TCP packets";
             }
             leaf queue-counters-red-packets-rate-ht {
               type int32;
               description
                 "RED drop rate for high-loss, TCP packets";
             }
             leaf queue-counters-red-packets-low {
               type int32;
               description
                 "Number of RED dropped low-loss packets";
             }
             leaf queue-counters-red-packets-rate-low {
               type int32;
               description
                 "RED drop rate for low-loss packets";
             }
             leaf queue-counters-red-packets-medium-low {
               type int32;
               description
                 "Number of RED dropped medium-low-loss packets";
             }
             leaf queue-counters-red-packets-rate-medium-low {
               type int32;
               description
                 "RED drop rate for medium-low-loss packets";
             }
             leaf queue-counters-red-packets-medium-high {
               type int32;
               description
                 "Number of RED dropped medium-high-loss packets";
             }
             leaf queue-counters-red-packets-rate-medium-high {
               type int32;
               description
                 "RED drop rate for medium-high-loss packets";
             }
             leaf queue-counters-red-packets-medium {
               type int32;
               description
                 "Number of RED dropped medium-loss packets";
             }
             leaf queue-counters-red-packets-rate-medium {
               type int32;
               description
                 "RED drop rate for medium-loss packets";
             }
             leaf queue-counters-red-packets-high {
               type int32;
               description
                 "Number of RED dropped high-loss packets";
             }
             leaf queue-counters-red-packets-rate-high {
               type int32;
               description
                 "RED drop rate for high-loss packets";
             }
             leaf queue-counters-red-bytes-na {
               type string;
               description
                 "Number of bytes dropped due to RED not available";
             }
             leaf queue-counters-red-bytes {
               type int32;
               description
                 "Number of bytes dropped due to RED";
             }
             leaf queue-counters-red-bytes-rate {
               type int32;
               description
                 "Rate at which bytes are dropped due to RED";
             }
             leaf queue-counters-red-bytes-ln {
               type int32;
               description
                 "Number of RED dropped low-loss, non-TCP bytes";
             }
             leaf queue-counters-red-bytes-rate-ln {
               type int32;
               description
                 "RED drop rate for low-loss, non-TCP bytes";
             }
             leaf queue-counters-red-bytes-lt {
               type int32;
               description
                 "Number of RED dropped low-loss, TCP bytes";
             }
             leaf queue-counters-red-bytes-rate-lt {
               type int32;
               description
                 "RED drop rate for low-loss, TCP bytes";
             }
             leaf queue-counters-red-bytes-hn {
               type int32;
               description
                 "Number of RED dropped high-loss, non-TCP bytes";
             }
             leaf queue-counters-red-bytes-rate-hn {
               type int32;
               description
                 "RED drop rate for high-loss, non-TCP bytes";
             }
             leaf queue-counters-red-bytes-ht {
               type int32;
               description
                 "Number of RED dropped high-loss, TCP bytes";
             }
             leaf queue-counters-red-bytes-rate-ht {
               type int32;
               description
                 "RED drop rate for high-loss, TCP bytes";
             }
             leaf queue-counters-red-bytes-low {
               type int32;
               description
                 "Number of RED dropped low-loss bytes";
             }
             leaf queue-counters-red-bytes-rate-low {
               type int32;
               description
                 "RED drop rate for low-loss bytes";
             }
             leaf queue-counters-red-bytes-medium-low {
               type int32;
               description
                 "Number of RED dropped medium-low-loss bytes";
             }
             leaf queue-counters-red-bytes-rate-medium-low {
               type int32;
               description
                 "RED drop rate for medium-low-loss bytes";
             }
             leaf queue-counters-red-bytes-medium-high {
               type int32;
               description
                 "Number of RED dropped medium-high-loss bytes";
             }
             leaf queue-counters-red-bytes-rate-medium-high {
               type int32;
               description
                 "RED drop rate for medium-high-loss bytes";
             }
             leaf queue-counters-red-bytes-medium {
               type int32;
               description
                 "Number of RED dropped medium-loss bytes";
             }
             leaf queue-counters-red-bytes-rate-medium {
               type int32;
               description
                 "RED drop rate for medium-loss bytes";
             }
             leaf queue-counters-red-bytes-high {
               type int32;
               description
                 "Number of RED dropped high-loss bytes";
             }
             leaf queue-counters-red-bytes-rate-high {
               type int32;
               description
                 "RED drop rate for high-loss bytes";
             }
             leaf queue-counters-timestamp {
               type int32;
               description
                 "Last packet enqueued timestamp";
             }
             leaf queue-counters-total-drop-packets-rate {
               type int32;
               description
                 "Number of total packets dropped at the queue";
             }
             leaf queue-counters-total-drop-bytes {
               type int32;
               description
                 "Number of total packets dropped at the queue";
             }
             leaf queue-counters-total-drop-bytes-rate {
               type int32;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
         }
         container voq-counters {
           description
             "VOQ counter statistics";
           leaf voq-counters-error-message {
             type string;
             description
               "VOQ statistics not available for this interface";
           }
           container voq {
             description
               "Counters for a single voq";
             container fpc {
               description
                 "Counters for a single FPC";
               leaf fpc-no {
                 type int32;
                 description
                   "FPC number";
               }
               container pfe {
                 description
                   "Counters for a single PFE";
                 leaf-list pfe-no {
                   type int32;
                   description
                     "PFE number";
                 }
                 leaf voq-counters-tail-drop-packets {
                   type int32;
                   description
                     "Tail DROP packet count";
                 }
                 leaf voq-counters-tail-drop-packets-rate {
                   type int32;
                   description
                     "Rate at which tail packets are dropped";
                 }
                 leaf voq-counters-tail-drop-bytes {
                   type int32;
                   description
                     "Tail DROP bytes count";
                 }
                 leaf voq-counters-tail-drop-bytes-rate {
                   type int32;
                   description
                     "Rate at which tail bytes are dropped";
                 }
                 leaf voq-counters-drop-packets {
                   type int32;
                   description
                     "DROP packet count";
                 }
                 leaf voq-counters-drop-packets-rate {
                   type int32;
                   description
                     "Rate at which packets are dropped";
                 }
                 leaf voq-counters-drop-bytes {
                   type int32;
                   description
                     "DROP bytes count";
                 }
                 leaf voq-counters-drop-bytes-rate {
                   type int32;
                   description
                     "Rate at which bytes are dropped";
                 }
                 leaf voq-counters-queued-packets {
                   type int32;
                   description
                     "QUEUED packets count";
                 }
                 leaf voq-counters-queued-packets-rate {
                   type int32;
                   description
                     "Rate at which packets are queued";
                 }
                 leaf voq-counters-queued-bytes {
                   type int32;
                   description
                     "QUEUED bytes count";
                 }
                 leaf voq-counters-queued-bytes-rate {
                   type int32;
                   description
                     "Rate at which bytes are queued";
                 }
                 leaf voq-counters-transmitted-packets {
                   type int32;
                   description
                     "Transmitted packets count";
                 }
                 leaf voq-counters-transmitted-packets-rate {
                   type int32;
                   description
                     "Rate at which packets are transmitted";
                 }
                 leaf voq-counters-transmitted-bytes {
                   type int32;
                   description
                     "Transmitted bytes count";
                 }
                 leaf voq-counters-transmitted-bytes-rate {
                   type int32;
                   description
                     "Rate at which bytes are transmitted";
                 }
                 leaf voq-counters-queue-depth-bytes-current {
                   type int32;
                   description
                     "Current queue length";
                 }
                 leaf voq-counters-queue-depth-bytes-peak {
                   type int32;
                   description
                     "Peak queue length";
                 }
                 leaf voq-counters-queue-depth-bytes-average {
                   type int32;
                   description
                     "Average queue length";
                 }
               }
             }
             leaf queue-number {
               type uint32;
               description
                 "Queue number";
             }
             leaf forwarding-class-name {
               type string;
               description
                 "Forwarding class name associated with queue";
             }
             leaf restricted-forwarding-class-name {
               type string;
             }
           }
         }
         container ingress-queue-counters {
           description
             "Ingress queue counter statistics";
           list queue {
             key "queue-number";
             description
               "Counters for a single queue";
             leaf queue-number {
               type uint32;
               description
                 "Queue number";
             }
             leaf forwarding-class-name {
               type string;
               description
                 "Forwarding class name associated with queue";
             }
             leaf queue-counters-queued-packets {
               type int32;
               description
                 "Queued packet count";
             }
             leaf queue-counters-queued-packets-rate {
               type int32;
               description
                 "Rate at which packets are queued";
             }
             leaf queue-counters-queued-bytes {
               type int32;
               description
                 "Queued bytes count";
             }
             leaf queue-counters-queued-bytes-rate {
               type int32;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets {
               type int32;
               description
                 "Total number of transmitted packets";
             }
             leaf queue-counters-trans-packets-rate {
               type int32;
               description
                 "Rate at which packets are transmitted";
             }
             leaf queue-counters-trans-bytes {
               type int32;
               description
                 "Total number of transmitted bytes";
             }
             leaf queue-counters-trans-bytes-rate {
               type int32;
               description
                 "Rate at which bytes are transmitted";
             }
             leaf queue-counters-tail-drop-packets-na {
               type string;
               description
                 "Number of packets dropped due to tail drop not available";
             }
             leaf queue-counters-tail-drop-packets {
               type int32;
               description
                 "Number of packets dropped at the tail of the queue";
             }
             leaf queue-counters-tail-drop-packets-rate {
               type int32;
               description
                 "Rate at which packets are dropped at tail of queue";
             }
             leaf queue-counters-tail-drop-bytes {
               type int32;
               description
                 "Number of packets dropped at tail drop of the queue";
             }
             leaf queue-counters-tail-drop-bytes-rate {
               type int32;
               description
                 "Number of packets dropped at tail drop of the queue";
             }
             leaf queue-counters-ecn-ce-packets {
               type int32;
               description
                 "Total number of ECN CE packets";
             }
             leaf queue-counters-ecn-ce-packets-rate {
               type int32;
               description
                 "Rate at which ECN CE packets are transmitted";
             }
             leaf queue-counters-ecn-ce-bytes {
               type int32;
               description
                 "Total number of ECN CE bytes";
             }
             leaf queue-counters-ecn-ce-bytes-rate {
               type int32;
               description
                 "Rate at which ECN CE bytes are transmitted";
             }
             leaf queue-counters-rate-limit-drop-packets-na {
               type string;
               description
                 "Number of packets dropped due to rate-limit drop not 
                 available";
             }
             leaf queue-counters-rate-limit-drop-packets {
               type int32;
               description
                 "Number of packets dropped by rate-limit for the queue";
             }
             leaf queue-counters-rate-limit-drop-packets-rate {
               type int32;
               description
                 "Rate at which packets are dropped by rate-limit for the 
                 queue";
             }
             leaf queue-counters-rate-limit-drop-bytes-na {
               type string;
               description
                 "Number of bytes dropped due to tail drop not available";
             }
             leaf queue-counters-rate-limit-drop-bytes {
               type int32;
               description
                 "Number of bytes dropped at the tail of the queue";
             }
             leaf queue-counters-rate-limit-drop-bytes-rate {
               type int32;
               description
                 "Rate at which bytes are dropped at the tail of the queue";
             }
             leaf queue-counters-red-packets-na {
               type string;
               description
                 "Number of packets dropped due to RED not available";
             }
             leaf queue-counters-red-packets {
               type int32;
               description
                 "Number of packets dropped due to RED";
             }
             leaf queue-counters-red-packets-rate {
               type int32;
               description
                 "Rate at which packets are dropped due to RED";
             }
             leaf queue-counters-red-packets-ln {
               type int32;
               description
                 "Number of RED dropped low-loss, non-TCP packets";
             }
             leaf queue-counters-red-packets-rate-ln {
               type int32;
               description
                 "RED drop rate for low-loss, non-TCP packets";
             }
             leaf queue-counters-red-packets-lt {
               type int32;
               description
                 "Number of RED dropped of low-loss, TCP packets";
             }
             leaf queue-counters-red-packets-rate-lt {
               type int32;
               description
                 "RED drop rate for low-loss, TCP packets";
             }
             leaf queue-counters-red-packets-hn {
               type int32;
               description
                 "Number of RED dropped high-loss, non-TCP packets";
             }
             leaf queue-counters-red-packets-rate-hn {
               type int32;
               description
                 "RED drop rate for high-loss, non-TCP packets";
             }
             leaf queue-counters-red-packets-ht {
               type int32;
               description
                 "Number of RED dropped high-loss, TCP packets";
             }
             leaf queue-counters-red-packets-rate-ht {
               type int32;
               description
                 "RED drop rate for high-loss, TCP packets";
             }
             leaf queue-counters-red-packets-low {
               type int32;
               description
                 "Number of RED dropped low-loss packets";
             }
             leaf queue-counters-red-packets-rate-low {
               type int32;
               description
                 "RED drop rate for low-loss packets";
             }
             leaf queue-counters-red-packets-medium-low {
               type int32;
               description
                 "Number of RED dropped medium-low-loss packets";
             }
             leaf queue-counters-red-packets-rate-medium-low {
               type int32;
               description
                 "RED drop rate for medium-low-loss packets";
             }
             leaf queue-counters-red-packets-medium-high {
               type int32;
               description
                 "Number of RED dropped medium-high-loss packets";
             }
             leaf queue-counters-red-packets-rate-medium-high {
               type int32;
               description
                 "RED drop rate for medium-high-loss packets";
             }
             leaf queue-counters-red-packets-medium {
               type int32;
               description
                 "Number of RED dropped medium-loss packets";
             }
             leaf queue-counters-red-packets-rate-medium {
               type int32;
               description
                 "RED drop rate for medium-loss packets";
             }
             leaf queue-counters-red-packets-high {
               type int32;
               description
                 "Number of RED dropped high-loss packets";
             }
             leaf queue-counters-red-packets-rate-high {
               type int32;
               description
                 "RED drop rate for high-loss packets";
             }
             leaf queue-counters-red-bytes-na {
               type string;
               description
                 "Number of bytes dropped due to RED not available";
             }
             leaf queue-counters-red-bytes {
               type int32;
               description
                 "Number of bytes dropped due to RED";
             }
             leaf queue-counters-red-bytes-rate {
               type int32;
               description
                 "Rate at which bytes are dropped due to RED";
             }
             leaf queue-counters-red-bytes-ln {
               type int32;
               description
                 "Number of RED dropped low-loss, non-TCP bytes";
             }
             leaf queue-counters-red-bytes-rate-ln {
               type int32;
               description
                 "RED drop rate for low-loss, non-TCP bytes";
             }
             leaf queue-counters-red-bytes-lt {
               type int32;
               description
                 "Number of RED dropped low-loss, TCP bytes";
             }
             leaf queue-counters-red-bytes-rate-lt {
               type int32;
               description
                 "RED drop rate for low-loss, TCP bytes";
             }
             leaf queue-counters-red-bytes-hn {
               type int32;
               description
                 "Number of RED dropped high-loss, non-TCP bytes";
             }
             leaf queue-counters-red-bytes-rate-hn {
               type int32;
               description
                 "RED drop rate for high-loss, non-TCP bytes";
             }
             leaf queue-counters-red-bytes-ht {
               type int32;
               description
                 "Number of RED dropped high-loss, TCP bytes";
             }
             leaf queue-counters-red-bytes-rate-ht {
               type int32;
               description
                 "RED drop rate for high-loss, TCP bytes";
             }
             leaf queue-counters-red-bytes-low {
               type int32;
               description
                 "Number of RED dropped low-loss bytes";
             }
             leaf queue-counters-red-bytes-rate-low {
               type int32;
               description
                 "RED drop rate for low-loss bytes";
             }
             leaf queue-counters-red-bytes-medium-low {
               type int32;
               description
                 "Number of RED dropped medium-low-loss bytes";
             }
             leaf queue-counters-red-bytes-rate-medium-low {
               type int32;
               description
                 "RED drop rate for medium-low-loss bytes";
             }
             leaf queue-counters-red-bytes-medium-high {
               type int32;
               description
                 "Number of RED dropped medium-high-loss bytes";
             }
             leaf queue-counters-red-bytes-rate-medium-high {
               type int32;
               description
                 "RED drop rate for medium-high-loss bytes";
             }
             leaf queue-counters-red-bytes-medium {
               type int32;
               description
                 "Number of RED dropped medium-loss bytes";
             }
             leaf queue-counters-red-bytes-rate-medium {
               type int32;
               description
                 "RED drop rate for medium-loss bytes";
             }
             leaf queue-counters-red-bytes-high {
               type int32;
               description
                 "Number of RED dropped high-loss bytes";
             }
             leaf queue-counters-red-bytes-rate-high {
               type int32;
               description
                 "RED drop rate for high-loss bytes";
             }
             leaf queue-counters-timestamp {
               type int32;
               description
                 "Last packet enqueued timestamp";
             }
             leaf queue-counters-total-drop-packets {
               type int32;
               description
                 "Number of total packets dropped at the queue";
             }
             leaf queue-counters-total-drop-packets-rate {
               type int32;
               description
                 "Number of total packets dropped at the queue";
             }
             leaf queue-counters-total-drop-bytes {
               type int32;
               description
                 "Number of total packets dropped at the queue";
             }
             leaf queue-counters-total-drop-bytes-rate {
               type int32;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
           container interface-cos-short-summary {
             description
               "Summary of queue information on an interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           list queue-num-forwarding-class-name-map {
             key "queue-number";
             leaf queue-number {
               type uint32;
               description
                 "Queue number";
             }
             leaf forwarding-class-name {
               type string;
               description
                 "Forwarding class name associated with queue";
             }
           }
         }
         container forwarding-class-counters {
           description
             "Forwarding-class counter statistics";
           leaf forwarding-class-counters-error-message {
             type string;
             description
               "Forwarding-class statistics not available for this interface";
           }
           container ipv4-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container ipv6-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container mpls-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container layer2-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container other-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container protocol-aggregate-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container forwarding-class-statistics {
             container protocol-aggregate-forwarding-class-counters {
             }
             container ipv4-forwarding-class-counters {
             }
             container ipv6-forwarding-class-counters {
             }
             container mpls-forwarding-class-counters {
             }
             container layer2-forwarding-class-counters {
             }
             container other-forwarding-class-counters {
             }
           }
           container forwarding-class-accounting-parameters {
             leaf forwarding-class-accounting-for-protocol {
               type string;
             }
             leaf forwarding-class-accounting-for-traffic-direction {
               type string;
             }
             leaf forwarding-class-accounting-for-traffic-type {
               type string;
             }
             leaf forwarding-class-accounting-overhead-bytes {
               type uint32;
             }
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container multilink-bundle-options {
           leaf filler-packet-interval {
             type int32;
           }
         }
         container multilink-traffic-statistics {
           container bundle {
           }
           container class {
             description
               "Multilink class traffic statistics";
           }
           container multilink-detail-statistics {
             container bundle-detail {
             }
             container class-detail {
             }
           }
           container crtp {
             container crtp-sessions {
               leaf input-frames {
                 type int32;
               }
               leaf output-frames {
                 type int32;
               }
             }
             list crtp-statistics {
               key "name";
               leaf name {
                 type string;
                 description
                   "Name of this item";
               }
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
           }
         }
         container traffic-statistics {
           leaf input-bps {
             type int32;
           }
           leaf input-pps {
             type int32;
           }
           leaf output-bps {
             type int32;
           }
           leaf output-pps {
             type int32;
           }
           leaf input-packets {
             type uint64;
           }
           leaf output-packets {
             type uint64;
           }
           container ipv4-traffic-statistics {
             leaf input-bps {
               type int32;
             }
             leaf output-bps {
               type int32;
             }
             leaf input-pps {
               type int32;
             }
             leaf output-pps {
               type int32;
             }
             leaf input-bytes {
               type int32;
             }
             leaf output-bytes {
               type int32;
             }
             leaf input-packets {
               type uint64;
             }
             leaf output-packets {
               type uint64;
             }
           }
           leaf input-bytes {
             type int32;
           }
           leaf output-bytes {
             type int32;
           }
           container ipv6-transit-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-traffic-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-total-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
         }
         container multicast-statistics {
           description
             "Multicast statistics for interface";
           leaf multicast-statistics-header {
             type empty;
           }
           container ipv4-multicast-statistics {
             description
               "IPV4 multicast statistics for interface";
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-multicast-statistics {
             description
               "IPV6 multicast statistics for interface";
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
         }
         container ingress-traffic-statistics {
           description
             "Traffic statistics at ingress before entering Packet 
             Forwarding Engine";
           leaf input-bps {
             type int32;
           }
           leaf input-pps {
             type int32;
           }
           leaf input-drop-bps {
             type int32;
             description
               "Drop rate at ingress in bits per second ";
           }
           leaf input-drop-pps {
             type int32;
             description
               "Drop rate at ingress in packets per second ";
           }
           leaf input-bytes {
             type int32;
           }
           leaf input-packets {
             type uint64;
           }
           leaf input-drop-bytes {
             type int32;
             description
               "Drop statistics at ingress in bytes";
           }
           leaf input-drop-packets {
             type int32;
             description
               "Drop statistics at ingress in packets";
           }
         }
         container local-traffic-statistics {
           description
             "Statistics for locally originated traffic";
         }
         container transit-traffic-statistics {
           description
             "Statistics for traffic passing through the Packet Forwarding 
             Engine";
         }
         container layer3-statistics {
         }
         container keepalive-statistics {
           description
             "Keepalive statistics for this interface";
           leaf keepalive-lmi-descriptor {
             type string;
           }
           leaf keepalive-input-count {
             type int32;
           }
           leaf keepalive-input-time {
             type string;
           }
           leaf keepalive-output-count {
             type int32;
           }
           leaf keepalive-output-time {
             type string;
           }
         }
         container virtual-circuit-information {
           description
             "Operational information and statistics for a virtual circuit";
           container traffic-statistics {
             leaf input-bps {
               type int32;
             }
             leaf input-pps {
               type int32;
             }
             leaf output-bps {
               type int32;
             }
             leaf output-pps {
               type int32;
             }
             leaf input-packets {
               type uint64;
             }
             leaf output-packets {
               type uint64;
             }
             container ipv4-traffic-statistics {
               leaf input-bps {
                 type int32;
               }
               leaf output-bps {
                 type int32;
               }
               leaf input-pps {
                 type int32;
               }
               leaf output-pps {
                 type int32;
               }
               leaf input-bytes {
                 type int32;
               }
               leaf output-bytes {
                 type int32;
               }
               leaf input-packets {
                 type uint64;
               }
               leaf output-packets {
                 type uint64;
               }
             }
             leaf input-bytes {
               type int32;
             }
             leaf output-bytes {
               type int32;
             }
             container ipv6-transit-statistics {
               leaf input-bytes {
                 type int32;
               }
               leaf input-bps {
                 type int32;
               }
               leaf output-bytes {
                 type int32;
               }
               leaf output-bps {
                 type int32;
               }
               leaf input-packets {
                 type uint64;
               }
               leaf input-pps {
                 type int32;
               }
               leaf output-packets {
                 type uint64;
               }
               leaf output-pps {
                 type int32;
               }
             }
             container ipv6-traffic-statistics {
               leaf input-bytes {
                 type int32;
               }
               leaf input-bps {
                 type int32;
               }
               leaf output-bytes {
                 type int32;
               }
               leaf output-bps {
                 type int32;
               }
               leaf input-packets {
                 type uint64;
               }
               leaf input-pps {
                 type int32;
               }
               leaf output-packets {
                 type uint64;
               }
               leaf output-pps {
                 type int32;
               }
             }
             container ipv6-total-statistics {
               leaf input-bytes {
                 type int32;
               }
               leaf input-bps {
                 type int32;
               }
               leaf output-bytes {
                 type int32;
               }
               leaf output-bps {
                 type int32;
               }
               leaf input-packets {
                 type uint64;
               }
               leaf input-pps {
                 type int32;
               }
               leaf output-packets {
                 type uint64;
               }
               leaf output-pps {
                 type int32;
               }
             }
           }
           container atm-cos-information {
             leaf vc-cos-mode {
               type string;
               description
                 "Virtual circuit CoS scheduling mode";
             }
             list atm-cos-queue {
               container atm-cos-queue-parameters {
                 leaf cos-forwarding-class-name {
                   type string;
                   description
                     "Forwarding class name associated with queue";
                 }
                 leaf cos-queue-number {
                   type int32;
                   description
                     "Queue number";
                 }
                 leaf scheduling-priority {
                   type string;
                   description
                     "Scheduling priority";
                 }
                 leaf transmit-weight-cells {
                   type int32;
                   description
                     "Weight to apply to scheduling as number of cells";
                 }
                 leaf transmit-weight-percent {
                   type int32;
                   description
                     "Weight to apply to scheduling as fill percentage";
                 }
                 leaf epd-threshold {
                   type int32;
                   description
                     "Early packet drop threshold";
                 }
                 leaf epd-threshold-plp0 {
                   type int32;
                   description
                     "Early packet drop threshold for PLP 0";
                 }
                 leaf epd-threshold-plp1 {
                   type int32;
                   description
                     "Early packet drop threshold for PLP 1";
                 }
                 container linear-red-drop-profile {
                   leaf queue-depth {
                     type int32;
                     description
                       "Maximum queue depth";
                   }
                   leaf low-red {
                     type int32;
                     description
                       "Fill level percentage when linear RED is applied for
                       low PLP";
                   }
                   leaf high-red {
                     type int32;
                     description
                       "Fill level percentage when linear RED is applied for
                       high PLP";
                   }
                   leaf max-low-red {
                     type int32;
                     description
                       "Fill level percentage with 100% packet drop for low 
                       PLP";
                   }
                   leaf max-high-red {
                     type int32;
                     description
                       "Fill level percentage with 100% packet drop for high
                       PLP";
                   }
                 }
               }
               container atm-cos-queue-statistics {
                 leaf atm-output-bytes {
                   type int32;
                 }
                 leaf atm-output-packets {
                   type int32;
                 }
                 leaf atm-packet-drops {
                   type int32;
                 }
               }
               container atm-cos-plp-statistics {
                 leaf atm-plp0-output-bytes {
                   type int32;
                 }
                 leaf atm-plp1-output-bytes {
                   type int32;
                 }
                 leaf atm-plp0-output-packets {
                   type int32;
                 }
                 leaf atm-plp1-output-packets {
                   type int32;
                 }
                 leaf atm-plp0-byte-drops {
                   type int32;
                 }
                 leaf atm-plp1-byte-drops {
                   type int32;
                 }
                 leaf atm-plp0-packet-drops {
                   type int32;
                 }
                 leaf atm-plp1-packet-drops {
                   type int32;
                 }
               }
             }
           }
         }
         container allowed-host-inbound-traffic {
           description
             "List of allowed system services and protocols";
           leaf inbound-all-protocols {
             type empty;
             description
               "All protocols";
           }
           leaf inbound-any-service {
             type empty;
             description
               "Any service";
           }
           leaf inbound-bootp {
             type empty;
             description
               "Bootp and dhcp relay-agent service";
           }
           leaf inbound-bfd {
             type empty;
             description
               "Bidirectional Forwarding Detection";
           }
           leaf inbound-bgp {
             type empty;
             description
               "Border Gateway Protocol";
           }
           leaf inbound-dns {
             type empty;
             description
               "DNS and DNS-proxy service";
           }
           leaf inbound-dvmrp {
             type empty;
             description
               "Distance Vector Multicast Routing Protocol";
           }
           leaf inbound-igmp {
             type empty;
             description
               "Internet Group Management Protocol";
           }
           leaf inbound-ldp {
             type empty;
             description
               "Label Distribution Protocol";
           }
           leaf inbound-msdp {
             type empty;
             description
               "Multicast Source Discovery Protocol";
           }
           leaf inbound-nhrp {
             type empty;
             description
               "Next Hop Resolution Protocol";
           }
           leaf inbound-ospf {
             type empty;
             description
               "Open Shortest Path First";
           }
           leaf inbound-ospf3 {
             type empty;
             description
               "Open Shortest Path First version 3";
           }
           leaf inbound-pgm {
             type empty;
             description
               "Pragmatic General Multicast";
           }
           leaf inbound-pim {
             type empty;
             description
               "Protocol Independent Multicast";
           }
           leaf inbound-rip {
             type empty;
             description
               "Routing Information Protocol";
           }
           leaf inbound-ripng {
             type empty;
             description
               "Routing Information Protocol next generation";
           }
           leaf inbound-router-discovery {
             type empty;
             description
               "Router Discovery";
           }
           leaf inbound-rsvp {
             type empty;
             description
               "Resource Reservation Protocol";
           }
           leaf inbound-sap {
             type empty;
             description
               "Session Announcement Protocol";
           }
           leaf inbound-vrrp {
             type empty;
             description
               "Virtual Router Redundancy Protocol";
           }
           leaf inbound-all-services {
             type empty;
             description
               "All system services";
           }
           leaf inbound-dhcp {
             type empty;
             description
               "Dynamic Host Configuration Protocol";
           }
           leaf inbound-finger {
             type empty;
             description
               "Finger service";
           }
           leaf inbound-ftp {
             type empty;
             description
               "File Transfer Protocol";
           }
           leaf inbound-tftp {
             type empty;
             description
               "Trivial File Transfer Protocol";
           }
           leaf ident-reset {
             type empty;
             description
               "Send back TCP RST to IDENT request for port 113";
           }
           leaf inbound-http {
             type empty;
             description
               "Web management service using HTTP";
           }
           leaf inbound-https {
             type empty;
             description
               "Web management service using HTTP secured by SSL";
           }
           leaf inbound-ike {
             type empty;
             description
               "Internet Key Exchange";
           }
           leaf inbound-netconf {
             type empty;
             description
               "NETCONF service";
           }
           leaf inbound-ping {
             type empty;
             description
               "Internet Control Message Protocol echo requests";
           }
           leaf inbound-reverse-telnet {
             type empty;
             description
               "Reverse telnet service";
           }
           leaf inbound-reverse-ssh {
             type empty;
             description
               "Reverse SSH service";
           }
           leaf inbound-rlogin {
             type empty;
             description
               "Rlogin service";
           }
           leaf inbound-rpm {
             type empty;
             description
               "Real-time performance monitoring";
           }
           leaf inbound-rsh {
             type empty;
             description
               "Rsh service";
           }
           leaf inbound-snmp {
             type empty;
             description
               "Simple Network Management Protocol service";
           }
           leaf inbound-snmp-trap {
             type empty;
             description
               "Simple Network Management Protocol traps";
           }
           leaf inbound-ssh {
             type empty;
             description
               "SSH service";
           }
           leaf inbound-telnet {
             type empty;
             description
               "Telnet service";
           }
           leaf inbound-traceroute {
             type empty;
             description
               "Traceroute service";
           }
           leaf inbound-xnm-clear-text {
             type empty;
             description
               "JUNOScript API for unencrypted traffic over TCP";
           }
           leaf inbound-xnm-ssl {
             type empty;
             description
               "JUNOScript API service over SSL";
           }
           leaf inbound-lsping {
             type empty;
             description
               "Label Switched Path ping service";
           }
           leaf inbound-lsselfping {
             type empty;
             description
               "Label Switched Path self ping service";
           }
           leaf inbound-ntp {
             type empty;
             description
               "Network Time Protocol service";
           }
           leaf inbound-sip {
             type empty;
             description
               "Session Initiation Protocol service";
           }
           leaf inbound-dhcpv6 {
             type empty;
             description
               "Dynamic Host Configuration Protocol for IPv6 service";
           }
           leaf inbound-r2cp {
             type empty;
             description
               "Radio Router Control Protocol service";
           }
           leaf inbound-webapi-clear-text {
             type empty;
             description
               "Webapi service using http";
           }
           leaf inbound-webapi-ssl {
             type empty;
             description
               "Webapi service using HTTP secured by SSL";
           }
           leaf inbound-tcp-encap {
             type empty;
             description
               "Tcp encapsulation service";
           }
           leaf inbound-sdwan-appqoe {
             type empty;
             description
               "Sdwan Appqoe service";
           }
           leaf inbound-high-availability {
             type empty;
             description
               "High Availability  service";
           }
         }
         list policer-information {
           description
             "Interface policer information";
           leaf policer-family {
             type string;
             description
               "Protocol family of the policer";
           }
           leaf policer-input {
             type string;
             description
               "Name of the input policer";
           }
           leaf policer-output {
             type string;
             description
               "Name of the output policer";
           }
         }
         list address-family {
           container pppoe-underlying-information {
             description
               "PPPoE Underlying information";
             list pppoe-underlying-interface {
               leaf dynamic-profile {
                 type string;
                 description
                   "Dynamic Profile name";
               }
               leaf service-name-table {
                 type string;
                 description
                   "Name of Service Name Table";
               }
               leaf max-sessions {
                 type int32;
                 description
                   "Maximum number of PPPoE sessions";
               }
               leaf max-sessions-vsa-ignore {
                 type string;
                 description
                   "Ignore max-sessions VSA";
               }
               leaf duplicate-protection {
                 type string;
                 description
                   "Duplicate protection mode";
               }
               leaf short-cycle-protection {
                 type string;
                 description
                   "Short cycle protection mode";
               }
               leaf direct-connect {
                 type string;
                 description
                   "Direct connect mode";
               }
               leaf ac-name {
                 type string;
                 description
                   "Access Concentrator name";
               }
               leaf underlying-interface-name {
                 type string;
                 description
                   "Underlying interface name";
               }
               leaf underlying-interface-index {
                 type string;
                 description
                   "Underlying interface index";
               }
               leaf encapsulation-type-identifier {
                 type string;
                 description
                   "Encapsulation type identifier";
               }
               leaf state {
                 type string;
                 description
                   "State";
               }
               leaf active-sessions {
                 type int32;
                 description
                   "Number of active PPPoE sessions";
               }
               leaf aci-autosensing {
                 type string;
                 description
                   "ACI VLAN Autosensing mode";
               }
               leaf line-identity-autosensing {
                 type string;
                 description
                   "Line Identity Autosensing mode";
               }
             }
           }
           list interface-address {
           }
           container destination-class-statistics {
             description
               "Destination class usage (DCU) statistics";
           }
           container source-class-statistics {
             description
               "Source class usage (SCU) statistics";
           }
           list local-bias-information {
             leaf local-bias-vtep-ifl-name {
               type string;
               description
                 "Interface name";
             }
             leaf local-bias-vtep-ifl-index {
               type uint32;
               description
                 "Interface index";
             }
             leaf local-bias-vtep-address {
               type string;
               description
                 "Protocol address of the connection";
             }
           }
           leaf ft-iff-dest-port {
             type uint32;
             description
               "Destination UDP port to be used for this family";
           }
         }
         list bridge-iff-properties {
           description
             "Information about Ethernet-switching address family";
         }
         container l2circuit-info {
           leaf out-of-sequence {
             type int32;
           }
           leaf denied-packets {
             type int32;
           }
           leaf cell-bundle-size {
             type int32;
           }
           leaf cell-bundle-timeout {
             type int32;
           }
           leaf cell-timeout-count {
             type int32;
           }
         }
         container media-information {
           description
             "Information about media alarms";
           leaf media-type {
             type string;
             description
               "Type of media this information is for";
           }
           list media-alarm {
             leaf media-alarm-name {
               type string;
             }
             leaf media-alarm-count {
               type int32;
             }
             leaf media-alarm-seconds {
               type int32;
             }
             leaf media-alarm-state {
               type string;
             }
             leaf ce-counter-name {
               type string;
               description
                 "Circuit Emulation counter information";
             }
             leaf ce-counter-packets {
               type int32;
               description
                 "Circuit Emulation number of packets";
             }
             leaf ce-counter-bytes {
               type int32;
               description
                 "Circuit Emulation number of bytes";
             }
             leaf ce-counter-count {
               type int32;
               description
                 "Circuit Emulation number of event occurrences";
             }
           }
           leaf ds1-timeslots {
             type string;
           }
           leaf ds1-line-encoding {
             type string;
           }
           leaf ds1-byte-encoding {
             type string;
           }
           leaf ds1-data-inversion {
             type string;
           }
           leaf idle-cycle-flag {
             type string;
           }
           leaf start-end-flag {
             type string;
           }
           leaf ds0-byte-encoding {
             type string;
           }
           leaf ds0-data-inversion {
             type string;
           }
           leaf e3-data-inversion {
             type string;
           }
           leaf ds1-buildout {
             type string;
             description
               "Number of feet";
           }
         }
         container macsec-statistics {
           description
             "MACSec Statistics ";
           leaf macsec-tx-sc-protected {
             type int32;
             description
               "Protected Secure Channel MACSec packets transmitted";
           }
           leaf macsec-tx-sc-encrypted {
             type int32;
             description
               "Encrypted Secure Channel MACSec packets transmitted";
           }
           leaf macsec-tx-sc-protectedbytes {
             type int32;
             description
               "Protected Secure Channel MACSec bytes transmitted";
           }
           leaf macsec-tx-sc-encryptedbytes {
             type int32;
             description
               "Encrypted Secure Channel MACSec bytes transmitted";
           }
           leaf macsec-rx-sc-ok {
             type int32;
             description
               "OK Secure Association MACSec packets received";
           }
           leaf macsec-rx-sc-validatedbytes {
             type int32;
             description
               "Validated Secure Association MACSec bytes received";
           }
           leaf macsec-rx-sc-decryptedbytes {
             type int32;
             description
               "Validated Secure Association MACSec bytes received";
           }
           leaf interface-name {
             type string;
             description
               "Class-of-service interface name";
           }
           leaf encrypted-packets {
             type uint64;
             description
               "Macsec encrypted packets sent";
           }
           leaf encrypted-bytes {
             type uint64;
             description
               "Macsec encrypted bytes sent";
           }
           leaf protected-packets {
             type uint64;
             description
               "Macsec packets sent with only integrity protection";
           }
           leaf protected-bytes {
             type uint64;
             description
               "Macsec bytes sent with only integrity protection";
           }
           leaf ok-packets {
             type uint64;
             description
               "Macsec packets accepted";
           }
           leaf decrypted-bytes {
             type uint64;
             description
               "Macsec received bytes decrypted";
           }
           leaf decrypted-packets {
             type uint64;
             description
               "Macsec received packets decrypted";
           }
           leaf validated-packets {
             type uint64;
             description
               "Macsec received packets validated";
           }
           leaf validated-bytes {
             type uint64;
             description
               "Macsec received bytes validated";
           }
           leaf untagged-packets {
             type uint64;
             description
               "Macsec untagged packets";
           }
           leaf toolong-packets {
             type uint64;
             description
               "Macsec too long packets transmitted on a secure channel";
           }
           leaf control-packets {
             type uint64;
             description
               "Macsec control packets received on a secure channel";
           }
           leaf tagged-miss-packets {
             type uint64;
             description
               "Macsec tagged miss packets received on a secure channel";
           }
           leaf untagged-hit-packets {
             type uint64;
             description
               "Macsec untagged hit packets received on a secure channel";
           }
           leaf notag-packets {
             type uint64;
             description
               "Macsec no tag packets received on a secure channel";
           }
           leaf badtag-packets {
             type uint64;
             description
               "Macsec bad tag packets received on a secure channel";
           }
           leaf unknown-sci-packets {
             type uint64;
             description
               "Macsec unknown sci packets received on a secure channel";
           }
           leaf no-sci-packets {
             type uint64;
             description
               "Macsec no sci packets received on a secure channel";
           }
           leaf control-pass-packets {
             type uint64;
             description
               "Macsec allowed control packets received on a secure channel";
           }
           leaf uncontrol-pass-packets {
             type uint64;
             description
               "Macsec allowed uncontrol packets received on a secure 
               channel";
           }
           leaf control-fail-packets {
             type uint64;
             description
               "Macsec dropped control packets received on a secure channel";
           }
           leaf uncontrol-fail-packets {
             type uint64;
             description
               "Macsec dropped uncontrol packets received on a secure 
               channel";
           }
           leaf hit-dropped-packets {
             type uint64;
             description
               "Macsec hit dropped packets received on a security channel";
           }
           leaf notusing-sa-packets {
             type uint64;
             description
               "Macsec not using sa packets received on a security channel";
           }
           leaf unused-sa-packets {
             type uint64;
             description
               "Macsec unused sa packets received on a security channel";
           }
           leaf late-packets {
             type uint64;
             description
               "Macsec late packets dropped on a security channel";
           }
           leaf delayed-packets {
             type uint64;
             description
               "Macsec delayed packets accepted on a security channel";
           }
           leaf unchecked-packets {
             type uint64;
             description
               "Macsec unchecked packets accepted on a security channel";
           }
           leaf notvalid-packets {
             type uint64;
             description
               "Macsec not valid packets dropped on a security channel";
           }
           leaf invalid-packets {
             type uint64;
             description
               "Macsec invalid packets accepted on a security channel";
           }
           list secure-channel-sent {
             leaf encrypted-packets {
               type uint64;
               description
                 "Macsec encrypted packets sent";
             }
             leaf encrypted-bytes {
               type uint64;
               description
                 "Macsec encrypted bytes sent";
             }
             leaf protected-packets {
               type uint64;
               description
                 "Macsec packets sent with only integrity protection";
             }
             leaf protected-bytes {
               type uint64;
               description
                 "Macsec bytes sent with only integrity protection";
             }
           }
           list secure-association-sent {
             leaf encrypted-packets {
               type uint64;
               description
                 "Macsec encrypted packets sent";
             }
             leaf encrypted-bytes {
               type uint64;
               description
                 "Macsec encrypted bytes sent";
             }
             leaf protected-packets {
               type uint64;
               description
                 "Macsec packets sent with only integrity protection";
             }
             leaf protected-bytes {
               type uint64;
               description
                 "Macsec bytes sent with only integrity protection";
             }
           }
           list secure-channel-received {
             leaf ok-packets {
               type uint64;
               description
                 "Macsec packets accepted";
             }
             leaf decrypted-packets {
               type uint64;
               description
                 "Macsec received packets decrypted";
             }
             leaf decrypted-bytes {
               type uint64;
               description
                 "Macsec received bytes decrypted";
             }
             leaf validated-packets {
               type uint64;
               description
                 "Macsec received packets validated";
             }
             leaf validated-bytes {
               type uint64;
               description
                 "Macsec received bytes validated";
             }
           }
           list secure-association-received {
             leaf ok-packets {
               type uint64;
               description
                 "Macsec packets accepted";
             }
             leaf decrypted-packets {
               type uint64;
               description
                 "Macsec received packets decrypted";
             }
             leaf decrypted-bytes {
               type uint64;
               description
                 "Macsec received bytes decrypted";
             }
             leaf validated-packets {
               type uint64;
               description
                 "Macsec received packets validated";
             }
             leaf validated-bytes {
               type uint64;
               description
                 "Macsec received bytes validated";
             }
           }
           list macsec-error-information {
             list secure-channel-sent-errors {
               leaf untagged-packets {
                 type uint64;
                 description
                   "Macsec untagged packets";
               }
               leaf toolong-packets {
                 type uint64;
                 description
                   "Macsec too long packets transmitted on a secure channel";
               }
             }
             list secure-channel-received-errors {
               leaf control-packets {
                 type uint64;
                 description
                   "Macsec control packets received on a secure channel";
               }
               leaf tagged-miss-packets {
                 type uint64;
                 description
                   "Macsec tagged miss packets received on a secure channel";
               }
               leaf untagged-hit-packets {
                 type uint64;
                 description
                   "Macsec untagged hit packets received on a secure channel";
               }
               leaf untagged-packets {
                 type uint64;
                 description
                   "Macsec untagged packets";
               }
               leaf notag-packets {
                 type uint64;
                 description
                   "Macsec no tag packets received on a secure channel";
               }
               leaf badtag-packets {
                 type uint64;
                 description
                   "Macsec bad tag packets received on a secure channel";
               }
               leaf unknown-sci-packets {
                 type uint64;
                 description
                   "Macsec unknown sci packets received on a secure channel";
               }
               leaf no-sci-packets {
                 type uint64;
                 description
                   "Macsec no sci packets received on a secure channel";
               }
               leaf control-pass-packets {
                 type uint64;
                 description
                   "Macsec allowed control packets received on a secure 
                   channel";
               }
               leaf control-fail-packets {
                 type uint64;
                 description
                   "Macsec dropped control packets received on a secure 
                   channel";
               }
               leaf uncontrol-pass-packets {
                 type uint64;
                 description
                   "Macsec allowed uncontrol packets received on a secure 
                   channel";
               }
               leaf uncontrol-fail-packets {
                 type uint64;
                 description
                   "Macsec dropped uncontrol packets received on a secure 
                   channel";
               }
             }
             list secure-channel-received-extended {
               leaf hit-dropped-packets {
                 type uint64;
                 description
                   "Macsec hit dropped packets received on a security 
                   channel";
               }
               leaf invalid-packets {
                 type uint64;
                 description
                   "Macsec invalid packets accepted on a security channel";
               }
               leaf late-packets {
                 type uint64;
                 description
                   "Macsec late packets dropped on a security channel";
               }
               leaf delayed-packets {
                 type uint64;
                 description
                   "Macsec delayed packets accepted on a security channel";
               }
               leaf unchecked-packets {
                 type uint64;
                 description
                   "Macsec unchecked packets accepted on a security channel";
               }
               leaf notvalid-packets {
                 type uint64;
                 description
                   "Macsec not valid packets dropped on a security channel";
               }
               leaf notusing-sa-packets {
                 type uint64;
                 description
                   "Macsec not using sa packets received on a security 
                   channel";
               }
               leaf unused-sa-packets {
                 type uint64;
                 description
                   "Macsec unused sa packets received on a security channel";
               }
               leaf untagged-hit-packets {
                 type uint64;
                 description
                   "Macsec untagged hit packets received on a secure channel";
               }
             }
           }
         }
         container security-input-flow-statistics {
           description
             "Flow input statistics for the interface";
           leaf flow-input-self-packets {
             type int32;
             description
               "Input Self packets";
           }
           leaf flow-input-icmp-packets {
             type int32;
             description
               "Input ICMP packets";
           }
           leaf flow-input-vpn-packets {
             type int32;
             description
               "Input VPN packets";
           }
           leaf flow-input-multicast-packets {
             type int32;
             description
               "Input multicast packets";
           }
           leaf flow-input-policy-bytes {
             type int32;
             description
               "Input policy bytes";
           }
           leaf flow-input-connections {
             type int32;
             description
               "Input connections";
           }
         }
         container security-output-flow-statistics {
           description
             "Flow output statistics for the interface";
           leaf flow-output-multicast-packets {
             type int32;
             description
               "Output multicast packets";
           }
           leaf flow-output-policy-bytes {
             type int32;
             description
               "Output bytes permitted by policy";
           }
         }
         container security-error-flow-statistics {
           description
             "Flow error statistics for the interface";
           leaf flow-error-policy-denied {
             type int32;
             description
               "Policy denied";
           }
           leaf flow-error-no-gate-parent {
             type int32;
             description
               "No parent for gate";
           }
           leaf flow-error-syn-protection {
             type int32;
             description
               "Syn-attack protection";
           }
           leaf flow-error-incoming-nat {
             type int32;
             description
               "Incoming NAT errors";
           }
           leaf flow-error-no-tunnel {
             type int32;
             description
               "No tunnel found";
           }
           leaf flow-error-no-more-session {
             type int32;
             description
               "No more sessions";
           }
           leaf flow-error-invalid-zone {
             type int32;
             description
               "Invalid zone received packet";
           }
           leaf flow-error-user-authentication {
             type int32;
             description
               "User authentication errors";
           }
           leaf flow-error-multiple-auth {
             type int32;
             description
               "Multiple user authentications";
           }
           leaf flow-error-multiple-incoming-nat {
             type int32;
             description
               "Multiple incoming NAT";
           }
           leaf flow-error-address-spoofing {
             type int32;
             description
               "Address spoofing";
           }
           leaf flow-error-null-zone {
             type int32;
             description
               "No zone or NULL zone binding";
           }
           leaf flow-error-no-nat-gate {
             type int32;
             description
               "No NAT gate";
           }
           leaf flow-error-no-minor-session {
             type int32;
             description
               "No minor session";
           }
           leaf flow-error-no-session-gate {
             type int32;
             description
               "No session for a gate";
           }
           leaf flow-error-seq-outside-window {
             type int32;
             description
               "TCP sequence number out of window";
           }
           leaf flow-error-no-route-present {
             type int32;
             description
               "No route present";
           }
           leaf flow-error-authentication-failed {
             type int32;
             description
               "Authentication failed";
           }
           leaf flow-error-security-association-missing {
             type int32;
             description
               "Security association not active";
           }
           leaf flow-error-no-sa-for-spi {
             type int32;
             description
               "No SA for incoming SPI";
           }
           leaf flow-error-no-interest-self-packet {
             type int32;
             description
               "No one interested in self packets";
           }
         }
         container lag-traffic-statistics {
           container lag-multicast-statistics {
             leaf lag-multicast-statistics-header {
               type empty;
             }
             container lag-ipv4-multicast-statistics {
               leaf input-packets {
                 type uint64;
               }
               leaf input-pps {
                 type int32;
               }
               leaf input-bytes {
                 type int32;
               }
               leaf input-bps {
                 type int32;
               }
               leaf output-packets {
                 type uint64;
               }
               leaf output-pps {
                 type int32;
               }
               leaf output-bytes {
                 type int32;
               }
               leaf output-bps {
                 type int32;
               }
             }
             container lag-ipv6-multicast-statistics {
               leaf input-packets {
                 type uint64;
               }
               leaf input-pps {
                 type int32;
               }
               leaf input-bytes {
                 type int32;
               }
               leaf input-bps {
                 type int32;
               }
               leaf output-packets {
                 type uint64;
               }
               leaf output-pps {
                 type int32;
               }
               leaf output-bytes {
                 type int32;
               }
               leaf output-bps {
                 type int32;
               }
             }
           }
           list if-distribution-list-information {
           }
           container ifd-lag-traffic-statistics {
           }
         }
         container ifd-lag-traffic-statistics {
         }
         container layer2-input-policer-statistics {
           description
             "Layer 2 input policer statistics for interface";
           leaf policer-medium-low-frames {
             type int32;
             description
               "Number of loss priority medium low frames";
           }
           leaf policer-medium-low-bytes {
             type int32;
             description
               "Number of loss priority medium low bytes";
           }
           leaf policer-medium-low-rate {
             type int32;
             description
               "Rate of loss priority medium low pkts";
           }
         }
         container layer2-output-policer-statistics {
           description
             "Layer 2 output policer statistics for interface";
           leaf policer-medium-low-frames {
             type int32;
             description
               "Number of loss priority medium low frames";
           }
           leaf policer-medium-low-bytes {
             type int32;
             description
               "Number of loss priority medium low bytes";
           }
           leaf policer-medium-low-rate {
             type int32;
             description
               "Rate of loss priority medium low pkts";
           }
         }
         container mac-policer-information {
           container ether-policer-list {
           }
         }
         leaf vrfname {
           type string;
           description
             "Routing instance name";
         }
         leaf zonename {
           type string;
           description
             "Zone name";
         }
       }
       container active-alarms-otn {
       }
       container active-defects-otn {
       }
       container active-alarms-optics {
       }
       container active-defects-optics {
       }
       container optics-defect-information {
         list media-alarm {
           leaf media-alarm-name {
             type string;
           }
           leaf media-alarm-seconds {
             type int32;
           }
           leaf media-alarm-count {
             type int32;
           }
           leaf media-alarm-state {
             type string;
           }
         }
       }
       container optics-fec-information {
         list media-alarm {
           leaf media-alarm-name {
             type string;
           }
           leaf media-alarm-seconds {
             type int32;
           }
           leaf media-alarm-count {
             type int32;
           }
           leaf media-alarm-state {
             type string;
           }
         }
       }
       container active-alerts-otn {
       }
       container links {
         description
           "Aggregated SONET/SDH link information";
         list link-entry {
           description
             "SONET/SDH link information";
           leaf sonet-payload-pointer-curptr {
             type string;
             description
               "Value of the SONET/SDH payload pointer, derived from the H1 
               and H2 overhead bytes";
           }
           leaf sonet-payload-pointer-ptrinc-count {
             type string;
             description
               "Number of times the value of the SONET/SDH payload pointer 
               had positive justification";
           }
           leaf sonet-payload-pointer-ptrdec-count {
             type string;
             description
               "Number of times the value of the SONET/SDH payload pointer 
               had negative justification";
           }
           leaf sonet-payload-pointer-newptr-ndf-count {
             type string;
             description
               "Number of times a new payload pointer was created with the 
               New Data Found flag set";
           }
           leaf sonet-rx-overhead {
             type string;
           }
           leaf sonet-tx-overhead {
             type string;
           }
           leaf sonet-rx-path-trace {
             type string;
             description
               "Received SONET path trace";
           }
           leaf sonet-tx-path-trace {
             type string;
             description
               "Transmitted SONET path trace";
           }
           container active-alarms {
           }
           container active-defects {
           }
           container sonet-errors {
             list media-alarm {
               leaf media-alarm-name {
                 type string;
               }
               leaf media-alarm-count {
                 type int32;
               }
             }
           }
           container sonet-physical-information {
             list media-alarm {
               leaf media-alarm-name {
                 type string;
               }
               leaf media-alarm-seconds {
                 type int32;
               }
               leaf media-alarm-count {
                 type int32;
               }
               leaf media-alarm-state {
                 type string;
               }
             }
           }
           container sonet-section-information {
             list media-alarm {
               leaf media-alarm-name {
                 type string;
               }
               leaf media-alarm-seconds {
                 type int32;
               }
               leaf media-alarm-count {
                 type int32;
               }
               leaf media-alarm-state {
                 type string;
               }
             }
           }
           container sonet-line-information {
             list media-alarm {
               leaf media-alarm-name {
                 type string;
               }
               leaf media-alarm-seconds {
                 type int32;
               }
               leaf media-alarm-count {
                 type int32;
               }
               leaf media-alarm-state {
                 type string;
               }
             }
           }
           container sonet-path-information {
             list media-alarm {
               leaf media-alarm-name {
                 type string;
               }
               leaf media-alarm-seconds {
                 type int32;
               }
               leaf media-alarm-count {
                 type int32;
               }
               leaf media-alarm-state {
                 type string;
               }
             }
           }
           container sonet-vt-information {
             list media-alarm {
               leaf media-alarm-name {
                 type string;
               }
               leaf media-alarm-seconds {
                 type int32;
               }
               leaf media-alarm-count {
                 type int32;
               }
               leaf media-alarm-state {
                 type string;
               }
             }
           }
           container optics-diagnostics {
             description
               "Optics diagnostics";
             leaf output-power {
               type string;
               description
                 "Output power (milliwatts)";
             }
             leaf output-power-dbm {
               type string;
               description
                 "Output power (dBm)";
             }
             leaf input-power {
               type string;
               description
                 "Input power (milliwatts)";
             }
             leaf input-power-dbm {
               type string;
               description
                 "Input power (dBm)";
             }
             leaf per-wave-rx-optical-power {
               type string;
               description
                 "Per-wavelength receiver optical power (milliwatts)";
             }
             leaf per-wave-rx-optical-power-dbm {
               type string;
               description
                 "Per-wavelength receiver optical power (dBm)";
             }
             leaf lane-laser-frequency-error {
               type string;
               description
                 "Lane laser frequency error (MHz)";
             }
             leaf tec-current {
               type string;
               description
                 "Tec current";
             }
             leaf residual-isi {
               type string;
               description
                 "Residual ISI";
             }
             container optics-diagnostics-ot {
               description
                 "OT interface optics diagnostics";
               leaf module-temp-fault {
                 type string;
                 description
                   "Module temperature fault";
               }
               leaf specific-hw-fault {
                 type string;
                 description
                   "Specific HW fault";
               }
               leaf internal-power-fault {
                 type string;
                 description
                   "Internal power fault";
               }
               leaf post-therm-fault {
                 type string;
                 description
                   "Power thermal fault";
               }
               leaf post-fault {
                 type string;
                 description
                   "Post fault";
               }
               leaf command-error {
                 type string;
                 description
                   "Command error";
               }
               leaf rx-pll-lock {
                 type string;
                 description
                   "RX PLL lock";
               }
               leaf network-lane-los {
                 type string;
                 description
                   "Network Lane LOS";
               }
               leaf network-lane-lof {
                 type string;
                 description
                   "Network Lane LOF";
               }
               leaf network-lane-oof {
                 type string;
                 description
                   "Network Lane OOF";
               }
               leaf network-lane-lom {
                 type string;
                 description
                   "Network Lane LOM";
               }
               leaf network-lane-oom {
                 type string;
                 description
                   "Network Lane OOM";
               }
               leaf network-lane-otu-bdi {
                 type string;
                 description
                   "Network Lane OTU BDI";
               }
               leaf lane-rx-fifo-error {
                 type string;
                 description
                   "Lane RX FIFO error";
               }
               leaf tx-reference-clock-fault {
                 type string;
                 description
                   "TX reference clock fault";
               }
               leaf rx-modem-sync-fault {
                 type string;
                 description
                   "Rx modem sync fault";
               }
               leaf rx-modem-loss-of-lock {
                 type string;
                 description
                   "RX modem loss of lock";
               }
               leaf rx-loss-of-alignment {
                 type string;
                 description
                   "RX loss of alignment";
               }
               leaf rx-out-of-alignment {
                 type string;
                 description
                   "RX out of alignment";
               }
               leaf rx-timing-fault {
                 type string;
                 description
                   "Rx timing fault";
               }
               leaf link-msg-data-available {
                 type string;
                 description
                   "Link msg data available";
               }
               leaf modulator-bias-control-loop-fail {
                 type string;
                 description
                   "Modulator Bias Control Loop Fail";
               }
               leaf itla-fault {
                 type string;
                 description
                   "ITLA fault";
               }
               leaf dac-calib-fault {
                 type string;
                 description
                   "DAC calib fault";
               }
               leaf adc-calib-fault {
                 type string;
                 description
                   "ADC calib fault";
               }
               leaf prom-fault {
                 type string;
                 description
                   "PROM fault";
               }
               leaf tx-mod-bias-voa-ctrl-loop-high-alarm {
                 type string;
                 description
                   "TX mod bias VOA ctrl loop high alarm";
               }
               leaf tx-mod-bias-voa-ctrl-loop-low-alarm {
                 type string;
                 description
                   "TX mod bias VOA ctrl loop low alarm";
               }
               leaf rx-phase-control-loop-high-alarm {
                 type string;
                 description
                   "RX phase control loop high alarm";
               }
               leaf rx-phase-control-loop-low-alarm {
                 type string;
                 description
                   "RX phase control loop low alarm";
               }
               leaf rx-phase-control-loop-high-warning {
                 type string;
                 description
                   "RX phase control loop high warning";
               }
               leaf rx-phase-control-loop-low-warning {
                 type string;
                 description
                   "RX phase control loop low warning";
               }
               leaf oa-pump-bias-current-high-alarm {
                 type string;
                 description
                   "OA pump bias current high alarm";
               }
               leaf oa-pump-bias-current-low-alarm {
                 type string;
                 description
                   "OA pump bias current low alarm";
               }
               leaf oa-pump-bias-current-high-warning {
                 type string;
                 description
                   "OA pump bias current high warning";
               }
               leaf oa-pump-bias-current-low-warning {
                 type string;
                 description
                   "OA pump bias current low warning";
               }
               leaf tx-jitter-pll-lol-input-nw-lane {
                 type string;
                 description
                   "Tx jitter PLL LOL i/p nw lane";
               }
               leaf tx-out-of-alignment {
                 type string;
                 description
                   "TX out of alignment";
               }
               leaf tx-cmu-lock-fault {
                 type string;
                 description
                   "Tx CMU lock fault";
               }
               leaf adc-signal-below-threshold {
                 type string;
                 description
                   "ADC signal below threshold";
               }
               leaf tx-output-power-adjustment-fault {
                 type string;
                 description
                   "Tx output power adjustment fault";
               }
               leaf tx-output-mod-converge-fault {
                 type string;
                 description
                   "TX output mod converge fault";
               }
               leaf tx-laser-ready-fault {
                 type string;
                 description
                   "Tx laser ready fault";
               }
               leaf tx-laser-ready-off-fault {
                 type string;
                 description
                   "Tx laser ready off fault";
               }
               leaf tx-asic-ready-fault {
                 type string;
                 description
                   "Tx asic ready fault";
               }
               leaf tx-initialization-fault {
                 type string;
                 description
                   "Tx initialization fault";
               }
               leaf rx-demodulator-lock-fault {
                 type string;
                 description
                   "Rx demodulator lock fault";
               }
               leaf rx-dispersion-lock-fault {
                 type string;
                 description
                   "Rx dispersion lock fault";
               }
               leaf rx-adc-output-fault {
                 type string;
                 description
                   "Rx ADC output fault";
               }
               leaf rx-optical-input-fault {
                 type string;
                 description
                   "Rx optical input fault";
               }
               leaf rx-asic-ready-fault {
                 type string;
                 description
                   "Rx asic ready fault";
               }
               leaf rx-initialization-fault {
                 type string;
                 description
                   "Rx initialization fault";
               }
               leaf tx-mod-bias-high-alarm {
                 type string;
                 description
                   "TX modulator bias high alarm";
               }
               leaf tx-mod-bias-low-alarm {
                 type string;
                 description
                   "TX modulator bias low alarm";
               }
               leaf tx-mod-bias-high-warning {
                 type string;
                 description
                   "TX modulator bias high warning";
               }
               leaf tx-mod-bias-low-warning {
                 type string;
                 description
                   "TX modulator bias low warning";
               }
               leaf rx-pwr-high-alarm {
                 type string;
                 description
                   "RX power high alarm";
               }
               leaf rx-pwr-low-alarm {
                 type string;
                 description
                   "RX power low alarm";
               }
               leaf rx-pwr-high-warn {
                 type string;
                 description
                   "RX power high warning";
               }
               leaf rx-pwr-low-warn {
                 type string;
                 description
                   "RX power low warning";
               }
               leaf tx-laser-power-high-alarm {
                 type string;
                 description
                   "TX laser power high alarm";
               }
               leaf tx-laser-power-low-alarm {
                 type string;
                 description
                   "TX laser power low alarm";
               }
               leaf tx-laser-power-high-warn {
                 type string;
                 description
                   "TX laser power high warning";
               }
               leaf tx-laser-power-low-warn {
                 type string;
                 description
                   "TX laser power low warning";
               }
               leaf tx-bias-high-alarm {
                 type string;
                 description
                   "TX laser current high alarm";
               }
               leaf tx-bias-low-alarm {
                 type string;
                 description
                   "TX laser current low alarm";
               }
               leaf tx-bias-high-warn {
                 type string;
                 description
                   "TX laser current high warning";
               }
               leaf tx-bias-low-warn {
                 type string;
                 description
                   "TX laser current low warning";
               }
               leaf tx-laser-temp-high-alarm {
                 type string;
                 description
                   "TX laser temperature high alarm";
               }
               leaf tx-laser-temp-low-alarm {
                 type string;
                 description
                   "TX laser temperature low alarm";
               }
               leaf tx-laser-temp-high-warn {
                 type string;
                 description
                   "TX laser temperature high warning";
               }
               leaf tx-laser-temp-low-warn {
                 type string;
                 description
                   "TX laser temperature low warning";
               }
             }
             list optics-diagnostics-lane-values {
               key "lane-index";
               leaf lane-index {
                 type int32;
               }
               leaf laser-bias-current {
                 type string;
                 description
                   "Laser bias current (milliamperes)";
               }
               leaf laser-bias-current-not-available {
                 type string;
                 description
                   "Laser bias current measurement not available";
               }
               leaf laser-output-power {
                 type string;
                 description
                   "Laser output power (milliwatts)";
               }
               leaf laser-output-power-dbm {
                 type string;
                 description
                   "Laser output power (dBm)";
               }
               leaf output-power {
                 type string;
                 description
                   "Output power (milliwatts)";
               }
               leaf output-power-dbm {
                 type string;
                 description
                   "Output power (dBm)";
               }
               leaf laser-temperature {
                 type string;
                 description
                   "Laser temperature";
               }
               leaf laser-module-temperature {
                 type string;
                 description
                   "Module temperature";
               }
               leaf laser-tx-optical-power {
                 type string;
                 description
                   "Laser transmitter optical power (milliwatts)";
               }
               leaf laser-tx-optical-power-dbm {
                 type string;
                 description
                   "Laser transmitter optical power (dBm)";
               }
               leaf laser-rx-optical-power {
                 type string;
                 description
                   "Laser receiver optical power (milliwatts)";
               }
               leaf laser-rx-optical-power-dbm {
                 type string;
                 description
                   "Laser receiver optical power (dBm)";
               }
               leaf input-power {
                 type string;
                 description
                   "Input power (milliwatts)";
               }
               leaf input-power-dbm {
                 type string;
                 description
                   "Input power (dBm)";
               }
               leaf input-total-power {
                 type string;
                 description
                   "Input power (total) (milliwatts)";
               }
               leaf input-total-power-dbm {
                 type string;
                 description
                   "Input power (dBm)";
               }
               leaf per-wave-rx-optical-power {
                 type string;
                 description
                   "Per-wavelength receiver optical power (milliwatts)";
               }
               leaf per-wave-rx-optical-power-dbm {
                 type string;
                 description
                   "Per-wavelength receiver optical power (dBm)";
               }
               leaf lane-configured-cd {
                 type string;
                 description
                   "Lane configured chromatic dispersion (ps/nm)";
               }
               leaf lane-chromatic-dispersion {
                 type string;
                 description
                   "Lane chromatic dispersion (ps/nm)";
               }
               leaf lane-avg-chromatic-dispersion {
                 type string;
                 description
                   "Lane avg chromatic dispersion (ps/nm)";
               }
               leaf lane-min-chromatic-dispersion {
                 type string;
                 description
                   "Lane min chromatic dispersion (ps/nm)";
               }
               leaf lane-max-chromatic-dispersion {
                 type string;
                 description
                   "Lane max chromatic dispersion (ps/nm)";
               }
               leaf lane-differential-group-delay {
                 type string;
                 description
                   "Lane differential group delay (ps)";
               }
               leaf lane-avg-differential-group-delay {
                 type string;
                 description
                   "Lane avg differential group delay (ps)";
               }
               leaf lane-min-differential-group-delay {
                 type string;
                 description
                   "Lane min differential group delay (ps)";
               }
               leaf lane-max-differential-group-delay {
                 type string;
                 description
                   "Lane max differential group delay (ps)";
               }
               leaf lane-sopmd {
                 type string;
                 description
                   "Lane sopmd";
               }
               leaf lane-avg-sopmd {
                 type string;
                 description
                   "Lane avg sopmd";
               }
               leaf lane-min-sopmd {
                 type string;
                 description
                   "Lane min sopmd";
               }
               leaf lane-max-sopmd {
                 type string;
                 description
                   "Lane max sopmd";
               }
               leaf q-factor {
                 type string;
                 description
                   "Lane q-factor";
               }
               leaf q-factor-not-available {
                 type string;
                 description
                   "Lane q-factor not available";
               }
               leaf q-margin {
                 type string;
                 description
                   "Lane q-margin";
               }
               leaf q-margin-not-available {
                 type string;
                 description
                   "Lane q-margin not available";
               }
               leaf lane-state-of-polarization {
                 type string;
                 description
                   "Lane state of polarization (rad/s)";
               }
               leaf lane-avg-state-of-polarization {
                 type string;
                 description
                   "Lane avg state of polarization (rad/s)";
               }
               leaf lane-min-state-of-polarization {
                 type string;
                 description
                   "Lane min state of polarization (rad/s)";
               }
               leaf lane-max-state-of-polarization {
                 type string;
                 description
                   "Lane max state of polarization (rad/s)";
               }
               leaf lane-polarization-dependent-loss {
                 type string;
                 description
                   "Lane polarization dependent loss (dB)";
               }
               leaf lane-avg-polarization-dependent-loss {
                 type string;
                 description
                   "Lane avg polarization dependent loss (dB)";
               }
               leaf lane-min-polarization-dependent-loss {
                 type string;
                 description
                   "Lane min polarization dependent loss (dB)";
               }
               leaf lane-max-polarization-dependent-loss {
                 type string;
                 description
                   "Lane max polarization dependent loss (dB)";
               }
               leaf lane-q2-factor {
                 type string;
                 description
                   "Lane Q2 factor (dB)";
               }
               leaf lane-q-value {
                 type string;
                 description
                   "Lane q value (dB)";
               }
               leaf lane-avg-q-value {
                 type string;
                 description
                   "Lane avg q value (dB)";
               }
               leaf lane-min-q-value {
                 type string;
                 description
                   "Lane min q value (dB)";
               }
               leaf lane-max-q-value {
                 type string;
                 description
                   "Lane max q value (dB)";
               }
               leaf lane-carrier-frequency-offset {
                 type string;
                 description
                   "Lane carrier frequency offset (MHz)";
               }
               leaf lane-avg-carrier-frequency-offset {
                 type string;
                 description
                   "Lane avg carrier frequency offset (MHz)";
               }
               leaf lane-min-carrier-frequency-offset {
                 type string;
                 description
                   "Lane min carrier frequency offset (MHz)";
               }
               leaf lane-max-carrier-frequency-offset {
                 type string;
                 description
                   "Lane max carrier frequency offset (MHz)";
               }
               leaf lane-electrical-snr {
                 type string;
                 description
                   "Lane electrical SNR (dB)";
               }
               leaf lane-snr {
                 type string;
                 description
                   "Lane snr (dB)";
               }
               leaf lane-avg-snr {
                 type string;
                 description
                   "Lane avg snr (dB)";
               }
               leaf lane-min-snr {
                 type string;
                 description
                   "Lane min snr (dB)";
               }
               leaf lane-max-snr {
                 type string;
                 description
                   "Lane max snr (dB)";
               }
               leaf lane-rx-laser-bias {
                 type string;
                 description
                   "Lane rx laser bias (mA)";
               }
               leaf lane-rx-laser-power {
                 type string;
                 description
                   "Lane rx laser power (dBm)";
               }
               leaf lane-rx-laser-temp {
                 type string;
                 description
                   "Lane rx laser temp (C)";
               }
               leaf lane-tx-modulator-bias-x-i {
                 type string;
                 description
                   "Lane tx modulator bias x i (mV)";
               }
               leaf lane-tx-modulator-bias-x-q {
                 type string;
                 description
                   "Lane tx modulator bias x q (mV)";
               }
               leaf lane-tx-modulator-bias-y-i {
                 type string;
                 description
                   "Lane tx modulator bias y i (mV)";
               }
               leaf lane-tx-modulator-bias-y-q {
                 type string;
                 description
                   "Lane tx modulator bias y q (mV)";
               }
               leaf lane-tx-modulator-bias-x-phase {
                 type string;
                 description
                   "Lane tx modulator bias x phase (mV)";
               }
               leaf lane-tx-modulator-bias-y-phase {
                 type string;
                 description
                   "Lane tx modulator bias y phase (mV)";
               }
               leaf tx-input-equalization {
                 type string;
                 description
                   "Tx input equalization";
               }
               leaf rx-output-amplitude {
                 type string;
                 description
                   "Rx output amplitude";
               }
               leaf rx-output-pre-emphasis {
                 type string;
                 description
                   "Rx output pre epmhasis";
               }
               leaf lane-laser-frequency-error {
                 type string;
                 description
                   "Lane laser frequency error (MHz)";
               }
               leaf tec-current {
                 type string;
                 description
                   "Tec current";
               }
               leaf residual-isi {
                 type string;
                 description
                   "Residual ISI";
               }
               leaf pam-histogram {
                 type string;
                 description
                   "PAM histogram";
               }
               leaf laser-bias-current-high-alarm {
                 type string;
                 description
                   "Laser bias current high alarm";
               }
               leaf laser-bias-current-low-alarm {
                 type string;
                 description
                   "Laser bias current low alarm";
               }
               leaf laser-bias-current-high-warn {
                 type string;
                 description
                   "Laser bias current high warning";
               }
               leaf laser-bias-current-low-warn {
                 type string;
                 description
                   "Laser bias current low warning";
               }
               leaf laser-tx-power-high-alarm {
                 type string;
                 description
                   "Laser output power high alarm";
               }
               leaf laser-tx-power-low-alarm {
                 type string;
                 description
                   "Laser output power low alarm";
               }
               leaf laser-tx-power-high-warn {
                 type string;
                 description
                   "Laser output power high warning";
               }
               leaf laser-tx-power-low-warn {
                 type string;
                 description
                   "Laser output power low warning";
               }
               leaf tx-power-high-alarm {
                 type string;
                 description
                   "Tx power high alarm";
               }
               leaf tx-power-low-alarm {
                 type string;
                 description
                   "Tx power low alarm";
               }
               leaf tx-power-high-warn {
                 type string;
                 description
                   "Tx power high warning";
               }
               leaf tx-power-low-warn {
                 type string;
                 description
                   "Tx power low warning";
               }
               leaf laser-temp-high-alarm {
                 type string;
                 description
                   "Laser temperature high alarm";
               }
               leaf laser-temp-low-alarm {
                 type string;
                 description
                   "Laser temperature low alarm";
               }
               leaf laser-temp-high-warn {
                 type string;
                 description
                   "Laser temperature high warning";
               }
               leaf laser-temp-low-warn {
                 type string;
                 description
                   "Laser temperature low warning";
               }
               leaf laser-rx-power-high-alarm {
                 type string;
                 description
                   "Laser receiver power high alarm";
               }
               leaf laser-rx-power-low-alarm {
                 type string;
                 description
                   "Laser receiver power low alarm";
               }
               leaf laser-rx-power-high-warn {
                 type string;
                 description
                   "Laser receiver power high warning";
               }
               leaf laser-rx-power-low-warn {
                 type string;
                 description
                   "Laser receiver power low warning";
               }
               leaf rx-power-high-alarm {
                 type string;
                 description
                   "Receiver power high alarm";
               }
               leaf rx-power-low-alarm {
                 type string;
                 description
                   "Receiver power low alarm";
               }
               leaf rx-power-high-warn {
                 type string;
                 description
                   "Receiver power high warning";
               }
               leaf rx-power-low-warn {
                 type string;
                 description
                   "Receiver power low warning";
               }
               leaf tx-loss-of-signal-functionality-alarm {
                 type string;
                 description
                   "Tx loss of signal functionality alarm";
               }
               leaf rx-loss-of-signal-functionality-alarm {
                 type string;
                 description
                   "Rx loss of signal functionality alarm";
               }
               leaf tx-cdr-loss-of-lock-alarm {
                 type string;
                 description
                   "Tx CDR loss of lock alarm";
               }
               leaf tx-loss-of-signal-alarm {
                 type string;
                 description
                   "Transmitter loss of signal alarm";
               }
               leaf rx-loss-of-signal-alarm {
                 type string;
                 description
                   "Receiver loss of signal alarm";
               }
               leaf tx-laser-disabled-alarm {
                 type string;
                 description
                   "Tx laser disabled alarm";
               }
               leaf rx-cdr-loss-of-lock-alarm {
                 type string;
                 description
                   "Receiver CDR loss of lock alarm";
               }
               leaf tec-fault-alarm {
                 type string;
                 description
                   "TEC fault alarm";
               }
               leaf wavelength-unlocked-alarm {
                 type string;
                 description
                   "Wavelength unlocked alarm";
               }
               leaf apd-supply-fault-alarm {
                 type string;
                 description
                   "APD supply fault alarm";
               }
               leaf tx-channel-disabled-alarm {
                 type string;
                 description
                   "Tx channel disabled alarm";
               }
               leaf rx-channel-disabled-alarm {
                 type string;
                 description
                   "Rx channel disabled alarm";
               }
               leaf tx-output-disabled-alarm {
                 type string;
                 description
                   "Rx laser disabled alarm";
               }
               leaf rx-output-disabled-alarm {
                 type string;
                 description
                   "Rx laser disabled alarm";
               }
               leaf tx-squelch-disabled-alarm {
                 type string;
                 description
                   "Tx squelch disabled alarm";
               }
               leaf rx-squelch-disabled-alarm {
                 type string;
                 description
                   "Rx squelch disabled alarm";
               }
               leaf laser-end-of-life-alarm {
                 type string;
                 description
                   "Laser end-of-life alarm";
               }
               leaf lane-cd {
                 type string;
                 description
                   "Lane chromatic dispersion";
               }
               leaf lane-dgd {
                 type string;
                 description
                   "Lane differential group delay";
               }
               leaf lane-cfo {
                 type string;
                 description
                   "Lane carrier frequency offset";
               }
               leaf lane-pdl {
                 type string;
                 description
                   "Lane polarization dependent loss";
               }
               leaf lane-osnr {
                 type string;
                 description
                   "Optical signal-to-noise ratio(dB)";
               }
             }
             leaf optic-diagnostics-not-available {
               type string;
               description
                 "Optical diagnostics not supported by this transceiver";
             }
             leaf laser-bias-current-not-available {
               type string;
               description
                 "Laser bias current measurement not available";
             }
             leaf soa-bias-current-not-available {
               type string;
               description
                 "SOA bias current measurement not available";
             }
             leaf laser-tx-power-not-available {
               type string;
               description
                 "Laser output power measurement not available";
             }
             leaf module-temperature-not-available {
               type string;
               description
                 "Module temperature measurement not available";
             }
             leaf tx-module-temperature-not-available {
               type string;
               description
                 "Tx module temperature measurement not available";
             }
             leaf rx-module-temperature-not-available {
               type string;
               description
                 "Rx module temperature measurement not available";
             }
             leaf laser-rx-power-not-available {
               type string;
               description
                 "Laser receiver optical power measurement not available";
             }
             leaf laser-tx-power-high-alarm-threshold-not-available {
               type string;
               description
                 "Laser output power high alarm threshold not available";
             }
             leaf laser-tx-power-low-alarm-threshold-not-available {
               type string;
               description
                 "Laser output power low alarm threshold not available";
             }
             leaf laser-tx-power-high-warning-threshold-not-available {
               type string;
               description
                 "Laser output power high warning threshold not available";
             }
             leaf laser-tx-power-low-warning-threshold-not-available {
               type string;
               description
                 "Laser output power low warning threshold not available";
             }
             leaf laser-bias-current {
               type string;
               description
                 "Laser bias current (milliamperes)";
             }
             leaf soa-bias-current {
               type string;
               description
                 "SOA bias current (milliamperes)";
             }
             leaf laser-output-power {
               type string;
               description
                 "Laser output power (milliwatts)";
             }
             leaf laser-output-power-dbm {
               type string;
               description
                 "Laser output power (dBm)";
             }
             leaf module-temperature {
               type string;
               description
                 "Module temperature";
             }
             leaf tx-module-temperature {
               type string;
               description
                 "Tx module temperature";
             }
             leaf rx-module-temperature {
               type string;
               description
                 "Rx module temperature";
             }
             leaf module-voltage {
               type string;
               description
                 "Module voltage";
             }
             leaf corrected-error-ratio {
               type string;
               description
                 "Corrected error ratio";
             }
             leaf uncorrected-words-ratio {
               type string;
               description
                 "Uncorrected words ratio";
             }
             leaf tx-module-voltage {
               type string;
               description
                 "Tx module voltage";
             }
             leaf rx-module-voltage {
               type string;
               description
                 "Rx module voltage";
             }
             leaf rx-signal-avg-optical-power {
               type string;
               description
                 "Receiver signal average power (milliwatts)";
             }
             leaf rx-signal-avg-optical-power-dbm {
               type string;
               description
                 "Receiver signal average power (dBm)";
             }
             leaf laser-rx-optical-power {
               type string;
               description
                 "Laser receiver optical power (milliwatts)";
             }
             leaf laser-rx-optical-power-dbm {
               type string;
               description
                 "Laser receiver optical power (dBm)";
             }
             leaf wavelength-channel {
               type string;
               description
                 "Wavelength channel number set";
             }
             leaf wavelength-setpoint {
               type string;
               description
                 "Wavelength point set";
             }
             leaf tx-dither {
               type string;
               description
                 "Tx dither status";
             }
             leaf frequency-error {
               type string;
               description
                 "Frequency error value";
             }
             leaf wavelength-error {
               type string;
               description
                 "Wavelength error value";
             }
             leaf laser-bias-current-high-alarm {
               type string;
               description
                 "Laser bias current high alarm";
             }
             leaf laser-bias-current-low-alarm {
               type string;
               description
                 "Laser bias current low alarm";
             }
             leaf laser-bias-current-high-warn {
               type string;
               description
                 "Laser bias current high warning";
             }
             leaf laser-bias-current-low-warn {
               type string;
               description
                 "Laser bias current low warning";
             }
             leaf soa-bias-current-high-alarm {
               type string;
               description
                 "SOA bias current high alarm";
             }
             leaf soa-bias-current-low-alarm {
               type string;
               description
                 "SOA bias current low alarm";
             }
             leaf soa-bias-current-high-warn {
               type string;
               description
                 "SOA bias current high warning";
             }
             leaf soa-bias-current-low-warn {
               type string;
               description
                 "SOA bias current low warning";
             }
             leaf laser-tx-power-high-alarm {
               type string;
               description
                 "Laser output power high alarm";
             }
             leaf laser-tx-power-low-alarm {
               type string;
               description
                 "Laser output power low alarm";
             }
             leaf laser-tx-power-high-warn {
               type string;
               description
                 "Laser output power high warning";
             }
             leaf laser-tx-power-low-warn {
               type string;
               description
                 "Laser output power low warning";
             }
             leaf tx-power-high-alarm {
               type string;
               description
                 "Tx power high alarm";
             }
             leaf tx-power-low-alarm {
               type string;
               description
                 "Tx power low alarm";
             }
             leaf tx-power-high-warn {
               type string;
               description
                 "Tx power high warning";
             }
             leaf tx-power-low-warn {
               type string;
               description
                 "Tx power low warning";
             }
             leaf module-temperature-high-alarm {
               type string;
               description
                 "Module temperature high alarm";
             }
             leaf module-temperature-low-alarm {
               type string;
               description
                 "Module temperature low alarm";
             }
             leaf module-temperature-high-warn {
               type string;
               description
                 "Module temperature high warning";
             }
             leaf module-temperature-low-warn {
               type string;
               description
                 "Module temperature low warning";
             }
             leaf tx-module-temperature-high-alarm {
               type string;
               description
                 "Tx module temperature high alarm";
             }
             leaf tx-module-temperature-low-alarm {
               type string;
               description
                 "Tx module temperature low alarm";
             }
             leaf rx-module-temperature-high-alarm {
               type string;
               description
                 "Rx module temperature high alarm";
             }
             leaf rx-module-temperature-low-alarm {
               type string;
               description
                 "Rx module temperature low alarm";
             }
             leaf module-voltage-high-alarm {
               type string;
               description
                 "Module voltage high alarm";
             }
             leaf module-voltage-low-alarm {
               type string;
               description
                 "Module voltage low alarm";
             }
             leaf module-voltage-high-warn {
               type string;
               description
                 "Module voltage high warning";
             }
             leaf module-voltage-low-warn {
               type string;
               description
                 "Module voltage low warning";
             }
             leaf tx-module-voltage-high-alarm {
               type string;
               description
                 "Tx module voltage high alarm";
             }
             leaf tx-module-voltage-low-alarm {
               type string;
               description
                 "Tx module voltage low alarm";
             }
             leaf rx-module-voltage-high-alarm {
               type string;
               description
                 "Rx module voltage high alarm";
             }
             leaf rx-module-voltage-low-alarm {
               type string;
               description
                 "Rx module voltage low alarm";
             }
             leaf laser-rx-power-high-alarm {
               type string;
               description
                 "Laser receiver power high alarm";
             }
             leaf laser-rx-power-low-alarm {
               type string;
               description
                 "Laser receiver power low alarm";
             }
             leaf laser-rx-power-high-warn {
               type string;
               description
                 "Laser receiver power high warning";
             }
             leaf laser-rx-power-low-warn {
               type string;
               description
                 "Laser receiver power low warning";
             }
             leaf rx-power-high-alarm {
               type string;
               description
                 "Receiver power high alarm";
             }
             leaf rx-power-low-alarm {
               type string;
               description
                 "Receiver power low alarm";
             }
             leaf rx-power-high-warn {
               type string;
               description
                 "Receiver power high warning";
             }
             leaf rx-power-low-warn {
               type string;
               description
                 "Receiver power low warning";
             }
             leaf laser-end-of-life-alarm {
               type string;
               description
                 "Laser end-of-life alarm";
             }
             leaf laser-wavelength-alarm {
               type string;
               description
                 "Laser wavelength alarm";
             }
             leaf laser-bias-current-alarm {
               type string;
               description
                 "Laser bias current alarm";
             }
             leaf module-temperature-alarm {
               type string;
               description
                 "Module temperature alarm";
             }
             leaf laser-power-alarm {
               type string;
               description
                 "Laser power alarm";
             }
             leaf modulator-temperature-alarm {
               type string;
               description
                 "Modulator temperature alarm";
             }
             leaf modulator-bias-alarm {
               type string;
               description
                 "Modulator bias alarm";
             }
             leaf module-not-ready-alarm {
               type string;
               description
                 "Module not ready alarm";
             }
             leaf module-power-down-alarm {
               type string;
               description
                 "Module power down alarm";
             }
             leaf module-not-init-done-alarm {
               type string;
               description
                 "Module initialization not done alarm";
             }
             leaf module-not-high-power-on-alarm {
               type string;
               description
                 "Module not high powered on alarm";
             }
             leaf module-fault-alarm {
               type string;
               description
                 "Module in fault state alarm";
             }
             leaf pld-flash-init-fault-alarm {
               type string;
               description
                 "PLD or Flash initialization fault alarm";
             }
             leaf power-supply-fault-alarm {
               type string;
               description
                 "Power supply fault alarm";
             }
             leaf checksum-fault-alarm {
               type string;
               description
                 "Checksum fault alarm";
             }
             leaf apd-supply-fault-alarm {
               type string;
               description
                 "APD supply fault alarm";
             }
             leaf tec-fault-alarm {
               type string;
               description
                 "TEC fault alarm";
             }
             leaf wavelength-unlocked-alarm {
               type string;
               description
                 "Wavelength unlocked alarm";
             }
             leaf tx-tune-alarm {
               type string;
               description
                 "Tx tune alarm";
             }
             leaf tx-mux-fifo-error-alarm {
               type string;
               description
                 "Tx multiplexer fifo error alarm";
             }
             leaf tx-loss-of-pll-alarm {
               type string;
               description
                 "Tx loss of PLL alarm";
             }
             leaf tx-data-not-ready-alarm {
               type string;
               description
                 "Tx data not ready alarm";
             }
             leaf tx-not-ready-alarm {
               type string;
               description
                 "Tx not ready alarm";
             }
             leaf tx-laser-fault-alarm {
               type string;
               description
                 "Tx laser fault alarm";
             }
             leaf tx-laser-disabled-alarm {
               type string;
               description
                 "Tx laser disabled alarm";
             }
             leaf tx-loss-of-signal-functionality-alarm {
               type string;
               description
                 "Tx loss of signal functionality alarm";
             }
             leaf tx-cdr-loss-of-lock-alarm {
               type string;
               description
                 "Tx CDR loss of lock alarm";
             }
             leaf rx-loss-avg-opt-power-alarm {
               type string;
               description
                 "Receiver loss of average optical power alarm";
             }
             leaf rx-loss-ac-power-alarm {
               type string;
               description
                 "Receiver loss of AC power alarm";
             }
             leaf rx-loss-of-pll-alarm {
               type string;
               description
                 "Receiver loss of PLL alarm";
             }
             leaf rx-not-ready-alarm {
               type string;
               description
                 "Receiver not ready alarm";
             }
             leaf rx-loss-of-signal-alarm {
               type string;
               description
                 "Receiver loss of signal alarm";
             }
             leaf rx-cdr-loss-of-lock-alarm {
               type string;
               description
                 "Receiver CDR loss of lock alarm";
             }
             leaf laser-bias-current-high-alarm-threshold {
               type string;
               description
                 "Laser bias current high alarm threshold (milliamperes)";
             }
             leaf laser-bias-current-low-alarm-threshold {
               type string;
               description
                 "Laser bias current low alarm threshold (milliamperes)";
             }
             leaf laser-bias-current-high-warn-threshold {
               type string;
               description
                 "Laser bias current high warning threshold (milliamperes)";
             }
             leaf laser-bias-current-low-warn-threshold {
               type string;
               description
                 "Laser bias current low warning threshold (milliamperes)";
             }
             leaf soa-bias-current-high-alarm-threshold {
               type string;
               description
                 "SOA bias current high alarm threshold (milliamperes)";
             }
             leaf soa-bias-current-low-alarm-threshold {
               type string;
               description
                 "SOA bias current low alarm threshold (milliamperes)";
             }
             leaf soa-bias-current-high-warn-threshold {
               type string;
               description
                 "SOA bias current high warning threshold (milliamperes)";
             }
             leaf soa-bias-current-low-warn-threshold {
               type string;
               description
                 "SOA bias current low warning threshold (milliamperes)";
             }
             leaf laser-tx-power-high-alarm-threshold {
               type string;
               description
                 "Laser transmitter power high alarm threshold (milliwatts)";
             }
             leaf laser-tx-power-high-alarm-threshold-dbm {
               type string;
               description
                 "Laser transmitter power high alarm threshold (dBm)";
             }
             leaf laser-tx-power-low-alarm-threshold {
               type string;
               description
                 "Laser transmitter power low alarm threshold (milliwatts)";
             }
             leaf laser-tx-power-low-alarm-threshold-dbm {
               type string;
               description
                 "Laser transmitter power low alarm threshold (dBm)";
             }
             leaf laser-tx-power-high-warn-threshold {
               type string;
               description
                 "Laser transmitter power high warning threshold 
                 (milliwatts)";
             }
             leaf laser-tx-power-high-warn-threshold-dbm {
               type string;
               description
                 "Laser transmitter power high warning threshold (dBm)";
             }
             leaf laser-tx-power-low-warn-threshold {
               type string;
               description
                 "Laser transmitter power low warning threshold (milliwatts)";
             }
             leaf laser-tx-power-low-warn-threshold-dbm {
               type string;
               description
                 "Laser transmitter power low warning threshold (dBm)";
             }
             leaf module-temperature-high-alarm-threshold {
               type string;
               description
                 "Module temperature high alarm threshold";
             }
             leaf module-temperature-low-alarm-threshold {
               type string;
               description
                 "Module temperature low alarm threshold";
             }
             leaf module-temperature-high-warn-threshold {
               type string;
               description
                 "Module temperature high warning threshold";
             }
             leaf module-temperature-low-warn-threshold {
               type string;
               description
                 "Module temperature low warning threshold";
             }
             leaf laser-temperature-high-alarm-threshold {
               type string;
               description
                 "Laser temperature high alarm threshold";
             }
             leaf laser-temperature-low-alarm-threshold {
               type string;
               description
                 "Laser temperature low alarm threshold";
             }
             leaf laser-temperature-high-warn-threshold {
               type string;
               description
                 "Laser temperature high warning threshold";
             }
             leaf laser-temperature-low-warn-threshold {
               type string;
               description
                 "Laser temperature low warning threshold";
             }
             leaf module-voltage-high-alarm-threshold {
               type string;
               description
                 "Module voltage high alarm threshold (volts)";
             }
             leaf module-voltage-low-alarm-threshold {
               type string;
               description
                 "Module voltage low alarm threshold (volts)";
             }
             leaf module-voltage-high-warn-threshold {
               type string;
               description
                 "Module voltage high warning threshold (volts)";
             }
             leaf module-voltage-low-warn-threshold {
               type string;
               description
                 "Module voltage low warning threshold (volts)";
             }
             leaf laser-rx-power-high-alarm-threshold {
               type string;
               description
                 "Laser receiver power high alarm (milliwatts)";
             }
             leaf laser-rx-power-high-alarm-threshold-dbm {
               type string;
               description
                 "Laser receiver power high alarm (dBm)";
             }
             leaf laser-rx-power-low-alarm-threshold {
               type string;
               description
                 "Laser receiver power low alarm (milliwatts)";
             }
             leaf laser-rx-power-low-alarm-threshold-dbm {
               type string;
               description
                 "Laser receiver power low alarm (dBm)";
             }
             leaf laser-rx-power-high-warn-threshold {
               type string;
               description
                 "Laser receiver power high warning (milliwatts)";
             }
             leaf laser-rx-power-high-warn-threshold-dbm {
               type string;
               description
                 "Laser receiver power high warning (dBm)";
             }
             leaf laser-rx-power-low-warn-threshold {
               type string;
               description
                 "Laser receiver power low warning (milliwatts)";
             }
             leaf laser-rx-power-low-warn-threshold-dbm {
               type string;
               description
                 "Laser receiver power low warning (dBm)";
             }
             leaf rx-power-high-alarm-threshold {
               type string;
               description
                 "Receiver power high alarm (milliwatts)";
             }
             leaf rx-power-high-alarm-threshold-dbm {
               type string;
               description
                 "Receiver power high alarm (dBm)";
             }
             leaf rx-power-low-alarm-threshold {
               type string;
               description
                 "Receiver power low alarm (milliwatts)";
             }
             leaf rx-power-low-alarm-threshold-dbm {
               type string;
               description
                 "Receiver power low alarm (dBm)";
             }
             leaf rx-power-high-warning-threshold {
               type string;
               description
                 "Receiver power high warning (milliwatts)";
             }
             leaf rx-power-high-warning-threshold-dbm {
               type string;
               description
                 "Receiver power high warning (dBm)";
             }
             leaf rx-power-low-warning-threshold {
               type string;
               description
                 "Receiver power low warning (milliwatts)";
             }
             leaf rx-power-low-warning-threshold-dbm {
               type string;
               description
                 "Receiver power low warning (dBm)";
             }
             leaf los-alarm-threshold {
               type string;
               description
                 "LOS alarm threshold (milliwatts)";
             }
             leaf los-alarm-threshold-dbm {
               type string;
               description
                 "LOS alarm threshold (dBm)";
             }
             leaf los-warning-threshold {
               type string;
               description
                 "LOS warning threshold (milliwatts)";
             }
             leaf los-warning-threshold-dbm {
               type string;
               description
                 "LOS warning threshold (dBm)";
             }
             leaf dsp-module-state {
               type string;
               description
                 "DSP module state";
             }
           }
           container optics-diagnostics-vendor-extension {
             description
               "Optics diagnostics vendor extension";
             leaf optics-vendor-part-number {
               type string;
               description
                 "Optics component vendor part number";
             }
             leaf optics-vendor-material-number {
               type string;
               description
                 "Optic component vendor material number";
             }
           }
           list optics-chromatics {
             key "optics-chromatic-diagnostics-support";
             leaf optics-chromatic-diagnostics-support {
               type string;
               description
                 "Optics chromatic not supported for interface";
             }
             leaf opticstype {
               type string;
               description
                 "Type of optical module";
             }
             list optics-chromatic {
               key "supported-cd supported-mediaid";
               leaf supported-speed {
                 type string;
                 description
                   "Supported Speed";
               }
               leaf supported-cd {
                 type string;
                 description
                   "Supported Chromatic Dispersion";
               }
               leaf supported-distance {
                 type string;
                 description
                   "Supported Distance";
               }
               leaf supported-mediaid {
                 type string;
                 description
                   "Supported Mediaid";
               }
             }
           }
         }
       }
       container macsec-statistics {
         description
           "MACSec Statistics ";
         leaf macsec-tx-sc-protected {
           type int32;
           description
             "Protected Secure Channel MACSec packets transmitted";
         }
         leaf macsec-tx-sc-encrypted {
           type int32;
           description
             "Encrypted Secure Channel MACSec packets transmitted";
         }
         leaf macsec-tx-sc-protectedbytes {
           type int32;
           description
             "Protected Secure Channel MACSec bytes transmitted";
         }
         leaf macsec-tx-sc-encryptedbytes {
           type int32;
           description
             "Encrypted Secure Channel MACSec bytes transmitted";
         }
         leaf macsec-rx-sc-ok {
           type int32;
           description
             "OK Secure Association MACSec packets received";
         }
         leaf macsec-rx-sc-validatedbytes {
           type int32;
           description
             "Validated Secure Association MACSec bytes received";
         }
         leaf macsec-rx-sc-decryptedbytes {
           type int32;
           description
             "Validated Secure Association MACSec bytes received";
         }
       }
       container peer-configuration-status {
         description
           "Nonmatching DCE end DLCIs";
         leaf peer-nonmatching-dlci {
           type int32;
           description
             "DCE end DLCIs that does not match the DTE";
         }
       }
       container lsi-traffic-statistics {
         leaf input-bytes {
           type int32;
         }
         leaf input-bps {
           type int32;
         }
         leaf input-packets {
           type uint64;
         }
         leaf input-pps {
           type int32;
         }
       }
       container stp-traffic-statistics {
         leaf stp-input-bytes-dropped {
           type int32;
           description
             "Drop statistics due to stp state at ingress in bytes";
         }
         leaf stp-output-bytes-dropped {
           type int32;
           description
             "Drop statistics due to stp state at egress in bytes";
         }
         leaf stp-input-packets-dropped {
           type int32;
           description
             "Drop statistics due to stp state at ingress in packets";
         }
         leaf stp-output-packets-dropped {
           type int32;
           description
             "Drop statistics due to stp state at egress in packets";
         }
       }
       container ethernet-rpf-counter-stats {
         leaf ethernet-rpf-ipv4-rpf-bytes {
           type int32;
           description
             "Counter for ipv4 rpf byptes";
         }
         leaf ethernet-rpf-ipv4-rpf-packets {
           type int32;
           description
             "Counter for ipv4 rpf packets";
         }
         leaf ethernet-rpf-ipv6-rpf-bytes {
           type int32;
           description
             "Counter for ipv6 rpf byptes";
         }
         leaf ethernet-rpf-ipv6-rpf-packets {
           type int32;
           description
             "Counter for ipv6 rpf packets";
         }
       }
       container af-fe-info {
       }
       container af-fe-lb-stats-info {
       }
       container af-fe-q-pkts {
       }
       container af-fe-q-bytes {
       }
       container chassis-queue-counters {
         description
           "Chassis queue counter statistics";
         container interface-chassis-cos-summary {
           description
             "Packet Forwarding Engine chassis forwarding class and queue 
             information for an interface";
           leaf intf-cos-chassis-num-queues-supported {
             type int32;
             description
               "Number of Packet Forwarding Engine chassis queues the 
               interface supports";
           }
           leaf intf-cos-chassis-num-queues-in-use {
             type int32;
             description
               "Number of Packet Forwarding Engine chassis queues in use on 
               the interface";
           }
         }
         list queue {
           key "queue-number";
           description
             "Counters for a single queue";
           leaf queue-number {
             type uint32;
             description
               "Queue number";
           }
           leaf forwarding-class-name {
             type string;
             description
               "Forwarding class name associated with queue";
           }
           leaf queue-counters-queued-packets {
             type int32;
             description
               "Queued packet count";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-queued-packets-na {
             type string;
             description
               "Queued packets not available";
           }
           leaf queue-counters-queued-bytes-na {
             type string;
             description
               "Queued bytes not available";
           }
           leaf queue-counters-trans-packets {
             type int32;
             description
               "Total number of transmitted packets";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets-na {
             type string;
             description
               "Number of packets dropped due to tail drop not available";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of packets dropped at tail drop of the queue";
           }
           leaf queue-counters-tail-drop-bytes-rate {
             type int32;
             description
               "Number of packets dropped at tail drop of the queue";
           }
           leaf queue-counters-ecn-ce-packets {
             type int32;
             description
               "Total number of ECN CE packets";
           }
           leaf queue-counters-ecn-ce-packets-rate {
             type int32;
             description
               "Rate at which ECN CE packets are transmitted";
           }
           leaf queue-counters-ecn-ce-bytes {
             type int32;
             description
               "Total number of ECN CE bytes";
           }
           leaf queue-counters-ecn-ce-bytes-rate {
             type int32;
             description
               "Rate at which ECN CE bytes are transmitted";
           }
           leaf queue-counters-rate-limit-drop-packets-na {
             type string;
             description
               "Number of packets dropped due to rate-limit drop not 
               available";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes-na {
             type string;
             description
               "Number of bytes dropped due to tail drop not available";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets-na {
             type string;
             description
               "Number of packets dropped due to RED not available";
           }
           leaf queue-counters-red-packets {
             type int32;
             description
               "Number of packets dropped due to RED";
           }
           leaf queue-counters-red-packets-rate {
             type int32;
             description
               "Rate at which packets are dropped due to RED";
           }
           leaf queue-counters-red-packets-ln {
             type int32;
             description
               "Number of RED dropped low-loss, non-TCP packets";
           }
           leaf queue-counters-red-packets-rate-ln {
             type int32;
             description
               "RED drop rate for low-loss, non-TCP packets";
           }
           leaf queue-counters-red-packets-lt {
             type int32;
             description
               "Number of RED dropped of low-loss, TCP packets";
           }
           leaf queue-counters-red-packets-rate-lt {
             type int32;
             description
               "RED drop rate for low-loss, TCP packets";
           }
           leaf queue-counters-red-packets-hn {
             type int32;
             description
               "Number of RED dropped high-loss, non-TCP packets";
           }
           leaf queue-counters-red-packets-rate-hn {
             type int32;
             description
               "RED drop rate for high-loss, non-TCP packets";
           }
           leaf queue-counters-red-packets-ht {
             type int32;
             description
               "Number of RED dropped high-loss, TCP packets";
           }
           leaf queue-counters-red-packets-rate-ht {
             type int32;
             description
               "RED drop rate for high-loss, TCP packets";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-medium {
             type int32;
             description
               "Number of RED dropped medium-loss packets";
           }
           leaf queue-counters-red-packets-rate-medium {
             type int32;
             description
               "RED drop rate for medium-loss packets";
           }
           leaf queue-counters-red-packets-high {
             type int32;
             description
               "Number of RED dropped high-loss packets";
           }
           leaf queue-counters-red-packets-rate-high {
             type int32;
             description
               "RED drop rate for high-loss packets";
           }
           leaf queue-counters-red-bytes-na {
             type string;
             description
               "Number of bytes dropped due to RED not available";
           }
           leaf queue-counters-red-bytes {
             type int32;
             description
               "Number of bytes dropped due to RED";
           }
           leaf queue-counters-red-bytes-rate {
             type int32;
             description
               "Rate at which bytes are dropped due to RED";
           }
           leaf queue-counters-red-bytes-ln {
             type int32;
             description
               "Number of RED dropped low-loss, non-TCP bytes";
           }
           leaf queue-counters-red-bytes-rate-ln {
             type int32;
             description
               "RED drop rate for low-loss, non-TCP bytes";
           }
           leaf queue-counters-red-bytes-lt {
             type int32;
             description
               "Number of RED dropped low-loss, TCP bytes";
           }
           leaf queue-counters-red-bytes-rate-lt {
             type int32;
             description
               "RED drop rate for low-loss, TCP bytes";
           }
           leaf queue-counters-red-bytes-hn {
             type int32;
             description
               "Number of RED dropped high-loss, non-TCP bytes";
           }
           leaf queue-counters-red-bytes-rate-hn {
             type int32;
             description
               "RED drop rate for high-loss, non-TCP bytes";
           }
           leaf queue-counters-red-bytes-ht {
             type int32;
             description
               "Number of RED dropped high-loss, TCP bytes";
           }
           leaf queue-counters-red-bytes-rate-ht {
             type int32;
             description
               "RED drop rate for high-loss, TCP bytes";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-medium {
             type int32;
             description
               "Number of RED dropped medium-loss bytes";
           }
           leaf queue-counters-red-bytes-rate-medium {
             type int32;
             description
               "RED drop rate for medium-loss bytes";
           }
           leaf queue-counters-red-bytes-high {
             type int32;
             description
               "Number of RED dropped high-loss bytes";
           }
           leaf queue-counters-red-bytes-rate-high {
             type int32;
             description
               "RED drop rate for high-loss bytes";
           }
           leaf queue-counters-timestamp {
             type int32;
             description
               "Last packet enqueued timestamp";
           }
           leaf queue-counters-total-drop-packets {
             type int32;
             description
               "Number of total packets dropped at the queue";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
           leaf queue-counters-reserved-buffer-packets {
             type int32;
             description
               "Queues's usage of reserved buffer pool in pkts";
           }
           leaf queue-counters-reserved-buffer-bytes {
             type int32;
             description
               "Queues's usage of reserved buffer pool in bytes";
           }
           leaf queue-counters-shared-buffer-packets {
             type int32;
             description
               "Queues's usage of shared buffer pool in pkts";
           }
           leaf queue-counters-shared-buffer-bytes {
             type int32;
             description
               "Queues's usage of shared buffer pool in bytes";
           }
           leaf queue-counters-depth-average {
             type int32;
             description
               "Time averaged queue depth";
           }
           leaf queue-counters-depth-current {
             type int32;
             description
               "Current instantaneous queue depth";
           }
           leaf queue-counters-depth-peak {
             type int32;
             description
               "Peak queue depth";
           }
           leaf queue-counters-depth-max {
             type int32;
             description
               "Maximum queue depth attained";
           }
           leaf queue-counters-srx-reserved-buffer-bytes {
             type int32;
             description
               "Queues's usage of reserved buffer pool in bytes";
           }
           leaf queue-counters-srx-depth-current {
             type int32;
             description
               "Current instantaneous queue depth";
           }
         }
       }
       container ingress-queue-counters {
         description
           "Ingress queue counter statistics";
         list queue {
           key "queue-number";
           description
             "Counters for a single queue";
           leaf queue-number {
             type uint32;
             description
               "Queue number";
           }
           leaf forwarding-class-name {
             type string;
             description
               "Forwarding class name associated with queue";
           }
           leaf queue-counters-queued-packets {
             type int32;
             description
               "Queued packet count";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-queued-packets-na {
             type string;
             description
               "Queued packets not available";
           }
           leaf queue-counters-queued-bytes-na {
             type string;
             description
               "Queued bytes not available";
           }
           leaf queue-counters-trans-packets {
             type int32;
             description
               "Total number of transmitted packets";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets-na {
             type string;
             description
               "Number of packets dropped due to tail drop not available";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of packets dropped at tail drop of the queue";
           }
           leaf queue-counters-tail-drop-bytes-rate {
             type int32;
             description
               "Number of packets dropped at tail drop of the queue";
           }
           leaf queue-counters-ecn-ce-packets {
             type int32;
             description
               "Total number of ECN CE packets";
           }
           leaf queue-counters-ecn-ce-packets-rate {
             type int32;
             description
               "Rate at which ECN CE packets are transmitted";
           }
           leaf queue-counters-ecn-ce-bytes {
             type int32;
             description
               "Total number of ECN CE bytes";
           }
           leaf queue-counters-ecn-ce-bytes-rate {
             type int32;
             description
               "Rate at which ECN CE bytes are transmitted";
           }
           leaf queue-counters-rate-limit-drop-packets-na {
             type string;
             description
               "Number of packets dropped due to rate-limit drop not 
               available";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes-na {
             type string;
             description
               "Number of bytes dropped due to tail drop not available";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets-na {
             type string;
             description
               "Number of packets dropped due to RED not available";
           }
           leaf queue-counters-red-packets {
             type int32;
             description
               "Number of packets dropped due to RED";
           }
           leaf queue-counters-red-packets-rate {
             type int32;
             description
               "Rate at which packets are dropped due to RED";
           }
           leaf queue-counters-red-packets-ln {
             type int32;
             description
               "Number of RED dropped low-loss, non-TCP packets";
           }
           leaf queue-counters-red-packets-rate-ln {
             type int32;
             description
               "RED drop rate for low-loss, non-TCP packets";
           }
           leaf queue-counters-red-packets-lt {
             type int32;
             description
               "Number of RED dropped of low-loss, TCP packets";
           }
           leaf queue-counters-red-packets-rate-lt {
             type int32;
             description
               "RED drop rate for low-loss, TCP packets";
           }
           leaf queue-counters-red-packets-hn {
             type int32;
             description
               "Number of RED dropped high-loss, non-TCP packets";
           }
           leaf queue-counters-red-packets-rate-hn {
             type int32;
             description
               "RED drop rate for high-loss, non-TCP packets";
           }
           leaf queue-counters-red-packets-ht {
             type int32;
             description
               "Number of RED dropped high-loss, TCP packets";
           }
           leaf queue-counters-red-packets-rate-ht {
             type int32;
             description
               "RED drop rate for high-loss, TCP packets";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-medium {
             type int32;
             description
               "Number of RED dropped medium-loss packets";
           }
           leaf queue-counters-red-packets-rate-medium {
             type int32;
             description
               "RED drop rate for medium-loss packets";
           }
           leaf queue-counters-red-packets-high {
             type int32;
             description
               "Number of RED dropped high-loss packets";
           }
           leaf queue-counters-red-packets-rate-high {
             type int32;
             description
               "RED drop rate for high-loss packets";
           }
           leaf queue-counters-red-bytes-na {
             type string;
             description
               "Number of bytes dropped due to RED not available";
           }
           leaf queue-counters-red-bytes {
             type int32;
             description
               "Number of bytes dropped due to RED";
           }
           leaf queue-counters-red-bytes-rate {
             type int32;
             description
               "Rate at which bytes are dropped due to RED";
           }
           leaf queue-counters-red-bytes-ln {
             type int32;
             description
               "Number of RED dropped low-loss, non-TCP bytes";
           }
           leaf queue-counters-red-bytes-rate-ln {
             type int32;
             description
               "RED drop rate for low-loss, non-TCP bytes";
           }
           leaf queue-counters-red-bytes-lt {
             type int32;
             description
               "Number of RED dropped low-loss, TCP bytes";
           }
           leaf queue-counters-red-bytes-rate-lt {
             type int32;
             description
               "RED drop rate for low-loss, TCP bytes";
           }
           leaf queue-counters-red-bytes-hn {
             type int32;
             description
               "Number of RED dropped high-loss, non-TCP bytes";
           }
           leaf queue-counters-red-bytes-rate-hn {
             type int32;
             description
               "RED drop rate for high-loss, non-TCP bytes";
           }
           leaf queue-counters-red-bytes-ht {
             type int32;
             description
               "Number of RED dropped high-loss, TCP bytes";
           }
           leaf queue-counters-red-bytes-rate-ht {
             type int32;
             description
               "RED drop rate for high-loss, TCP bytes";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-medium {
             type int32;
             description
               "Number of RED dropped medium-loss bytes";
           }
           leaf queue-counters-red-bytes-rate-medium {
             type int32;
             description
               "RED drop rate for medium-loss bytes";
           }
           leaf queue-counters-red-bytes-high {
             type int32;
             description
               "Number of RED dropped high-loss bytes";
           }
           leaf queue-counters-red-bytes-rate-high {
             type int32;
             description
               "RED drop rate for high-loss bytes";
           }
           leaf queue-counters-timestamp {
             type int32;
             description
               "Last packet enqueued timestamp";
           }
           leaf queue-counters-total-drop-packets {
             type int32;
             description
               "Number of total packets dropped at the queue";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
           leaf queue-counters-reserved-buffer-packets {
             type int32;
             description
               "Queues's usage of reserved buffer pool in pkts";
           }
           leaf queue-counters-reserved-buffer-bytes {
             type int32;
             description
               "Queues's usage of reserved buffer pool in bytes";
           }
           leaf queue-counters-shared-buffer-packets {
             type int32;
             description
               "Queues's usage of shared buffer pool in pkts";
           }
           leaf queue-counters-shared-buffer-bytes {
             type int32;
             description
               "Queues's usage of shared buffer pool in bytes";
           }
           leaf queue-counters-depth-average {
             type int32;
             description
               "Time averaged queue depth";
           }
           leaf queue-counters-depth-current {
             type int32;
             description
               "Current instantaneous queue depth";
           }
           leaf queue-counters-depth-peak {
             type int32;
             description
               "Peak queue depth";
           }
           leaf queue-counters-depth-max {
             type int32;
             description
               "Maximum queue depth attained";
           }
           leaf queue-counters-srx-reserved-buffer-bytes {
             type int32;
             description
               "Queues's usage of reserved buffer pool in bytes";
           }
           leaf queue-counters-srx-depth-current {
             type int32;
             description
               "Current instantaneous queue depth";
           }
         }
         container interface-cos-summary {
           description
             "Summary of forwarding class and queue information on an 
             interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
           leaf intf-cos-burst-size-for-ifl {
             type int32;
             description
               "Burst size for the logical interface";
           }
         }
         container interface-cos-short-summary {
           description
             "Summary of queue information on an interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
         }
         list queue-num-forwarding-class-name-map {
           key "queue-number";
           leaf queue-number {
             type uint32;
             description
               "Queue number";
           }
           leaf forwarding-class-name {
             type string;
             description
               "Forwarding class name associated with queue";
           }
         }
       }
       container otn-oc-information {
         list media-alarm {
           leaf media-alarm-name {
             type string;
           }
           leaf media-alarm-seconds {
             type int32;
           }
           leaf media-alarm-count {
             type int32;
           }
           leaf media-alarm-state {
             type string;
           }
         }
       }
       container otn-otu-information {
         list media-alarm {
           leaf media-alarm-name {
             type string;
           }
           leaf media-alarm-seconds {
             type int32;
           }
           leaf media-alarm-count {
             type int32;
           }
           leaf media-alarm-state {
             type string;
           }
         }
       }
       container otn-odu-information {
         list media-alarm {
           leaf media-alarm-name {
             type string;
           }
           leaf media-alarm-seconds {
             type int32;
           }
           leaf media-alarm-count {
             type int32;
           }
           leaf media-alarm-state {
             type string;
           }
         }
       }
       container otn-ot-module-information {
         list media-alarm {
           leaf media-alarm-name {
             type string;
           }
           leaf media-alarm-seconds {
             type int32;
           }
           leaf media-alarm-count {
             type int32;
           }
           leaf media-alarm-state {
             type string;
           }
         }
       }
       list otn-odu-tcm-information {
         list media-alarm {
           leaf media-alarm-name {
             type string;
           }
           leaf media-alarm-seconds {
             type int32;
           }
           leaf media-alarm-count {
             type int32;
           }
           leaf media-alarm-state {
             type string;
           }
         }
       }
       container ima-group-information {
         description
           "IMA group alarms";
       }
       container ima-link-information {
         description
           "IMA link alarms";
       }
       list smart-sfp-channel-statistics {
         key "iwf-channel-num";
         description
           "Smart SFP channel IWF statistics";
         leaf iwf-channel-num {
           type uint32;
           description
             "Channel number for IWF stats";
         }
         leaf channel-not-applicable {
           type string;
           description
             "Channelization are not supported";
         }
         container smart-sfp-av-titan-iwf-statistics {
           leaf rx-packets {
             type uint32;
           }
           leaf tx-packets {
             type uint32;
           }
           leaf malformed-packets {
             type uint32;
           }
           leaf reordered-packets {
             type uint32;
           }
           leaf misordered-dropped-packets {
             type uint32;
           }
           leaf missing-packets {
             type uint32;
           }
           leaf played-out-packets {
             type uint32;
           }
           leaf jb-overrun {
             type uint32;
           }
           leaf jb-underrun {
             type uint32;
           }
         }
       }
       list smart-sfp-channel-defects {
         key "defect-channel-num";
         description
           "Smart SFP channel Defects";
         leaf defect-channel-num {
           type uint32;
           description
             "Channel number ";
         }
         leaf sfp-channel-defects {
           type string;
         }
         leaf channel-not-applicable {
           type string;
           description
             "Channelization are not supported";
         }
       }
       container ethernet-mac-pfc-statistics {
         description
           "Ethernet MAC Priority Flow control Statistics";
         leaf mac-pfc-dot1p {
           type int32;
         }
         leaf input-mac-pfc-frames {
           type int32;
         }
         leaf output-mac-pfc-frames {
           type int32;
         }
       }
       container ethernet-pfcwd-statistics {
         description
           "Ethernet MAC Priority Flow control Watchdog Statistics";
         leaf queue-number {
           type uint32;
           description
             "Queue number";
         }
         leaf detected {
           type int32;
         }
         leaf recovered {
           type int32;
         }
         leaf last-count {
           type int32;
         }
         leaf total-count {
           type int32;
         }
       }
       container cos-information {
         description
           "Information about class-of-service configuration";
         list cos-stream-information {
           description
             "Information about the traffic stream";
         }
         container cos-forwarding-class-information {
           container fc-map {
             description
               "Class-of-service forwarding class to queue mapping";
             list fc-map-item {
               leaf fc-name {
                 type string;
                 description
                   "Class-of-service forwarding class name";
               }
               leaf fc-number {
                 type uint32;
                 description
                   "Identifier for Class-of-service forwarding class";
               }
               leaf fc-queue-number {
                 type uint32;
                 description
                   "Class-of-service forwarding class queue number";
               }
               leaf fc-rqueue-number {
                 type uint32;
                 description
                   "Class-of-service forwarding class restricted queue 
                   number";
               }
               leaf fc-priority {
                 type string;
                 description
                   "Class-of-service forwarding class queue priority";
               }
               leaf fc-policing-priority {
                 type string;
                 description
                   "Class-of-service forwarding class policing priority";
               }
               leaf fc-spu-priority {
                 type string;
                 description
                   "Class-of-service forwarding class spu priority";
               }
               leaf fc-no-loss {
                 type string;
                 description
                   "Class-of-service forwarding class no-loss";
               }
               leaf fc-pfc-priority {
                 type string;
                 description
                   "Class-of-service forwarding class pfc-priority";
               }
               leaf fc-multicast {
                 type string;
                 description
                   "Class-of-service forwarding class multicast";
               }
               leaf fc-latency-ecn {
                 type string;
                 description
                   "Class-of-service forwarding class latency ECN";
               }
             }
           }
         }
         container cos-forwarding-class-map-information {
           container fc-map {
             description
               "Class-of-service forwarding class to queue mapping";
             list fc-map-item {
               leaf fc-name {
                 type string;
                 description
                   "Class-of-service forwarding class name";
               }
               leaf fc-number {
                 type uint32;
                 description
                   "Identifier for Class-of-service forwarding class";
               }
               leaf fc-queue-number {
                 type uint32;
                 description
                   "Class-of-service forwarding class queue number";
               }
               leaf fc-rqueue-number {
                 type uint32;
                 description
                   "Class-of-service forwarding class restricted queue 
                   number";
               }
               leaf fc-priority {
                 type string;
                 description
                   "Class-of-service forwarding class queue priority";
               }
               leaf fc-policing-priority {
                 type string;
                 description
                   "Class-of-service forwarding class policing priority";
               }
               leaf fc-spu-priority {
                 type string;
                 description
                   "Class-of-service forwarding class spu priority";
               }
               leaf fc-no-loss {
                 type string;
                 description
                   "Class-of-service forwarding class no-loss";
               }
               leaf fc-pfc-priority {
                 type string;
                 description
                   "Class-of-service forwarding class pfc-priority";
               }
               leaf fc-multicast {
                 type string;
                 description
                   "Class-of-service forwarding class multicast";
               }
               leaf fc-latency-ecn {
                 type string;
                 description
                   "Class-of-service forwarding class latency ECN";
               }
             }
           }
         }
         container cos-classifier-information {
           list classifier {
             description
               "Class-of-service code point classifier";
             leaf classifier-name {
               type string;
               description
                 "Class-of-service classifier name";
             }
             leaf code-point-type {
               type string;
               description
                 "Class-of-service code point type";
             }
             leaf table-index {
               type uint32;
               description
                 "Table index";
             }
             container classifier-map {
               list classifier-map-item {
                 leaf code-point {
                   type string;
                   description
                     "Class-of-service code point alias name or bits";
                 }
                 leaf fc-name {
                   type string;
                   description
                     "Class-of-service forwarding class name";
                 }
                 leaf loss-priority {
                   type string;
                   description
                     "Class-of-service loss priority";
                 }
                 leaf cntag-present {
                   type string;
                   description
                     "Class-of-service cntag present";
                 }
               }
             }
           }
         }
         container cos-loss-priority-map-information {
           list loss-priority-map {
             description
               "Class-of-service code point loss priority map";
             leaf loss-priority-map-name {
               type string;
               description
                 "Name of class-of-service loss priority map";
             }
             leaf code-point-type {
               type string;
               description
                 "Class-of-service code point type";
             }
             leaf table-index {
               type uint32;
               description
                 "Table index";
             }
             list loss-priority-map-table {
               list loss-priority-map-item {
                 leaf code-point {
                   type string;
                   description
                     "Class-of-service code point alias name or bits";
                 }
                 leaf loss-priority {
                   type string;
                   description
                     "Class-of-service loss priority";
                 }
               }
               list loss-priority-map-table-entry {
                 leaf table-index {
                   type uint32;
                   description
                     "Table index";
                 }
                 leaf code-point {
                   type string;
                   description
                     "Class-of-service code point alias name or bits";
                 }
                 leaf loss-priority {
                   type string;
                   description
                     "Class-of-service loss priority";
                 }
               }
             }
           }
         }
         container cos-drop-profile-information {
           list drop-profile {
             description
               "Class-of-service drop profile";
             leaf profile-name {
               type string;
               description
                 "Class-of-service drop profile name";
             }
             leaf profile-type {
               type string;
               description
                 "Class-of-service drop profile type";
             }
             leaf table-index {
               type uint32;
               description
                 "Table index";
             }
             container profile-map {
               list profile-map-item {
                 leaf fill-level {
                   type uint32;
                   description
                     "Class-of-service drop profile fill level value";
                 }
                 leaf probability {
                   type uint32;
                   description
                     "Class-of-service drop profile probability value";
                 }
               }
             }
           }
         }
         container cos-mpls-ecn-map-information {
           list cos-mpls-ecn-map-info {
             description
               "Class-of-service mpls-ecn-map information";
             leaf ecn-capable-exp {
               type int32;
               description
                 "ECN capable exp";
             }
             leaf congestion-experienced-exp {
               type int32;
               description
                 "Congestion Expereienced exp";
             }
           }
         }
         container cos-monitoring-profile-information {
           list monitoring-profile {
             description
               "Class-of-service monitoring profile";
             leaf monitoring-profile-name {
               type string;
               description
                 "Class-of-service monitoring profile name";
             }
             container export-filters {
               container export-filter {
                 leaf filter-name {
                   type string;
                   description
                     "Class-of-service monitoring profile filter name";
                 }
                 leaf monitoring-queue-number {
                   type uint32;
                   description
                     "Class-of-service monitoring profile filter queue value";
                 }
                 leaf peak-queue-length-value {
                   type uint32;
                   description
                     "Class-of-service monitoring profile peak queue length 
                     value";
                 }
               }
             }
           }
         }
         container cos-rewrite-information {
           list rewrite {
             description
               "Class-of-service drop profile";
             leaf rewrite-name {
               type string;
               description
                 "Class-of-service rewrite rule name";
             }
             leaf code-point-type {
               type string;
               description
                 "Class-of-service code point type";
             }
             leaf table-index {
               type uint32;
               description
                 "Table index";
             }
             container rewrite-map {
               list rewrite-map-item {
                 leaf fc-name {
                   type string;
                   description
                     "Class-of-service forwarding class name";
                 }
                 leaf loss-priority {
                   type string;
                   description
                     "Class-of-service loss priority";
                 }
                 leaf code-point {
                   type string;
                   description
                     "Class-of-service code point alias name or bits";
                 }
               }
             }
           }
         }
         container cos-loss-priority-rewrite-information {
           list loss-priority-rewrite {
             description
               "Class-of-service loss priority to code point rewrite";
             leaf loss-priority-rewrite-name {
               type string;
               description
                 "Name of class-of-service loss priority rewrite";
             }
             leaf code-point-type {
               type string;
               description
                 "Class-of-service code point type";
             }
             leaf table-index {
               type uint32;
               description
                 "Table index";
             }
             list loss-priority-rewrite-table {
               list loss-priority-rewrite-item {
                 leaf loss-priority {
                   type string;
                   description
                     "Class-of-service loss priority";
                 }
                 leaf code-point {
                   type string;
                   description
                     "Class-of-service code point alias name or bits";
                 }
               }
               list loss-priority-rewrite-table-entry {
                 leaf table-index {
                   type uint32;
                   description
                     "Table index";
                 }
                 leaf loss-priority {
                   type string;
                   description
                     "Class-of-service loss priority";
                 }
                 leaf code-point {
                   type string;
                   description
                     "Class-of-service code point alias name or bits";
                 }
               }
             }
           }
         }
         container cos-code-point-map-information {
           list code-point-map {
             description
               "Class-of-service code point alias map";
             leaf code-point-type {
               type string;
               description
                 "Class-of-service code point type";
             }
             container alias-map {
               list alias-map-item {
                 leaf code-point-alias {
                   type string;
                   description
                     "Class-of-service code point alias name";
                 }
                 leaf code-point-bits {
                   type string;
                   description
                     "Class-of-service code point bit sequence";
                 }
               }
             }
           }
         }
         container cos-fragmentation-map-information {
           list fragmentation-map {
             description
               "Class-of-service fragmentation map";
             leaf fragmentation-map-name {
               type string;
               description
                 "Class-of-service fragmentation map name";
             }
             leaf fragmentation-map-index {
               type uint32;
               description
                 "Index number for Class-of-service fragmentation map";
             }
             list fragment-map {
               leaf fc-name {
                 type string;
                 description
                   "Class-of-service forwarding class name";
               }
               leaf no-fragmentation {
                 type empty;
                 description
                   "Do not fragment packets of this class";
               }
               leaf fragment-threshold {
                 type string;
                 description
                   "Fragmentation threshold";
               }
               leaf fragment-multilink-class {
                 type int32;
                 description
                   "Identifier for multilink class";
               }
             }
           }
         }
         container cos-translation-table-map-information {
           list translation-table {
             description
               "Class-of-service code point translation table";
             leaf translation-table-name {
               type string;
               description
                 "Class-of-service translation table name";
             }
             leaf translation-table-type {
               type string;
               description
                 "Class-of-service translation table type";
             }
             leaf table-index {
               type uint32;
               description
                 "Table index";
             }
             container translation-table-map {
               container translation-table-map-item {
                 leaf from-code-point {
                   type string;
                   description
                     "Class-of-service code point alias name or bits";
                 }
                 leaf to-code-point {
                   type string;
                   description
                     "Class-of-service code point alias name or bits";
                 }
               }
             }
             list translation-table-entry {
               leaf table-index {
                 type uint32;
                 description
                   "Table index";
               }
               leaf from-code-point {
                 type string;
                 description
                   "Class-of-service code point alias name or bits";
               }
               leaf to-code-point {
                 type string;
                 description
                   "Class-of-service code point alias name or bits";
               }
             }
           }
         }
         container cos-multi-destination-information {
           container sm-md-map {
             leaf scheduler-map-name {
               type string;
               description
                 "Class-of-service scheduler map name";
             }
             leaf scheduler-map-index {
               type uint64;
               description
                 "Class-of-service scheduler map index";
             }
           }
           container fc-md-map {
             leaf fc-name {
               type string;
               description
                 "Class-of-service forwarding class name";
             }
             leaf fc-queue-number {
               type uint32;
               description
                 "Class-of-service forwarding class queue number";
             }
           }
           container cls-md-map {
             leaf multidest-classifier-name {
               type string;
               description
                 "Multi destination classifier name";
             }
             leaf multidest-classifier-type {
               type string;
               description
                 "Multi destination classifier type";
             }
             leaf multidest-classifier-index {
               type uint32;
               description
                 "Multi destination classifier id";
             }
           }
         }
         container cos-forwarding-class-set-information {
           list forwarding-class-set {
             description
               "Class-of-service forwarding class set information";
             list forwarding-class-set-entry {
               leaf forwarding-class-set-name {
                 type string;
                 description
                   "Class-of-service forwarding class set name";
               }
               leaf forwarding-class-set-type {
                 type string;
                 description
                   "Identifier for Class-of-service forwarding class set 
                   type";
               }
               leaf forwarding-class-set-index {
                 type uint32;
                 description
                   "Identifier for Class-of-service forwarding class set";
               }
               container fc-map {
                 description
                   "Class-of-service forwarding class to queue mapping";
                 list fc-map-item {
                   leaf fc-name {
                     type string;
                     description
                       "Class-of-service forwarding class name";
                   }
                   leaf fc-number {
                     type uint32;
                     description
                       "Identifier for Class-of-service forwarding class";
                   }
                   leaf fc-queue-number {
                     type uint32;
                     description
                       "Class-of-service forwarding class queue number";
                   }
                   leaf fc-rqueue-number {
                     type uint32;
                     description
                       "Class-of-service forwarding class restricted queue 
                       number";
                   }
                   leaf fc-priority {
                     type string;
                     description
                       "Class-of-service forwarding class queue priority";
                   }
                   leaf fc-policing-priority {
                     type string;
                     description
                       "Class-of-service forwarding class policing priority";
                   }
                   leaf fc-spu-priority {
                     type string;
                     description
                       "Class-of-service forwarding class spu priority";
                   }
                   leaf fc-no-loss {
                     type string;
                     description
                       "Class-of-service forwarding class no-loss";
                   }
                   leaf fc-pfc-priority {
                     type string;
                     description
                       "Class-of-service forwarding class pfc-priority";
                   }
                   leaf fc-multicast {
                     type string;
                     description
                       "Class-of-service forwarding class multicast";
                   }
                   leaf fc-latency-ecn {
                     type string;
                     description
                       "Class-of-service forwarding class latency ECN";
                   }
                 }
               }
             }
           }
         }
         container cos-policy-map-information {
           list policy-map {
             description
               "Class-of-service Policy-map";
             leaf policy-map-name {
               type string;
               description
                 "Class-of-service Policy-map name";
             }
             leaf table-index {
               type uint32;
               description
                 "Table index";
             }
             leaf policy-map-user-attribute {
               type uint32;
               description
                 "User-defined attribute";
             }
             container policy-map-cp-entries {
               leaf code-point-type {
                 type string;
                 description
                   "Class-of-service code point type";
               }
               leaf code-point {
                 type string;
                 description
                   "Class-of-service code point alias name or bits";
               }
               leaf code-point-option {
                 type string;
                 description
                   "Class-of-service code point option flag";
               }
             }
           }
         }
         container cos-client-info {
           list cos-client {
             description
               "Class-of-service Junos client information";
             leaf cos-client-info-internal-id {
               type uint32;
               description
                 "Junos client internal identifier";
             }
             leaf cos-client-info-requests {
               type uint32;
               description
                 "Number of requests from Junos client";
             }
             leaf cos-client-info-responses {
               type uint32;
               description
                 "Number of responses to Junos client";
             }
             leaf cos-client-info-failures {
               type uint32;
               description
                 "Number of failures while handling Junos client requests";
             }
             leaf cos-client-info-identifier {
               type string;
               description
                 "Junos client identifier";
             }
             leaf cos-client-name {
               type string;
               description
                 "Junos client name";
             }
             leaf cos-client-state {
               type string;
               description
                 "Junos client state information";
             }
             leaf cos-client-internal-name {
               type string;
               description
                 "Junos client internal name";
             }
             leaf cos-client-stats {
               type string;
               description
                 "Junos client statistics";
             }
             leaf cos-client-failure-stats {
               type string;
               description
                 "Junos client failure/error statistics";
             }
             leaf cos-client-validate-failures {
               type uint32;
               description
                 "Junos client request validation failures";
             }
             leaf cos-client-ownership-failures {
               type uint32;
               description
                 "Junos client ownership validation failures";
             }
             leaf cos-client-info-name {
               type string;
               description
                 "CoS client name";
             }
             leaf cos-client-internal-id {
               type uint32;
               description
                 "Junos client internal identifier";
             }
             leaf cos-client-requests {
               type uint64;
               description
                 "Number of requests from Junos client";
             }
             leaf cos-client-responses {
               type uint64;
               description
                 "Number of responses to Junos client";
             }
             leaf cos-client-failures {
               type uint64;
               description
                 "Number of failures while handling Junos client requests";
             }
             leaf cos-client-identifier {
               type string;
               description
                 "Junos client identifier";
             }
             leaf cos-client-status {
               type string;
               description
                 "Junos client status";
             }
             leaf cos-client-connected-time {
               type string;
               description
                 "Junos client time of connect";
             }
             leaf cos-client-reconnected-time {
               type string;
               description
                 "Junos client time of reconnect";
             }
             leaf cos-client-disconnected-time {
               type string;
               description
                 "Junos client time of disconnect";
             }
             leaf cos-client-message-type {
               type string;
               description
                 "Junos client message type";
             }
             leaf cos-client-operation-type {
               type string;
               description
                 "Junos client operation type";
             }
             leaf-list cos-bind-point-type {
               type string;
               description
                 "Class-of-service bind point type";
             }
             leaf-list cos-bind-point-owner-type {
               type string;
               description
                 "Class-of-service bind point owner type";
             }
             leaf-list cos-bind-point-owner-internal-id {
               type uint32;
               description
                 "Junos client internal identifier";
             }
             leaf-list cos-bind-point-name {
               type string;
               description
                 "Class-of-service bind point name";
             }
             leaf cos-bind-point-feature {
               type string;
               description
                 "Class-of-service bind point feature name";
             }
             leaf cos-bind-point-feature-object-name {
               type string;
               description
                 "Class-of-service bind point feature object name";
             }
           }
         }
         container cos-host-outbound-info {
           list cos-host-outbound-traffic-info {
             description
               "Class-of-service host-outbound-traffic information";
             leaf cos-host-outbound-traffic-protocol-name {
               type string;
               description
                 "CoS host outbound traffic protocol name";
             }
             leaf cos-host-outbound-traffic-dscp {
               type string;
               description
                 "CoS host outbound traffic dscp";
             }
             leaf cos-host-outbound-traffic-dot1p {
               type string;
               description
                 "CoS host outbound traffic ieee 802.1p";
             }
             leaf cos-host-outbound-traffic-fc-id {
               type string;
               description
                 "CoS host outbound traffic forwarding class id";
             }
             leaf cos-host-outbound-traffic-queue-id {
               type string;
               description
                 "CoS host outbound traffic queue id";
             }
             leaf cos-host-outbound-traffic-restrict-queue-id {
               type string;
               description
                 "CoS host outbound traffic restrict queue id";
             }
             leaf cos-host-outbound-traffic-override-firewall {
               type string;
               description
                 "CoS host outbound traffic override firwall action";
             }
             leaf cos-host-outbound-traffic-rw-dot1p {
               type string;
               description
                 "CoS host outbound traffic - use ieee 802.1p rewrite rules";
             }
           }
         }
         container cos-drop-congestion-notification-information {
           list cos-drop-congestion-notification-info {
             description
               "Class-of-service drop-congestion-notification information";
             leaf cos-dcn-fc-name {
               type string;
               description
                 "Cos DCN forwarding class";
             }
             leaf cos-dcn-udp-port {
               type int32;
               description
                 "Cos DCN udp port number";
             }
           }
           container cos-drop-congestion-notification-dscp-map {
             list cos-drop-congestion-notification-dscp-map-item {
               leaf trimmable-dscp {
                 type uint32;
                 description
                   "Trimmable DSCP code-point";
               }
               leaf trimmed-dscp {
                 type uint32;
                 description
                   "Trimmed DSCP code-point";
               }
             }
           }
         }
         container cos-dedicated-buffer-profile-information {
           list dedicated-buffer-profile {
             description
               "Class-of-service dedicated buffer profile";
             leaf dedicated-buffer-profile-name {
               type string;
               description
                 "Class-of-service dedicated buffer profile name";
             }
             leaf dedicated-buffer-profile-index {
               type int32;
               description
                 "Class-of-service dedicated buffer profile index";
             }
             leaf ingress-buffer-size {
               type string;
               description
                 "Ingress per port dedicated buffer in cells";
             }
             leaf egress-buffer-size {
               type string;
               description
                 "Egress per port dedicated buffer in cells";
             }
           }
         }
         container cos-dynamic-threshold-profile-information {
           list dynamic-threshold-profile {
             key "dynamic-threshold-profile-name";
             description
               "Class-of-service dynamic threshold profile";
             leaf dynamic-threshold-profile-name {
               type string;
               description
                 "Class-of-service dynamic threshold profile name";
             }
             leaf dynamic-threshold-profile-index {
               type uint64;
               description
                 "Class-of-service dynamic threshold profile index";
             }
             list dynamic-threshold-profile-entry {
               key "dynamic-threshold-profile-priority-group";
               description
                 "Class-of-service dynamic threshold profile entry";
               leaf dynamic-threshold-profile-priority-group {
                 type string;
                 description
                   "Class-of-service dynamic threshold profile priority 
                   group";
               }
               leaf dynamic-threshold-profile-threshold-value {
                 type uint32;
                 description
                   "Class-of-service dynamic threshold profile threshold 
                   value";
               }
             }
           }
         }
         container cos-decn-profile-information {
           list decn-profile {
             description
               "Class-of-service decn profile";
             leaf decn-profile-name {
               type string;
               description
                 "Class-of-service decn profile name";
             }
             leaf decn-profile-index {
               type uint64;
               description
                 "Class-of-service decn profile index";
             }
             list decn-profile-queue {
               description
                 "Class-of-service decn profile queue";
               leaf dynamic-explicit-congestion-notification-queue {
                 type uint32;
                 description
                   "Class-of-service DECN queue";
               }
               leaf dynamic-explicit-congestion-notification-offset {
                 type uint32;
                 description
                   "Class-of-service DECN offset";
               }
               leaf dynamic-explicit-congestion-notification-floor {
                 type uint32;
                 description
                   "Class-of-service DECN floor";
               }
             }
           }
         }
         container cos-scheduler-map-information {
           list scheduler-map {
             description
               "Class-of-service scheduler map";
             leaf scheduler-map-name {
               type string;
               description
                 "Class-of-service scheduler map name";
             }
             leaf scheduler-map-index {
               type uint64;
               description
                 "Class-of-service scheduler map index";
             }
             leaf user-plane-name {
               type string;
               description
                 "Class-of-service user-plane name for XDA";
             }
             list scheduler {
               leaf scheduler-name {
                 type string;
                 description
                   "Class-of-service scheduler name";
               }
               leaf fc-name {
                 type string;
                 description
                   "Class-of-service forwarding class name";
               }
               leaf scheduler-index {
                 type uint64;
                 description
                   "Class of service scheduler index";
               }
               leaf scheduler-tx-rate {
                 type string;
                 description
                   "Class-of-service scheduler transmit rate";
               }
               leaf scheduler-tx-limit {
                 type string;
                 description
                   "Class-of-service scheduler transmit limit";
               }
               leaf scheduler-buffer-size {
                 type string;
                 description
                   "Class-of-service scheduler buffer size";
               }
               leaf scheduler-buffer-multicast-share {
                 type uint32;
                 description
                   "Class-of-service scheduler multicast buffer share";
               }
               leaf scheduler-buffer-limit {
                 type string;
                 description
                   "Class-of-service scheduler buffer limit";
               }
               leaf scheduler-buffer-rate {
                 type string;
                 description
                   "Class-of-service scheduler buffer rate";
               }
               leaf scheduler-shared-buffer-maximum-percentage {
                 type uint32;
                 description
                   "Shared Buffer maximum percentage";
               }
               leaf scheduler-shared-buffer-multicast-maximum-percentage {
                 type uint32;
                 description
                   "Shared Buffer multicast maximum percentage";
               }
               leaf scheduler-buffer-dynamic-threshold {
                 type uint32;
                 description
                   "Queue shared-buffer dynamic threshold";
               }
               leaf scheduler-priority {
                 type string;
                 description
                   "Class-of-service scheduler priority";
               }
               leaf scheduler-shaping-rate {
                 type string;
                 description
                   "Class-of-service scheduler shaping rate";
               }
               leaf scheduler-shaping-rate-burst {
                 type string;
                 description
                   "Class-of-service scheduler shaping rate burst";
               }
               leaf scheduler-adjust-minimum {
                 type int32;
                 description
                   "Class-of-service scheduler adjustment minimum rate";
               }
               leaf scheduler-adjust-percent {
                 type int32;
                 description
                   "Class-of-service scheduler percent adjustment for a 
                   queue";
               }
               leaf scheduler-excess-priority {
                 type string;
                 description
                   "Class-of-service scheduler excess priority";
               }
               leaf scheduler-excess-rate {
                 type string;
                 description
                   "Class-of-service scheduler excess rate";
               }
               leaf scheduler-explicit-congestion-notification {
                 type string;
                 description
                   "Class-of-service ECN status of queue";
               }
               leaf scheduler-ecn-rtlog-rate-limit {
                 type uint32;
                 description
                   "Class-of-service ECN Security Log Rate Limit";
               }
               leaf scheduler-ecn-no-pfc-assist {
                 type string;
                 description
                   "Class-of-service ECN no pfc assist";
               }
               leaf scheduler-latency-ecn {
                 type string;
                 description
                   "Latency based ECN";
               }
               leaf scheduler-latency-ecn-threshold {
                 type uint32;
                 description
                   "Latency threshold";
               }
               leaf scheduler-queue-monitoring {
                 type string;
                 description
                   "Class-of-service queue depth monitoring of queue";
               }
               leaf scheduler-drop-profile-ln-index {
                 type uint32;
                 description
                   "Class-of-service scheduler drop profile index low, 
                   non-TCP";
               }
               leaf scheduler-drop-profile-ln {
                 type string;
                 description
                   "Class-of-service scheduler drop profile low, non-TCP";
               }
               leaf scheduler-drop-profile-lt-index {
                 type uint32;
                 description
                   "Class-of-service scheduler drop profile index low, TCP";
               }
               leaf scheduler-drop-profile-lt {
                 type string;
                 description
                   "Class-of-service scheduler drop profile low, TCP";
               }
               leaf scheduler-drop-profile-hn-index {
                 type uint32;
                 description
                   "Class-of-service scheduler drop profile index high, 
                   non-TCP";
               }
               leaf scheduler-drop-profile-hn {
                 type string;
                 description
                   "Class-of-service scheduler drop profile high, non-TCP";
               }
               leaf scheduler-drop-profile-ht-index {
                 type uint32;
                 description
                   "Class-of-service scheduler drop profile index high, TCP";
               }
               leaf scheduler-drop-profile-ht {
                 type string;
                 description
                   "Class-of-service scheduler drop profile high, TCP";
               }
               leaf scheduler-drop-profile-la-index {
                 type uint32;
                 description
                   "Class-of-service scheduler drop profile index low";
               }
               leaf scheduler-drop-profile-la {
                 type string;
                 description
                   "Class-of-service scheduler drop profile low";
               }
               leaf scheduler-drop-profile-ma-index {
                 type uint32;
                 description
                   "Class-of-service scheduler drop profile index medium";
               }
               leaf scheduler-drop-profile-ma {
                 type string;
                 description
                   "Class-of-service scheduler drop profile medium";
               }
               leaf scheduler-drop-profile-mla-index {
                 type uint32;
                 description
                   "Class-of-service scheduler drop profile index medium-low";
               }
               leaf scheduler-drop-profile-mla {
                 type string;
                 description
                   "Class-of-service scheduler drop profile medium-low";
               }
               leaf scheduler-drop-profile-mha-index {
                 type uint32;
                 description
                   "Class-of-service scheduler drop profile index 
                   medium-high";
               }
               leaf scheduler-drop-profile-mha {
                 type string;
                 description
                   "Class-of-service scheduler drop profile medium-high";
               }
               leaf scheduler-drop-profile-ha-index {
                 type uint32;
                 description
                   "Class-of-service scheduler drop profile index high";
               }
               leaf scheduler-drop-profile-ha {
                 type string;
                 description
                   "Class-of-service scheduler drop profile high";
               }
             }
           }
         }
         container cos-traffic-control-profile-information {
           list traffic-control-profile {
             description
               "Information about one or more traffic control profiles";
             leaf traffic-control-profile-name {
               type string;
               description
                 "Class-of-service traffic control profile name";
             }
             leaf traffic-control-profile-index {
               type uint64;
               description
                 "Index number for Class-of-service traffic control profile";
             }
             leaf user-plane-name {
               type string;
               description
                 "Class-of-service user-plane name for XDA";
             }
             leaf scheduler-map-name {
               type string;
               description
                 "Class-of-service scheduler map name";
             }
             leaf atm-service {
               type string;
               description
                 "Class-of-service traffic control profile atm service";
             }
             leaf shaping-rate {
               type uint64;
               description
                 "Class-of-service shaping rate";
             }
             leaf shaping-rate-burst {
               type uint32;
               description
                 "Class-of-service shaping rate burst, in bytes";
             }
             leaf low-granularity {
               type uint32;
               description
                 "Class-of-service low-granularity mode support";
             }
             leaf queue-mode-4q {
               type uint32;
               description
                 "Class-of-service tcp-voq-mode(4Q) mode support";
             }
             leaf shaping-rate-priority-strict-high {
               type uint64;
               description
                 "Class-of-service shaping rate for priority strict high";
             }
             leaf shaping-rate-priority-strict-high-burst {
               type uint32;
               description
                 "Class-of-service shaping rate burst for priority 
                 strict-high";
             }
             leaf shaping-rate-priority-high {
               type uint64;
               description
                 "Class-of-service shaping rate for priority high";
             }
             leaf shaping-rate-priority-high-burst {
               type uint32;
               description
                 "Class-of-service shaping rate for priority high burst";
             }
             leaf shaping-rate-priority-medium {
               type uint64;
               description
                 "Class-of-service shaping rate for priority medium";
             }
             leaf shaping-rate-priority-medium-burst {
               type uint32;
               description
                 "Class-of-service shaping rate for priority medium burst";
             }
             leaf shaping-rate-priority-medium-low {
               type uint64;
               description
                 "Class-of-service shaping rate for priority medium-low";
             }
             leaf shaping-rate-priority-medium-low-burst {
               type uint32;
               description
                 "Class-of-service shaping rate burst for priority 
                 medium-low";
             }
             leaf shaping-rate-priority-low {
               type uint64;
               description
                 "Class-of-service shaping rate for priority low";
             }
             leaf shaping-rate-priority-low-burst {
               type uint32;
               description
                 "Class-of-service shaping rate for priority low burst";
             }
             leaf shaping-rate-excess-high {
               type uint64;
               description
                 "Class-of-service shaping rate for excess high";
             }
             leaf shaping-rate-excess-high-burst {
               type uint32;
               description
                 "Class-of-service shaping rate for excess high burst";
             }
             leaf shaping-rate-excess-medium-high {
               type uint64;
               description
                 "Class-of-service shaping rate for excess medium-high";
             }
             leaf shaping-rate-excess-medium-high-burst {
               type uint32;
               description
                 "Class-of-service shaping rate burst for excess medium-high";
             }
             leaf shaping-rate-excess-medium-low {
               type uint64;
               description
                 "Class-of-service shaping rate for excess medium-low";
             }
             leaf shaping-rate-excess-medium-low-burst {
               type uint32;
               description
                 "Class-of-service shaping rate burst for excess medium-low";
             }
             leaf shaping-rate-excess-low {
               type uint64;
               description
                 "Class-of-service shaping rate for excess low";
             }
             leaf shaping-rate-excess-low-burst {
               type uint32;
               description
                 "Class-of-service shaping rate for excess low burst";
             }
             leaf guaranteed-rate {
               type uint64;
               description
                 "Class-of-service guaranteed rate";
             }
             leaf guaranteed-rate-burst {
               type uint32;
               description
                 "Class-of-service guaranteed rate burst, in bytes";
             }
             leaf delay-buffer-rate {
               type uint64;
               description
                 "Class-of-service delay buffer rate";
             }
             leaf excess-rate {
               type uint32;
               description
                 "Class-of-service excess rate";
             }
             leaf excess-rate-high {
               type uint32;
               description
                 "Class-of-service excess rate for excess-high priority 
                 traffic";
             }
             leaf excess-rate-medium-high {
               type uint32;
               description
                 "Class-of-service excess rate for excess-medium-high 
                 priority traffic";
             }
             leaf excess-rate-medium-low {
               type uint32;
               description
                 "Class-of-service excess rate for excess-medium-low 
                 priority traffic";
             }
             leaf excess-rate-low {
               type uint32;
               description
                 "Class-of-service excess rate for excess-low priority 
                 traffic";
             }
             leaf adjust-minimum {
               type uint64;
               description
                 "Class-of-service adjustment minimum rate";
             }
             leaf overhead-bytes {
               type int32;
               description
                 "Class-of-service Overhead bytes";
             }
             leaf frame-mode-bytes {
               type int32;
               description
                 "Class-of-service overhead bytes when in frame-mode";
             }
             leaf cell-mode-bytes {
               type int32;
               description
                 "Class-of-service overhead bytes when in cell-mode";
             }
             leaf overhead-accounting-mode {
               type string;
               description
                 "Class-of-service Overhead Accounting Mode";
             }
             list traffic-control-profile-instance {
               description
                 "Class-of-service traffic control profile instance";
               leaf traffic-control-profile-instance-name {
                 type string;
                 description
                   "Class-of-service traffic control profile instance";
               }
               leaf traffic-control-profile-instance-index {
                 type uint32;
                 description
                   "Index number for Class-of-service traffic control 
                   profile instance";
               }
               leaf instance-reference-count {
                 type uint32;
                 description
                   "Instance reference count";
               }
             }
           }
         }
         container cos-routing-instance-information {
           list routing-instance-map {
             description
               "Mapping between class-of-service objects and routing 
               instances";
             leaf routing-instance-name {
               type string;
               description
                 "Name of class-of-service routing instance";
             }
             list i-logical-map {
               leaf i-logical-name {
                 type string;
                 description
                   "Class-of-service logical interface name";
               }
               leaf i-logical-index {
                 type uint32;
                 description
                   "Class-of-service logical interface index";
               }
               leaf monitoring-profile-map-name {
                 type string;
                 description
                   "Monitoring Profile Name";
               }
               list cos-objects {
                 description
                   "Class-of-service object  mappings";
                 leaf cos-object-type {
                   type string;
                   description
                     "Class-of-service object type";
                 }
                 leaf cos-object-name {
                   type string;
                   description
                     "Class-of-service object name";
                 }
                 leaf cos-object-subtype {
                   type string;
                   description
                     "Class-of-service object subtype";
                 }
                 leaf cos-object-index {
                   type uint64;
                   description
                     "Class-of-service object index";
                 }
               }
             }
           }
         }
         container cos-fabric-scheduler-map-information {
           container fabric-scheduler-map {
             list fabric-scheduler {
               leaf fabric-scheduler-name {
                 type string;
                 description
                   "Class-of-service scheduler name";
               }
               leaf fabric-scheduler-index {
                 type uint32;
                 description
                   "Class of service scheduler index";
               }
               leaf fabric-scheduler-drop-profile-ln-index {
                 type uint32;
                 description
                   "Class-of-service scheduler drop profile index low, 
                   non-TCP";
               }
               leaf fabric-scheduler-drop-profile-ln {
                 type string;
                 description
                   "Class-of-service scheduler drop profile low, non-TCP";
               }
               leaf fabric-scheduler-drop-profile-lt-index {
                 type uint32;
                 description
                   "Class-of-service scheduler drop profile index low, TCP";
               }
               leaf fabric-scheduler-drop-profile-lt {
                 type string;
                 description
                   "Class-of-service scheduler drop profile low, TCP";
               }
               leaf fabric-scheduler-drop-profile-hn-index {
                 type uint32;
                 description
                   "Class-of-service scheduler drop profile index high, 
                   non-TCP";
               }
               leaf fabric-scheduler-drop-profile-hn {
                 type string;
                 description
                   "Class-of-service scheduler drop profile high, non-TCP";
               }
               leaf fabric-scheduler-drop-profile-ht-index {
                 type uint32;
                 description
                   "Class-of-service scheduler drop profile index high, TCP";
               }
               leaf fabric-scheduler-drop-profile-ht {
                 type string;
                 description
                   "Class-of-service scheduler drop profile high, TCP";
               }
               leaf fabric-scheduler-priority {
                 type string;
               }
             }
           }
         }
         container cos-tcm-information {
           list tcm {
             description
               "Class-of-service traffic-class-map";
             leaf tcm-name {
               type string;
               description
                 "Class-of-service traffic-class-map name";
             }
             leaf tcm-type {
               type string;
               description
                 "Class-of-service traffic-class-map type";
             }
             leaf table-index {
               type uint32;
               description
                 "Table index";
             }
             container tcm-map {
               list tcm-map-item {
                 leaf code-point {
                   type string;
                   description
                     "Class-of-service code point alias name or bits";
                 }
                 leaf tc-name {
                   type string;
                   description
                     "Class-of-service traffic-class-map traffic-class name";
                 }
               }
             }
           }
         }
         container cos-lecn-profile-information {
           list lecn-profile {
             description
               "Class-of-service lecn profile";
             leaf lecn-profile-name {
               type string;
               description
                 "Class-of-service lecn profile name";
             }
             leaf lecn-profile-index {
               type uint64;
               description
                 "Class-of-service lecn profile index";
             }
             list lecn-profile-queue {
               description
                 "Class-of-service lecn profile queue";
               leaf latency-explicit-congestion-notification-queue {
                 type uint32;
                 description
                   "Class-of-service LECN queue";
               }
               leaf latency-explicit-congestion-notification-latency {
                 type uint32;
                 description
                   "Class-of-service LECN latency";
               }
             }
           }
         }
       }
       container physical-interface-cos-information {
         description
           "Physical interface class-of-service parameters";
       }
       container precl-statistics {
         description
           "Preclassifier Statistics ";
         container precl-information {
           description
             "Preclassifier Statistics";
         }
       }
       container mlfr-uni-nni-traffic-statistics {
         container bundle {
         }
       }
       container lag-traffic-statistics {
         container lag-multicast-statistics {
           leaf lag-multicast-statistics-header {
             type empty;
           }
           container lag-ipv4-multicast-statistics {
             leaf input-packets {
               type uint64;
             }
             leaf input-pps {
               type int32;
             }
             leaf input-bytes {
               type int32;
             }
             leaf input-bps {
               type int32;
             }
             leaf output-packets {
               type uint64;
             }
             leaf output-pps {
               type int32;
             }
             leaf output-bytes {
               type int32;
             }
             leaf output-bps {
               type int32;
             }
           }
           container lag-ipv6-multicast-statistics {
             leaf input-packets {
               type uint64;
             }
             leaf input-pps {
               type int32;
             }
             leaf input-bytes {
               type int32;
             }
             leaf input-bps {
               type int32;
             }
             leaf output-packets {
               type uint64;
             }
             leaf output-pps {
               type int32;
             }
             leaf output-bytes {
               type int32;
             }
             leaf output-bps {
               type int32;
             }
           }
         }
         list if-distribution-list-information {
         }
         container ifd-lag-traffic-statistics {
         }
       }
       container ifd-lag-traffic-statistics {
       }
       container interval-information {
         list interval {
           description
             "Statistics for a single interval";
         }
       }
       container transport-interval-information {
         list transport-interval {
           description
             "Statistics for a single interval";
           list transport-pm-ber {
             leaf transport-pm-ber-thr-max {
               type string;
             }
             leaf transport-pm-ber-tca-max-en {
               type string;
             }
             leaf transport-pm-ber-tca-max {
               type string;
             }
           }
           list transport-pm-ber-cur {
             leaf transport-pm-ber-cur-thr-max {
               type string;
             }
             leaf transport-pm-ber-cur-tca-max-en {
               type string;
             }
             leaf transport-pm-ber-cur-tca-max {
               type string;
             }
           }
         }
       }
     }
     list logical-interface {
       key "name";
       description
         "Information about a single logical interface";
       leaf name {
         type string;
         description
           "Name of this item";
       }
       leaf admin-status {
         type string;
         description
           "Desired state of the interface";
       }
       leaf oper-status {
         type string;
         description
           "Current operational state of the interface";
       }
       leaf logical-interface-zone-name {
         type string;
         description
           "Zone name for this interface";
       }
       leaf subunit {
         type int32;
         description
           "Subunit for this interface";
       }
       leaf dialer-time-to-disconnect {
         type string;
         description
           "Time for dialer to disconnect due to idle timeout";
       }
       leaf lcp-state {
         type string;
         description
           "State of the Line Control Protocol";
       }
       leaf chap-state {
         type string;
         description
           "State of the Challenge Handshake Authentication Protocol";
       }
       leaf pap-state {
         type string;
         description
           "State of the Password Authentication Protocol";
       }
       container layer2-input-policer-information {
         description
           "Information about Layer 2 input policer for interface";
         leaf layer2-input-policer {
           type string;
           description
             "Name of the Layer 2 input policer";
         }
       }
       container layer2-output-policer-information {
         description
           "Information about Layer 2 output policer for interface";
         leaf layer2-output-policer {
           type string;
           description
             "Name of the Layer 2 output policer";
         }
       }
       container pppoe-information {
         description
           "PPPoE information";
         list pppoe-interface {
           leaf state {
             type string;
             description
               "State";
           }
           leaf session-id {
             type string;
             description
               "Session ID";
           }
           leaf ac-name-session {
             type string;
             description
               "Session AC name";
           }
           leaf remote-mac {
             type string;
             description
               "Remote MAC address";
           }
           leaf ac-name-config {
             type string;
             description
               "Configured AC name";
           }
           leaf service-name {
             type string;
             description
               "Service name";
           }
           leaf auto-reconnect {
             type string;
             description
               "Autoreconnect timeout";
           }
           leaf idle-timeout {
             type string;
             description
               "Idle timeout";
           }
           leaf underlying-interface-name {
             type string;
             description
               "Underlying interface name";
           }
           leaf underlying-interface-index {
             type string;
             description
               "Underlying interface index";
           }
           leaf padg-credits {
             type int32;
             description
               "PADG transmit credits";
           }
           leaf pppoe-credit-scale-factor {
             type string;
             description
               "Scaling factor";
           }
           leaf ignore-eol-tag {
             type string;
             description
               "Ignore End-of-List TAG";
           }
           leaf ppp-max-payload-tag {
             type int32;
             description
               "PPP-Max-Payload TAG";
           }
           leaf interface-name {
             type string;
             description
               "Interface name";
           }
           leaf interface-index {
             type string;
             description
               "Index";
           }
           leaf aci-iflset-name {
             type string;
             description
               "ACI Interface Set name";
           }
           leaf aci-iflset-index {
             type string;
             description
               "ACI Interface Set index";
           }
           leaf ifl-type {
             type string;
             description
               "Type";
           }
           leaf session-uptime {
             type string;
             description
               "Duration for which the session has been up";
           }
           leaf dynamic-profile {
             type string;
             description
               "Dynamic Profile name";
           }
           leaf pppoe-credits {
             type string;
             description
               "Forwarding credit balances";
           }
           leaf dynamic-interface-bandwidth {
             type string;
             description
               "Dynamic interface bandwidth";
           }
           leaf agent-circuit-id {
             type string;
             description
               "Agent Circuit ID";
           }
           leaf agent-remote-id {
             type string;
             description
               "Agent Remote ID";
           }
           leaf padm-motm {
             type string;
             description
               "PADM Message of the Moment tag";
           }
           leaf padm-hurl {
             type string;
             description
               "PADM HTTP URL tag";
           }
           leaf pppoe-relay-session-id {
             type string;
             description
               "PPPoE Relay Session ID";
           }
         }
       }
       container pppoe-underlying-information {
         description
           "PPPoE Underlying information";
         list pppoe-underlying-interface {
           leaf dynamic-profile {
             type string;
             description
               "Dynamic Profile name";
           }
           leaf service-name-table {
             type string;
             description
               "Name of Service Name Table";
           }
           leaf max-sessions {
             type int32;
             description
               "Maximum number of PPPoE sessions";
           }
           leaf max-sessions-vsa-ignore {
             type string;
             description
               "Ignore max-sessions VSA";
           }
           leaf duplicate-protection {
             type string;
             description
               "Duplicate protection mode";
           }
           leaf short-cycle-protection {
             type string;
             description
               "Short cycle protection mode";
           }
           leaf direct-connect {
             type string;
             description
               "Direct connect mode";
           }
           leaf ac-name {
             type string;
             description
               "Access Concentrator name";
           }
           leaf underlying-interface-name {
             type string;
             description
               "Underlying interface name";
           }
           leaf underlying-interface-index {
             type string;
             description
               "Underlying interface index";
           }
           leaf encapsulation-type-identifier {
             type string;
             description
               "Encapsulation type identifier";
           }
           leaf state {
             type string;
             description
               "State";
           }
           leaf active-sessions {
             type int32;
             description
               "Number of active PPPoE sessions";
           }
           leaf aci-autosensing {
             type string;
             description
               "ACI VLAN Autosensing mode";
           }
           leaf line-identity-autosensing {
             type string;
             description
               "Line Identity Autosensing mode";
           }
         }
       }
       container aci-vlan-information {
         leaf dynamic-profile {
           type string;
           description
             "Dynamic Profile name";
         }
       }
       container line-identity-information {
         leaf dynamic-profile {
           type string;
           description
             "Dynamic Profile name";
         }
         leaf circuit-id {
           type string;
           description
             "Aci vlan attribute";
         }
         leaf remote-id {
           type string;
           description
             "Aci vlan attribute";
         }
         leaf accept-no-ids {
           type string;
           description
             "Aci vlan attribute";
         }
       }
       container demux-information {
         description
           "Demux information";
         container demux-interface {
           leaf demux-underlying-interface-name {
             type string;
             description
               "Underlying interface name";
           }
           leaf demux-underlying-interface-index {
             type string;
             description
               "Underlying interface index";
           }
           leaf demux-inet-prefix-type {
             type string;
             description
               "Prefix type";
           }
           leaf demux-inet-prefix-count {
             type string;
             description
               "IPv4 Prefix count";
           }
           leaf demux-inet-prefix {
             type string;
             description
               "IPv4 Prefix";
           }
           leaf demux-inet6-prefix-type {
             type string;
             description
               "Prefix type";
           }
           leaf demux-inet6-prefix-count {
             type string;
             description
               "IPv6 Prefix count";
           }
           leaf demux-inet6-prefix {
             type string;
             description
               "IPv6 Prefix";
           }
         }
       }
       container dual-ad-icl-color-information {
         container dual-ad-icl-color-info {
           description
             "Dual-AD ICL Color Information";
           leaf dual-ad-icl-color-type {
             type uint32;
             description
               "Dual-AD ICL Color Type";
           }
           leaf dual-ad-icl-color {
             type uint32;
             description
               "Dual-AD ICL Color";
           }
         }
       }
       container dialer-information {
         description
           "Dialer information";
         leaf dialer-time-to-disconnect {
           type string;
           description
             "Time for dialer to disconnect due to idle timeout";
         }
         container dialer-interface {
           container dialer-interface-flags {
             description
               "Flags indicating interface configuration";
             leaf backup {
               type empty;
               description
                 "Dialer backup";
             }
             leaf multilink {
               type empty;
               description
                 "Dialer multilink";
             }
             leaf watchlist {
               type empty;
               description
                 "Dialer watchlist";
             }
             leaf interesting-detected {
               type empty;
               description
                 "Interesting packet detected";
             }
           }
           list dial-string-list {
             leaf dial-string {
               type string;
               description
                 "Dial string";
             }
           }
           list sub-interface-list {
             leaf sub-interface-name {
               type string;
               description
                 "Subordinate interface name";
             }
           }
           list watch-list {
             leaf watch-route {
               type string;
               description
                 "Watch route";
             }
           }
           leaf dialer-interface-name {
             type string;
             description
               "Interface name";
           }
           leaf dialer-interface-state {
             type string;
             description
               "Dialer interface state";
           }
           leaf pool-id {
             type string;
             description
               "Pool identifier";
           }
           leaf primary-interface {
             type string;
             description
               "Primary interface";
           }
           leaf activation-delay {
             type string;
             description
               "Activation delay";
           }
           leaf deactivation-delay {
             type string;
             description
               "Deactivation delay";
           }
           leaf activation-delay-elapsed {
             type string;
             description
               "Activation delay elapsed";
           }
           leaf deactivation-delay-elapsed {
             type string;
             description
               "Deactivation delay elapsed";
           }
           leaf call-idle-timeout {
             type string;
             description
               "Call idle timeout";
           }
           leaf initial-route-check {
             type string;
             description
               "Initial route check delay";
           }
           leaf redial-delay {
             type string;
             description
               "Delay before dialer dials out again (seconds)";
           }
           leaf callback-wait-period {
             type string;
             description
               "Delay before dialer attempts callback (seconds)";
           }
           leaf callback-wait-period-elapsed {
             type string;
             description
               "Number of seconds in callback wait period that have elapsed";
           }
           leaf load-threshold {
             type string;
             description
               "Load threshold that determines when interfaces are added to 
               bundle";
           }
           leaf load-interval {
             type string;
             description
               "Interval over which average load is calculated";
           }
         }
       }
       container shared-interface-information {
         description
           "Shared interface information";
         container shared-interface-logical-interface {
           description
             "Shared interface logical interface";
           leaf peer-interface-name {
             type string;
             description
               "Peer interface name";
           }
           leaf interface-shared-with {
             type string;
             description
               "Logical interface owner";
           }
           leaf rx-fe {
             type string;
             description
               "Rx tunnel token forwarding element";
           }
           leaf rx-nhid {
             type string;
             description
               "Rx tunnel token next hop index";
           }
           leaf tx-fe {
             type string;
             description
               "Tx tunnel token forwarding element";
           }
           leaf tx-nhid {
             type string;
             description
               "Tx tunnel token next hop index";
           }
         }
       }
       container mac-database {
       }
       container queue-counters {
         description
           "Queue counter statistics";
         leaf queue-counters-error-message {
           type string;
           description
             "Queue statistics not available for this interface";
         }
         container interface-cos-short-summary {
           description
             "Summary of queue information on an interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
         }
         list queue {
           key "queue-number";
           description
             "Counters for a single queue";
           leaf queue-number {
             type uint32;
             description
               "Queue number";
           }
           leaf queue-counters-queued-packets {
             type int32;
             description
               "Queued packet count";
           }
           leaf queue-counters-trans-packets {
             type int32;
             description
               "Total number of transmitted packets";
           }
           leaf queue-counters-total-drop-packets {
             type int32;
             description
               "Number of total packets dropped at the queue";
           }
           leaf forwarding-class-name {
             type string;
             description
               "Forwarding class name associated with queue";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-queued-packets-na {
             type string;
             description
               "Queued packets not available";
           }
           leaf queue-counters-queued-bytes-na {
             type string;
             description
               "Queued bytes not available";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets-na {
             type string;
             description
               "Number of packets dropped due to tail drop not available";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of packets dropped at tail drop of the queue";
           }
           leaf queue-counters-tail-drop-bytes-rate {
             type int32;
             description
               "Number of packets dropped at tail drop of the queue";
           }
           leaf queue-counters-ecn-ce-packets {
             type int32;
             description
               "Total number of ECN CE packets";
           }
           leaf queue-counters-ecn-ce-packets-rate {
             type int32;
             description
               "Rate at which ECN CE packets are transmitted";
           }
           leaf queue-counters-ecn-ce-bytes {
             type int32;
             description
               "Total number of ECN CE bytes";
           }
           leaf queue-counters-ecn-ce-bytes-rate {
             type int32;
             description
               "Rate at which ECN CE bytes are transmitted";
           }
           leaf queue-counters-rate-limit-drop-packets-na {
             type string;
             description
               "Number of packets dropped due to rate-limit drop not 
               available";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes-na {
             type string;
             description
               "Number of bytes dropped due to tail drop not available";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets-na {
             type string;
             description
               "Number of packets dropped due to RED not available";
           }
           leaf queue-counters-red-packets {
             type int32;
             description
               "Number of packets dropped due to RED";
           }
           leaf queue-counters-red-packets-rate {
             type int32;
             description
               "Rate at which packets are dropped due to RED";
           }
           leaf queue-counters-red-packets-ln {
             type int32;
             description
               "Number of RED dropped low-loss, non-TCP packets";
           }
           leaf queue-counters-red-packets-rate-ln {
             type int32;
             description
               "RED drop rate for low-loss, non-TCP packets";
           }
           leaf queue-counters-red-packets-lt {
             type int32;
             description
               "Number of RED dropped of low-loss, TCP packets";
           }
           leaf queue-counters-red-packets-rate-lt {
             type int32;
             description
               "RED drop rate for low-loss, TCP packets";
           }
           leaf queue-counters-red-packets-hn {
             type int32;
             description
               "Number of RED dropped high-loss, non-TCP packets";
           }
           leaf queue-counters-red-packets-rate-hn {
             type int32;
             description
               "RED drop rate for high-loss, non-TCP packets";
           }
           leaf queue-counters-red-packets-ht {
             type int32;
             description
               "Number of RED dropped high-loss, TCP packets";
           }
           leaf queue-counters-red-packets-rate-ht {
             type int32;
             description
               "RED drop rate for high-loss, TCP packets";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-medium {
             type int32;
             description
               "Number of RED dropped medium-loss packets";
           }
           leaf queue-counters-red-packets-rate-medium {
             type int32;
             description
               "RED drop rate for medium-loss packets";
           }
           leaf queue-counters-red-packets-high {
             type int32;
             description
               "Number of RED dropped high-loss packets";
           }
           leaf queue-counters-red-packets-rate-high {
             type int32;
             description
               "RED drop rate for high-loss packets";
           }
           leaf queue-counters-red-bytes-na {
             type string;
             description
               "Number of bytes dropped due to RED not available";
           }
           leaf queue-counters-red-bytes {
             type int32;
             description
               "Number of bytes dropped due to RED";
           }
           leaf queue-counters-red-bytes-rate {
             type int32;
             description
               "Rate at which bytes are dropped due to RED";
           }
           leaf queue-counters-red-bytes-ln {
             type int32;
             description
               "Number of RED dropped low-loss, non-TCP bytes";
           }
           leaf queue-counters-red-bytes-rate-ln {
             type int32;
             description
               "RED drop rate for low-loss, non-TCP bytes";
           }
           leaf queue-counters-red-bytes-lt {
             type int32;
             description
               "Number of RED dropped low-loss, TCP bytes";
           }
           leaf queue-counters-red-bytes-rate-lt {
             type int32;
             description
               "RED drop rate for low-loss, TCP bytes";
           }
           leaf queue-counters-red-bytes-hn {
             type int32;
             description
               "Number of RED dropped high-loss, non-TCP bytes";
           }
           leaf queue-counters-red-bytes-rate-hn {
             type int32;
             description
               "RED drop rate for high-loss, non-TCP bytes";
           }
           leaf queue-counters-red-bytes-ht {
             type int32;
             description
               "Number of RED dropped high-loss, TCP bytes";
           }
           leaf queue-counters-red-bytes-rate-ht {
             type int32;
             description
               "RED drop rate for high-loss, TCP bytes";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-medium {
             type int32;
             description
               "Number of RED dropped medium-loss bytes";
           }
           leaf queue-counters-red-bytes-rate-medium {
             type int32;
             description
               "RED drop rate for medium-loss bytes";
           }
           leaf queue-counters-red-bytes-high {
             type int32;
             description
               "Number of RED dropped high-loss bytes";
           }
           leaf queue-counters-red-bytes-rate-high {
             type int32;
             description
               "RED drop rate for high-loss bytes";
           }
           leaf queue-counters-timestamp {
             type int32;
             description
               "Last packet enqueued timestamp";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
           leaf queue-counters-reserved-buffer-packets {
             type int32;
             description
               "Queues's usage of reserved buffer pool in pkts";
           }
           leaf queue-counters-reserved-buffer-bytes {
             type int32;
             description
               "Queues's usage of reserved buffer pool in bytes";
           }
           leaf queue-counters-shared-buffer-packets {
             type int32;
             description
               "Queues's usage of shared buffer pool in pkts";
           }
           leaf queue-counters-shared-buffer-bytes {
             type int32;
             description
               "Queues's usage of shared buffer pool in bytes";
           }
           leaf queue-counters-depth-average {
             type int32;
             description
               "Time averaged queue depth";
           }
           leaf queue-counters-depth-current {
             type int32;
             description
               "Current instantaneous queue depth";
           }
           leaf queue-counters-depth-peak {
             type int32;
             description
               "Peak queue depth";
           }
           leaf queue-counters-depth-max {
             type int32;
             description
               "Maximum queue depth attained";
           }
           leaf queue-counters-srx-reserved-buffer-bytes {
             type int32;
             description
               "Queues's usage of reserved buffer pool in bytes";
           }
           leaf queue-counters-srx-depth-current {
             type int32;
             description
               "Current instantaneous queue depth";
           }
         }
         container interface-cos-summary {
           description
             "Summary of forwarding class and queue information on an 
             interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
           leaf intf-cos-burst-size-for-ifl {
             type int32;
             description
               "Burst size for the logical interface";
           }
         }
       }
       container voq-counters {
         description
           "VOQ counter statistics";
         leaf voq-counters-error-message {
           type string;
           description
             "VOQ statistics not available for this interface";
         }
         container voq {
           description
             "Counters for a single voq";
           container fpc {
             description
               "Counters for a single FPC";
             leaf fpc-no {
               type int32;
               description
                 "FPC number";
             }
             container pfe {
               description
                 "Counters for a single PFE";
               leaf-list pfe-no {
                 type int32;
                 description
                   "PFE number";
               }
               leaf voq-counters-tail-drop-packets {
                 type int32;
                 description
                   "Tail DROP packet count";
               }
               leaf voq-counters-tail-drop-packets-rate {
                 type int32;
                 description
                   "Rate at which tail packets are dropped";
               }
               leaf voq-counters-tail-drop-bytes {
                 type int32;
                 description
                   "Tail DROP bytes count";
               }
               leaf voq-counters-tail-drop-bytes-rate {
                 type int32;
                 description
                   "Rate at which tail bytes are dropped";
               }
               leaf voq-counters-drop-packets {
                 type int32;
                 description
                   "DROP packet count";
               }
               leaf voq-counters-drop-packets-rate {
                 type int32;
                 description
                   "Rate at which packets are dropped";
               }
               leaf voq-counters-drop-bytes {
                 type int32;
                 description
                   "DROP bytes count";
               }
               leaf voq-counters-drop-bytes-rate {
                 type int32;
                 description
                   "Rate at which bytes are dropped";
               }
               leaf voq-counters-queued-packets {
                 type int32;
                 description
                   "QUEUED packets count";
               }
               leaf voq-counters-queued-packets-rate {
                 type int32;
                 description
                   "Rate at which packets are queued";
               }
               leaf voq-counters-queued-bytes {
                 type int32;
                 description
                   "QUEUED bytes count";
               }
               leaf voq-counters-queued-bytes-rate {
                 type int32;
                 description
                   "Rate at which bytes are queued";
               }
               leaf voq-counters-transmitted-packets {
                 type int32;
                 description
                   "Transmitted packets count";
               }
               leaf voq-counters-transmitted-packets-rate {
                 type int32;
                 description
                   "Rate at which packets are transmitted";
               }
               leaf voq-counters-transmitted-bytes {
                 type int32;
                 description
                   "Transmitted bytes count";
               }
               leaf voq-counters-transmitted-bytes-rate {
                 type int32;
                 description
                   "Rate at which bytes are transmitted";
               }
               leaf voq-counters-queue-depth-bytes-current {
                 type int32;
                 description
                   "Current queue length";
               }
               leaf voq-counters-queue-depth-bytes-peak {
                 type int32;
                 description
                   "Peak queue length";
               }
               leaf voq-counters-queue-depth-bytes-average {
                 type int32;
                 description
                   "Average queue length";
               }
             }
           }
           leaf queue-number {
             type uint32;
             description
               "Queue number";
           }
           leaf forwarding-class-name {
             type string;
             description
               "Forwarding class name associated with queue";
           }
           leaf restricted-forwarding-class-name {
             type string;
           }
         }
       }
       container ingress-queue-counters {
         description
           "Ingress queue counter statistics";
         list queue {
           key "queue-number";
           description
             "Counters for a single queue";
           leaf queue-number {
             type uint32;
             description
               "Queue number";
           }
           leaf forwarding-class-name {
             type string;
             description
               "Forwarding class name associated with queue";
           }
           leaf queue-counters-queued-packets {
             type int32;
             description
               "Queued packet count";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-queued-packets-na {
             type string;
             description
               "Queued packets not available";
           }
           leaf queue-counters-queued-bytes-na {
             type string;
             description
               "Queued bytes not available";
           }
           leaf queue-counters-trans-packets {
             type int32;
             description
               "Total number of transmitted packets";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets-na {
             type string;
             description
               "Number of packets dropped due to tail drop not available";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of packets dropped at tail drop of the queue";
           }
           leaf queue-counters-tail-drop-bytes-rate {
             type int32;
             description
               "Number of packets dropped at tail drop of the queue";
           }
           leaf queue-counters-ecn-ce-packets {
             type int32;
             description
               "Total number of ECN CE packets";
           }
           leaf queue-counters-ecn-ce-packets-rate {
             type int32;
             description
               "Rate at which ECN CE packets are transmitted";
           }
           leaf queue-counters-ecn-ce-bytes {
             type int32;
             description
               "Total number of ECN CE bytes";
           }
           leaf queue-counters-ecn-ce-bytes-rate {
             type int32;
             description
               "Rate at which ECN CE bytes are transmitted";
           }
           leaf queue-counters-rate-limit-drop-packets-na {
             type string;
             description
               "Number of packets dropped due to rate-limit drop not 
               available";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes-na {
             type string;
             description
               "Number of bytes dropped due to tail drop not available";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets-na {
             type string;
             description
               "Number of packets dropped due to RED not available";
           }
           leaf queue-counters-red-packets {
             type int32;
             description
               "Number of packets dropped due to RED";
           }
           leaf queue-counters-red-packets-rate {
             type int32;
             description
               "Rate at which packets are dropped due to RED";
           }
           leaf queue-counters-red-packets-ln {
             type int32;
             description
               "Number of RED dropped low-loss, non-TCP packets";
           }
           leaf queue-counters-red-packets-rate-ln {
             type int32;
             description
               "RED drop rate for low-loss, non-TCP packets";
           }
           leaf queue-counters-red-packets-lt {
             type int32;
             description
               "Number of RED dropped of low-loss, TCP packets";
           }
           leaf queue-counters-red-packets-rate-lt {
             type int32;
             description
               "RED drop rate for low-loss, TCP packets";
           }
           leaf queue-counters-red-packets-hn {
             type int32;
             description
               "Number of RED dropped high-loss, non-TCP packets";
           }
           leaf queue-counters-red-packets-rate-hn {
             type int32;
             description
               "RED drop rate for high-loss, non-TCP packets";
           }
           leaf queue-counters-red-packets-ht {
             type int32;
             description
               "Number of RED dropped high-loss, TCP packets";
           }
           leaf queue-counters-red-packets-rate-ht {
             type int32;
             description
               "RED drop rate for high-loss, TCP packets";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-medium {
             type int32;
             description
               "Number of RED dropped medium-loss packets";
           }
           leaf queue-counters-red-packets-rate-medium {
             type int32;
             description
               "RED drop rate for medium-loss packets";
           }
           leaf queue-counters-red-packets-high {
             type int32;
             description
               "Number of RED dropped high-loss packets";
           }
           leaf queue-counters-red-packets-rate-high {
             type int32;
             description
               "RED drop rate for high-loss packets";
           }
           leaf queue-counters-red-bytes-na {
             type string;
             description
               "Number of bytes dropped due to RED not available";
           }
           leaf queue-counters-red-bytes {
             type int32;
             description
               "Number of bytes dropped due to RED";
           }
           leaf queue-counters-red-bytes-rate {
             type int32;
             description
               "Rate at which bytes are dropped due to RED";
           }
           leaf queue-counters-red-bytes-ln {
             type int32;
             description
               "Number of RED dropped low-loss, non-TCP bytes";
           }
           leaf queue-counters-red-bytes-rate-ln {
             type int32;
             description
               "RED drop rate for low-loss, non-TCP bytes";
           }
           leaf queue-counters-red-bytes-lt {
             type int32;
             description
               "Number of RED dropped low-loss, TCP bytes";
           }
           leaf queue-counters-red-bytes-rate-lt {
             type int32;
             description
               "RED drop rate for low-loss, TCP bytes";
           }
           leaf queue-counters-red-bytes-hn {
             type int32;
             description
               "Number of RED dropped high-loss, non-TCP bytes";
           }
           leaf queue-counters-red-bytes-rate-hn {
             type int32;
             description
               "RED drop rate for high-loss, non-TCP bytes";
           }
           leaf queue-counters-red-bytes-ht {
             type int32;
             description
               "Number of RED dropped high-loss, TCP bytes";
           }
           leaf queue-counters-red-bytes-rate-ht {
             type int32;
             description
               "RED drop rate for high-loss, TCP bytes";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-medium {
             type int32;
             description
               "Number of RED dropped medium-loss bytes";
           }
           leaf queue-counters-red-bytes-rate-medium {
             type int32;
             description
               "RED drop rate for medium-loss bytes";
           }
           leaf queue-counters-red-bytes-high {
             type int32;
             description
               "Number of RED dropped high-loss bytes";
           }
           leaf queue-counters-red-bytes-rate-high {
             type int32;
             description
               "RED drop rate for high-loss bytes";
           }
           leaf queue-counters-timestamp {
             type int32;
             description
               "Last packet enqueued timestamp";
           }
           leaf queue-counters-total-drop-packets {
             type int32;
             description
               "Number of total packets dropped at the queue";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
           leaf queue-counters-reserved-buffer-packets {
             type int32;
             description
               "Queues's usage of reserved buffer pool in pkts";
           }
           leaf queue-counters-reserved-buffer-bytes {
             type int32;
             description
               "Queues's usage of reserved buffer pool in bytes";
           }
           leaf queue-counters-shared-buffer-packets {
             type int32;
             description
               "Queues's usage of shared buffer pool in pkts";
           }
           leaf queue-counters-shared-buffer-bytes {
             type int32;
             description
               "Queues's usage of shared buffer pool in bytes";
           }
           leaf queue-counters-depth-average {
             type int32;
             description
               "Time averaged queue depth";
           }
           leaf queue-counters-depth-current {
             type int32;
             description
               "Current instantaneous queue depth";
           }
           leaf queue-counters-depth-peak {
             type int32;
             description
               "Peak queue depth";
           }
           leaf queue-counters-depth-max {
             type int32;
             description
               "Maximum queue depth attained";
           }
           leaf queue-counters-srx-reserved-buffer-bytes {
             type int32;
             description
               "Queues's usage of reserved buffer pool in bytes";
           }
           leaf queue-counters-srx-depth-current {
             type int32;
             description
               "Current instantaneous queue depth";
           }
         }
         container interface-cos-summary {
           description
             "Summary of forwarding class and queue information on an 
             interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
           leaf intf-cos-burst-size-for-ifl {
             type int32;
             description
               "Burst size for the logical interface";
           }
         }
         container interface-cos-short-summary {
           description
             "Summary of queue information on an interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
         }
         list queue-num-forwarding-class-name-map {
           key "queue-number";
           leaf queue-number {
             type uint32;
             description
               "Queue number";
           }
           leaf forwarding-class-name {
             type string;
             description
               "Forwarding class name associated with queue";
           }
         }
       }
       container forwarding-class-counters {
         description
           "Forwarding-class counter statistics";
         leaf forwarding-class-counters-error-message {
           type string;
           description
             "Forwarding-class statistics not available for this interface";
         }
         container ipv4-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container ipv6-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container mpls-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container layer2-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container other-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container protocol-aggregate-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container forwarding-class-statistics {
           container protocol-aggregate-forwarding-class-counters {
           }
           container ipv4-forwarding-class-counters {
           }
           container ipv6-forwarding-class-counters {
           }
           container mpls-forwarding-class-counters {
           }
           container layer2-forwarding-class-counters {
           }
           container other-forwarding-class-counters {
           }
         }
         container forwarding-class-accounting-parameters {
           leaf forwarding-class-accounting-for-protocol {
             type string;
           }
           leaf forwarding-class-accounting-for-traffic-direction {
             type string;
           }
           leaf forwarding-class-accounting-for-traffic-type {
             type string;
           }
           leaf forwarding-class-accounting-overhead-bytes {
             type uint32;
           }
         }
         container per-forwarding-class-counters {
           leaf fc_name_header {
             type string;
           }
           leaf forwarding-class-name {
             type string;
             description
               "Forwarding class name associated with queue";
           }
           leaf fc-input-bytes {
             type int32;
           }
           leaf fc-input-bytes-rate {
             type int32;
             description
               "Input bytes rate";
           }
           leaf fc-output-bytes {
             type int32;
           }
           leaf fc-output-bytes-rate {
             type int32;
             description
               "Output bytes rate";
           }
           leaf fc-input-packets {
             type int32;
           }
           leaf fc-input-packets-rate {
             type int32;
             description
               "Input packets rate";
           }
           leaf fc-output-packets {
             type int32;
           }
           leaf fc-output-packets-rate {
             type int32;
             description
               "Output packets rate";
           }
           leaf input-unicast-bytes {
             type int32;
           }
           leaf output-unicast-bytes {
             type int32;
           }
           leaf input-unicast-packets {
             type int32;
           }
           leaf output-unicast-packets {
             type int32;
           }
           leaf input-multicast-bytes {
             type int32;
           }
           leaf output-multicast-bytes {
             type int32;
           }
           leaf input-multicast-packets {
             type int32;
           }
           leaf output-multicast-packets {
             type int32;
           }
         }
       }
       container multilink-bundle-options {
         leaf filler-packet-interval {
           type int32;
         }
       }
       container multilink-traffic-statistics {
         container bundle {
         }
         container class {
           description
             "Multilink class traffic statistics";
         }
         container multilink-detail-statistics {
           container bundle-detail {
           }
           container class-detail {
           }
         }
         container crtp {
           container crtp-sessions {
             leaf input-frames {
               type int32;
             }
             leaf output-frames {
               type int32;
             }
           }
           list crtp-statistics {
             key "name";
             leaf name {
               type string;
               description
                 "Name of this item";
             }
             leaf input-frames {
               type int32;
             }
             leaf input-fps {
               type int32;
             }
             leaf input-bytes {
               type int32;
             }
             leaf input-bps {
               type int32;
             }
             leaf output-frames {
               type int32;
             }
             leaf output-fps {
               type int32;
             }
             leaf output-bytes {
               type int32;
             }
             leaf output-bps {
               type int32;
             }
           }
         }
       }
       container traffic-statistics {
         leaf input-bps {
           type int32;
         }
         leaf input-pps {
           type int32;
         }
         leaf output-bps {
           type int32;
         }
         leaf output-pps {
           type int32;
         }
         leaf input-packets {
           type uint64;
         }
         leaf output-packets {
           type uint64;
         }
         container ipv4-traffic-statistics {
           leaf input-bps {
             type int32;
           }
           leaf output-bps {
             type int32;
           }
           leaf input-pps {
             type int32;
           }
           leaf output-pps {
             type int32;
           }
           leaf input-bytes {
             type int32;
           }
           leaf output-bytes {
             type int32;
           }
           leaf input-packets {
             type uint64;
           }
           leaf output-packets {
             type uint64;
           }
         }
         leaf input-bytes {
           type int32;
         }
         leaf output-bytes {
           type int32;
         }
         container ipv6-transit-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-traffic-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-total-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
       }
       container multicast-statistics {
         description
           "Multicast statistics for interface";
         leaf multicast-statistics-header {
           type empty;
         }
         container ipv4-multicast-statistics {
           description
             "IPV4 multicast statistics for interface";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-multicast-statistics {
           description
             "IPV6 multicast statistics for interface";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
       }
       container ingress-traffic-statistics {
         description
           "Traffic statistics at ingress before entering Packet Forwarding 
           Engine";
         leaf input-bps {
           type int32;
         }
         leaf input-pps {
           type int32;
         }
         leaf input-drop-bps {
           type int32;
           description
             "Drop rate at ingress in bits per second ";
         }
         leaf input-drop-pps {
           type int32;
           description
             "Drop rate at ingress in packets per second ";
         }
         leaf input-bytes {
           type int32;
         }
         leaf input-packets {
           type uint64;
         }
         leaf input-drop-bytes {
           type int32;
           description
             "Drop statistics at ingress in bytes";
         }
         leaf input-drop-packets {
           type int32;
           description
             "Drop statistics at ingress in packets";
         }
       }
       container local-traffic-statistics {
         description
           "Statistics for locally originated traffic";
       }
       container transit-traffic-statistics {
         description
           "Statistics for traffic passing through the Packet Forwarding 
           Engine";
       }
       container layer3-statistics {
       }
       container keepalive-statistics {
         description
           "Keepalive statistics for this interface";
         leaf keepalive-lmi-descriptor {
           type string;
         }
         leaf keepalive-input-count {
           type int32;
         }
         leaf keepalive-input-time {
           type string;
         }
         leaf keepalive-output-count {
           type int32;
         }
         leaf keepalive-output-time {
           type string;
         }
       }
       container virtual-circuit-information {
         description
           "Operational information and statistics for a virtual circuit";
         container traffic-statistics {
           leaf input-bps {
             type int32;
           }
           leaf input-pps {
             type int32;
           }
           leaf output-bps {
             type int32;
           }
           leaf output-pps {
             type int32;
           }
           leaf input-packets {
             type uint64;
           }
           leaf output-packets {
             type uint64;
           }
           container ipv4-traffic-statistics {
             leaf input-bps {
               type int32;
             }
             leaf output-bps {
               type int32;
             }
             leaf input-pps {
               type int32;
             }
             leaf output-pps {
               type int32;
             }
             leaf input-bytes {
               type int32;
             }
             leaf output-bytes {
               type int32;
             }
             leaf input-packets {
               type uint64;
             }
             leaf output-packets {
               type uint64;
             }
           }
           leaf input-bytes {
             type int32;
           }
           leaf output-bytes {
             type int32;
           }
           container ipv6-transit-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-traffic-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-total-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
         }
         container atm-cos-information {
           leaf vc-cos-mode {
             type string;
             description
               "Virtual circuit CoS scheduling mode";
           }
           list atm-cos-queue {
             container atm-cos-queue-parameters {
               leaf cos-forwarding-class-name {
                 type string;
                 description
                   "Forwarding class name associated with queue";
               }
               leaf cos-queue-number {
                 type int32;
                 description
                   "Queue number";
               }
               leaf scheduling-priority {
                 type string;
                 description
                   "Scheduling priority";
               }
               leaf transmit-weight-cells {
                 type int32;
                 description
                   "Weight to apply to scheduling as number of cells";
               }
               leaf transmit-weight-percent {
                 type int32;
                 description
                   "Weight to apply to scheduling as fill percentage";
               }
               leaf epd-threshold {
                 type int32;
                 description
                   "Early packet drop threshold";
               }
               leaf epd-threshold-plp0 {
                 type int32;
                 description
                   "Early packet drop threshold for PLP 0";
               }
               leaf epd-threshold-plp1 {
                 type int32;
                 description
                   "Early packet drop threshold for PLP 1";
               }
               container linear-red-drop-profile {
                 leaf queue-depth {
                   type int32;
                   description
                     "Maximum queue depth";
                 }
                 leaf low-red {
                   type int32;
                   description
                     "Fill level percentage when linear RED is applied for 
                     low PLP";
                 }
                 leaf high-red {
                   type int32;
                   description
                     "Fill level percentage when linear RED is applied for 
                     high PLP";
                 }
                 leaf max-low-red {
                   type int32;
                   description
                     "Fill level percentage with 100% packet drop for low 
                     PLP";
                 }
                 leaf max-high-red {
                   type int32;
                   description
                     "Fill level percentage with 100% packet drop for high 
                     PLP";
                 }
               }
             }
             container atm-cos-queue-statistics {
               leaf atm-output-bytes {
                 type int32;
               }
               leaf atm-output-packets {
                 type int32;
               }
               leaf atm-packet-drops {
                 type int32;
               }
             }
             container atm-cos-plp-statistics {
               leaf atm-plp0-output-bytes {
                 type int32;
               }
               leaf atm-plp1-output-bytes {
                 type int32;
               }
               leaf atm-plp0-output-packets {
                 type int32;
               }
               leaf atm-plp1-output-packets {
                 type int32;
               }
               leaf atm-plp0-byte-drops {
                 type int32;
               }
               leaf atm-plp1-byte-drops {
                 type int32;
               }
               leaf atm-plp0-packet-drops {
                 type int32;
               }
               leaf atm-plp1-packet-drops {
                 type int32;
               }
             }
           }
         }
       }
       container allowed-host-inbound-traffic {
         description
           "List of allowed system services and protocols";
         leaf inbound-all-protocols {
           type empty;
           description
             "All protocols";
         }
         leaf inbound-any-service {
           type empty;
           description
             "Any service";
         }
         leaf inbound-bootp {
           type empty;
           description
             "Bootp and dhcp relay-agent service";
         }
         leaf inbound-bfd {
           type empty;
           description
             "Bidirectional Forwarding Detection";
         }
         leaf inbound-bgp {
           type empty;
           description
             "Border Gateway Protocol";
         }
         leaf inbound-dns {
           type empty;
           description
             "DNS and DNS-proxy service";
         }
         leaf inbound-dvmrp {
           type empty;
           description
             "Distance Vector Multicast Routing Protocol";
         }
         leaf inbound-igmp {
           type empty;
           description
             "Internet Group Management Protocol";
         }
         leaf inbound-ldp {
           type empty;
           description
             "Label Distribution Protocol";
         }
         leaf inbound-msdp {
           type empty;
           description
             "Multicast Source Discovery Protocol";
         }
         leaf inbound-nhrp {
           type empty;
           description
             "Next Hop Resolution Protocol";
         }
         leaf inbound-ospf {
           type empty;
           description
             "Open Shortest Path First";
         }
         leaf inbound-ospf3 {
           type empty;
           description
             "Open Shortest Path First version 3";
         }
         leaf inbound-pgm {
           type empty;
           description
             "Pragmatic General Multicast";
         }
         leaf inbound-pim {
           type empty;
           description
             "Protocol Independent Multicast";
         }
         leaf inbound-rip {
           type empty;
           description
             "Routing Information Protocol";
         }
         leaf inbound-ripng {
           type empty;
           description
             "Routing Information Protocol next generation";
         }
         leaf inbound-router-discovery {
           type empty;
           description
             "Router Discovery";
         }
         leaf inbound-rsvp {
           type empty;
           description
             "Resource Reservation Protocol";
         }
         leaf inbound-sap {
           type empty;
           description
             "Session Announcement Protocol";
         }
         leaf inbound-vrrp {
           type empty;
           description
             "Virtual Router Redundancy Protocol";
         }
         leaf inbound-all-services {
           type empty;
           description
             "All system services";
         }
         leaf inbound-dhcp {
           type empty;
           description
             "Dynamic Host Configuration Protocol";
         }
         leaf inbound-finger {
           type empty;
           description
             "Finger service";
         }
         leaf inbound-ftp {
           type empty;
           description
             "File Transfer Protocol";
         }
         leaf inbound-tftp {
           type empty;
           description
             "Trivial File Transfer Protocol";
         }
         leaf ident-reset {
           type empty;
           description
             "Send back TCP RST to IDENT request for port 113";
         }
         leaf inbound-http {
           type empty;
           description
             "Web management service using HTTP";
         }
         leaf inbound-https {
           type empty;
           description
             "Web management service using HTTP secured by SSL";
         }
         leaf inbound-ike {
           type empty;
           description
             "Internet Key Exchange";
         }
         leaf inbound-netconf {
           type empty;
           description
             "NETCONF service";
         }
         leaf inbound-ping {
           type empty;
           description
             "Internet Control Message Protocol echo requests";
         }
         leaf inbound-reverse-telnet {
           type empty;
           description
             "Reverse telnet service";
         }
         leaf inbound-reverse-ssh {
           type empty;
           description
             "Reverse SSH service";
         }
         leaf inbound-rlogin {
           type empty;
           description
             "Rlogin service";
         }
         leaf inbound-rpm {
           type empty;
           description
             "Real-time performance monitoring";
         }
         leaf inbound-rsh {
           type empty;
           description
             "Rsh service";
         }
         leaf inbound-snmp {
           type empty;
           description
             "Simple Network Management Protocol service";
         }
         leaf inbound-snmp-trap {
           type empty;
           description
             "Simple Network Management Protocol traps";
         }
         leaf inbound-ssh {
           type empty;
           description
             "SSH service";
         }
         leaf inbound-telnet {
           type empty;
           description
             "Telnet service";
         }
         leaf inbound-traceroute {
           type empty;
           description
             "Traceroute service";
         }
         leaf inbound-xnm-clear-text {
           type empty;
           description
             "JUNOScript API for unencrypted traffic over TCP";
         }
         leaf inbound-xnm-ssl {
           type empty;
           description
             "JUNOScript API service over SSL";
         }
         leaf inbound-lsping {
           type empty;
           description
             "Label Switched Path ping service";
         }
         leaf inbound-lsselfping {
           type empty;
           description
             "Label Switched Path self ping service";
         }
         leaf inbound-ntp {
           type empty;
           description
             "Network Time Protocol service";
         }
         leaf inbound-sip {
           type empty;
           description
             "Session Initiation Protocol service";
         }
         leaf inbound-dhcpv6 {
           type empty;
           description
             "Dynamic Host Configuration Protocol for IPv6 service";
         }
         leaf inbound-r2cp {
           type empty;
           description
             "Radio Router Control Protocol service";
         }
         leaf inbound-webapi-clear-text {
           type empty;
           description
             "Webapi service using http";
         }
         leaf inbound-webapi-ssl {
           type empty;
           description
             "Webapi service using HTTP secured by SSL";
         }
         leaf inbound-tcp-encap {
           type empty;
           description
             "Tcp encapsulation service";
         }
         leaf inbound-sdwan-appqoe {
           type empty;
           description
             "Sdwan Appqoe service";
         }
         leaf inbound-high-availability {
           type empty;
           description
             "High Availability  service";
         }
       }
       list policer-information {
         description
           "Interface policer information";
         leaf policer-family {
           type string;
           description
             "Protocol family of the policer";
         }
         leaf policer-input {
           type string;
           description
             "Name of the input policer";
         }
         leaf policer-output {
           type string;
           description
             "Name of the output policer";
         }
       }
       list address-family {
         container pppoe-underlying-information {
           description
             "PPPoE Underlying information";
           list pppoe-underlying-interface {
             leaf dynamic-profile {
               type string;
               description
                 "Dynamic Profile name";
             }
             leaf service-name-table {
               type string;
               description
                 "Name of Service Name Table";
             }
             leaf max-sessions {
               type int32;
               description
                 "Maximum number of PPPoE sessions";
             }
             leaf max-sessions-vsa-ignore {
               type string;
               description
                 "Ignore max-sessions VSA";
             }
             leaf duplicate-protection {
               type string;
               description
                 "Duplicate protection mode";
             }
             leaf short-cycle-protection {
               type string;
               description
                 "Short cycle protection mode";
             }
             leaf direct-connect {
               type string;
               description
                 "Direct connect mode";
             }
             leaf ac-name {
               type string;
               description
                 "Access Concentrator name";
             }
             leaf underlying-interface-name {
               type string;
               description
                 "Underlying interface name";
             }
             leaf underlying-interface-index {
               type string;
               description
                 "Underlying interface index";
             }
             leaf encapsulation-type-identifier {
               type string;
               description
                 "Encapsulation type identifier";
             }
             leaf state {
               type string;
               description
                 "State";
             }
             leaf active-sessions {
               type int32;
               description
                 "Number of active PPPoE sessions";
             }
             leaf aci-autosensing {
               type string;
               description
                 "ACI VLAN Autosensing mode";
             }
             leaf line-identity-autosensing {
               type string;
               description
                 "Line Identity Autosensing mode";
             }
           }
         }
         list interface-address {
         }
         container destination-class-statistics {
           description
             "Destination class usage (DCU) statistics";
         }
         container source-class-statistics {
           description
             "Source class usage (SCU) statistics";
         }
         list local-bias-information {
           leaf local-bias-vtep-ifl-name {
             type string;
             description
               "Interface name";
           }
           leaf local-bias-vtep-ifl-index {
             type uint32;
             description
               "Interface index";
           }
           leaf local-bias-vtep-address {
             type string;
             description
               "Protocol address of the connection";
           }
         }
         leaf ft-iff-dest-port {
           type uint32;
           description
             "Destination UDP port to be used for this family";
         }
       }
       list bridge-iff-properties {
         description
           "Information about Ethernet-switching address family";
       }
       container l2circuit-info {
         leaf out-of-sequence {
           type int32;
         }
         leaf denied-packets {
           type int32;
         }
         leaf cell-bundle-size {
           type int32;
         }
         leaf cell-bundle-timeout {
           type int32;
         }
         leaf cell-timeout-count {
           type int32;
         }
       }
       container media-information {
         description
           "Information about media alarms";
         leaf media-type {
           type string;
           description
             "Type of media this information is for";
         }
         list media-alarm {
           leaf media-alarm-name {
             type string;
           }
           leaf media-alarm-count {
             type int32;
           }
           leaf media-alarm-seconds {
             type int32;
           }
           leaf media-alarm-state {
             type string;
           }
           leaf ce-counter-name {
             type string;
             description
               "Circuit Emulation counter information";
           }
           leaf ce-counter-packets {
             type int32;
             description
               "Circuit Emulation number of packets";
           }
           leaf ce-counter-bytes {
             type int32;
             description
               "Circuit Emulation number of bytes";
           }
           leaf ce-counter-count {
             type int32;
             description
               "Circuit Emulation number of event occurrences";
           }
         }
         leaf ds1-timeslots {
           type string;
         }
         leaf ds1-line-encoding {
           type string;
         }
         leaf ds1-byte-encoding {
           type string;
         }
         leaf ds1-data-inversion {
           type string;
         }
         leaf idle-cycle-flag {
           type string;
         }
         leaf start-end-flag {
           type string;
         }
         leaf ds0-byte-encoding {
           type string;
         }
         leaf ds0-data-inversion {
           type string;
         }
         leaf e3-data-inversion {
           type string;
         }
         leaf ds1-buildout {
           type string;
           description
             "Number of feet";
         }
       }
       container macsec-statistics {
         description
           "MACSec Statistics ";
         leaf macsec-tx-sc-protected {
           type int32;
           description
             "Protected Secure Channel MACSec packets transmitted";
         }
         leaf macsec-tx-sc-encrypted {
           type int32;
           description
             "Encrypted Secure Channel MACSec packets transmitted";
         }
         leaf macsec-tx-sc-protectedbytes {
           type int32;
           description
             "Protected Secure Channel MACSec bytes transmitted";
         }
         leaf macsec-tx-sc-encryptedbytes {
           type int32;
           description
             "Encrypted Secure Channel MACSec bytes transmitted";
         }
         leaf macsec-rx-sc-ok {
           type int32;
           description
             "OK Secure Association MACSec packets received";
         }
         leaf macsec-rx-sc-validatedbytes {
           type int32;
           description
             "Validated Secure Association MACSec bytes received";
         }
         leaf macsec-rx-sc-decryptedbytes {
           type int32;
           description
             "Validated Secure Association MACSec bytes received";
         }
         leaf interface-name {
           type string;
           description
             "Class-of-service interface name";
         }
         leaf encrypted-packets {
           type uint64;
           description
             "Macsec encrypted packets sent";
         }
         leaf encrypted-bytes {
           type uint64;
           description
             "Macsec encrypted bytes sent";
         }
         leaf protected-packets {
           type uint64;
           description
             "Macsec packets sent with only integrity protection";
         }
         leaf protected-bytes {
           type uint64;
           description
             "Macsec bytes sent with only integrity protection";
         }
         leaf ok-packets {
           type uint64;
           description
             "Macsec packets accepted";
         }
         leaf decrypted-bytes {
           type uint64;
           description
             "Macsec received bytes decrypted";
         }
         leaf decrypted-packets {
           type uint64;
           description
             "Macsec received packets decrypted";
         }
         leaf validated-packets {
           type uint64;
           description
             "Macsec received packets validated";
         }
         leaf validated-bytes {
           type uint64;
           description
             "Macsec received bytes validated";
         }
         leaf untagged-packets {
           type uint64;
           description
             "Macsec untagged packets";
         }
         leaf toolong-packets {
           type uint64;
           description
             "Macsec too long packets transmitted on a secure channel";
         }
         leaf control-packets {
           type uint64;
           description
             "Macsec control packets received on a secure channel";
         }
         leaf tagged-miss-packets {
           type uint64;
           description
             "Macsec tagged miss packets received on a secure channel";
         }
         leaf untagged-hit-packets {
           type uint64;
           description
             "Macsec untagged hit packets received on a secure channel";
         }
         leaf notag-packets {
           type uint64;
           description
             "Macsec no tag packets received on a secure channel";
         }
         leaf badtag-packets {
           type uint64;
           description
             "Macsec bad tag packets received on a secure channel";
         }
         leaf unknown-sci-packets {
           type uint64;
           description
             "Macsec unknown sci packets received on a secure channel";
         }
         leaf no-sci-packets {
           type uint64;
           description
             "Macsec no sci packets received on a secure channel";
         }
         leaf control-pass-packets {
           type uint64;
           description
             "Macsec allowed control packets received on a secure channel";
         }
         leaf uncontrol-pass-packets {
           type uint64;
           description
             "Macsec allowed uncontrol packets received on a secure channel";
         }
         leaf control-fail-packets {
           type uint64;
           description
             "Macsec dropped control packets received on a secure channel";
         }
         leaf uncontrol-fail-packets {
           type uint64;
           description
             "Macsec dropped uncontrol packets received on a secure channel";
         }
         leaf hit-dropped-packets {
           type uint64;
           description
             "Macsec hit dropped packets received on a security channel";
         }
         leaf notusing-sa-packets {
           type uint64;
           description
             "Macsec not using sa packets received on a security channel";
         }
         leaf unused-sa-packets {
           type uint64;
           description
             "Macsec unused sa packets received on a security channel";
         }
         leaf late-packets {
           type uint64;
           description
             "Macsec late packets dropped on a security channel";
         }
         leaf delayed-packets {
           type uint64;
           description
             "Macsec delayed packets accepted on a security channel";
         }
         leaf unchecked-packets {
           type uint64;
           description
             "Macsec unchecked packets accepted on a security channel";
         }
         leaf notvalid-packets {
           type uint64;
           description
             "Macsec not valid packets dropped on a security channel";
         }
         leaf invalid-packets {
           type uint64;
           description
             "Macsec invalid packets accepted on a security channel";
         }
         list secure-channel-sent {
           leaf encrypted-packets {
             type uint64;
             description
               "Macsec encrypted packets sent";
           }
           leaf encrypted-bytes {
             type uint64;
             description
               "Macsec encrypted bytes sent";
           }
           leaf protected-packets {
             type uint64;
             description
               "Macsec packets sent with only integrity protection";
           }
           leaf protected-bytes {
             type uint64;
             description
               "Macsec bytes sent with only integrity protection";
           }
         }
         list secure-association-sent {
           leaf encrypted-packets {
             type uint64;
             description
               "Macsec encrypted packets sent";
           }
           leaf encrypted-bytes {
             type uint64;
             description
               "Macsec encrypted bytes sent";
           }
           leaf protected-packets {
             type uint64;
             description
               "Macsec packets sent with only integrity protection";
           }
           leaf protected-bytes {
             type uint64;
             description
               "Macsec bytes sent with only integrity protection";
           }
         }
         list secure-channel-received {
           leaf ok-packets {
             type uint64;
             description
               "Macsec packets accepted";
           }
           leaf decrypted-packets {
             type uint64;
             description
               "Macsec received packets decrypted";
           }
           leaf decrypted-bytes {
             type uint64;
             description
               "Macsec received bytes decrypted";
           }
           leaf validated-packets {
             type uint64;
             description
               "Macsec received packets validated";
           }
           leaf validated-bytes {
             type uint64;
             description
               "Macsec received bytes validated";
           }
         }
         list secure-association-received {
           leaf ok-packets {
             type uint64;
             description
               "Macsec packets accepted";
           }
           leaf decrypted-packets {
             type uint64;
             description
               "Macsec received packets decrypted";
           }
           leaf decrypted-bytes {
             type uint64;
             description
               "Macsec received bytes decrypted";
           }
           leaf validated-packets {
             type uint64;
             description
               "Macsec received packets validated";
           }
           leaf validated-bytes {
             type uint64;
             description
               "Macsec received bytes validated";
           }
         }
         list macsec-error-information {
           list secure-channel-sent-errors {
             leaf untagged-packets {
               type uint64;
               description
                 "Macsec untagged packets";
             }
             leaf toolong-packets {
               type uint64;
               description
                 "Macsec too long packets transmitted on a secure channel";
             }
           }
           list secure-channel-received-errors {
             leaf control-packets {
               type uint64;
               description
                 "Macsec control packets received on a secure channel";
             }
             leaf tagged-miss-packets {
               type uint64;
               description
                 "Macsec tagged miss packets received on a secure channel";
             }
             leaf untagged-hit-packets {
               type uint64;
               description
                 "Macsec untagged hit packets received on a secure channel";
             }
             leaf untagged-packets {
               type uint64;
               description
                 "Macsec untagged packets";
             }
             leaf notag-packets {
               type uint64;
               description
                 "Macsec no tag packets received on a secure channel";
             }
             leaf badtag-packets {
               type uint64;
               description
                 "Macsec bad tag packets received on a secure channel";
             }
             leaf unknown-sci-packets {
               type uint64;
               description
                 "Macsec unknown sci packets received on a secure channel";
             }
             leaf no-sci-packets {
               type uint64;
               description
                 "Macsec no sci packets received on a secure channel";
             }
             leaf control-pass-packets {
               type uint64;
               description
                 "Macsec allowed control packets received on a secure 
                 channel";
             }
             leaf control-fail-packets {
               type uint64;
               description
                 "Macsec dropped control packets received on a secure 
                 channel";
             }
             leaf uncontrol-pass-packets {
               type uint64;
               description
                 "Macsec allowed uncontrol packets received on a secure 
                 channel";
             }
             leaf uncontrol-fail-packets {
               type uint64;
               description
                 "Macsec dropped uncontrol packets received on a secure 
                 channel";
             }
           }
           list secure-channel-received-extended {
             leaf hit-dropped-packets {
               type uint64;
               description
                 "Macsec hit dropped packets received on a security channel";
             }
             leaf invalid-packets {
               type uint64;
               description
                 "Macsec invalid packets accepted on a security channel";
             }
             leaf late-packets {
               type uint64;
               description
                 "Macsec late packets dropped on a security channel";
             }
             leaf delayed-packets {
               type uint64;
               description
                 "Macsec delayed packets accepted on a security channel";
             }
             leaf unchecked-packets {
               type uint64;
               description
                 "Macsec unchecked packets accepted on a security channel";
             }
             leaf notvalid-packets {
               type uint64;
               description
                 "Macsec not valid packets dropped on a security channel";
             }
             leaf notusing-sa-packets {
               type uint64;
               description
                 "Macsec not using sa packets received on a security channel";
             }
             leaf unused-sa-packets {
               type uint64;
               description
                 "Macsec unused sa packets received on a security channel";
             }
             leaf untagged-hit-packets {
               type uint64;
               description
                 "Macsec untagged hit packets received on a secure channel";
             }
           }
         }
       }
       container security-input-flow-statistics {
         description
           "Flow input statistics for the interface";
         leaf flow-input-self-packets {
           type int32;
           description
             "Input Self packets";
         }
         leaf flow-input-icmp-packets {
           type int32;
           description
             "Input ICMP packets";
         }
         leaf flow-input-vpn-packets {
           type int32;
           description
             "Input VPN packets";
         }
         leaf flow-input-multicast-packets {
           type int32;
           description
             "Input multicast packets";
         }
         leaf flow-input-policy-bytes {
           type int32;
           description
             "Input policy bytes";
         }
         leaf flow-input-connections {
           type int32;
           description
             "Input connections";
         }
       }
       container security-output-flow-statistics {
         description
           "Flow output statistics for the interface";
         leaf flow-output-multicast-packets {
           type int32;
           description
             "Output multicast packets";
         }
         leaf flow-output-policy-bytes {
           type int32;
           description
             "Output bytes permitted by policy";
         }
       }
       container security-error-flow-statistics {
         description
           "Flow error statistics for the interface";
         leaf flow-error-policy-denied {
           type int32;
           description
             "Policy denied";
         }
         leaf flow-error-no-gate-parent {
           type int32;
           description
             "No parent for gate";
         }
         leaf flow-error-syn-protection {
           type int32;
           description
             "Syn-attack protection";
         }
         leaf flow-error-incoming-nat {
           type int32;
           description
             "Incoming NAT errors";
         }
         leaf flow-error-no-tunnel {
           type int32;
           description
             "No tunnel found";
         }
         leaf flow-error-no-more-session {
           type int32;
           description
             "No more sessions";
         }
         leaf flow-error-invalid-zone {
           type int32;
           description
             "Invalid zone received packet";
         }
         leaf flow-error-user-authentication {
           type int32;
           description
             "User authentication errors";
         }
         leaf flow-error-multiple-auth {
           type int32;
           description
             "Multiple user authentications";
         }
         leaf flow-error-multiple-incoming-nat {
           type int32;
           description
             "Multiple incoming NAT";
         }
         leaf flow-error-address-spoofing {
           type int32;
           description
             "Address spoofing";
         }
         leaf flow-error-null-zone {
           type int32;
           description
             "No zone or NULL zone binding";
         }
         leaf flow-error-no-nat-gate {
           type int32;
           description
             "No NAT gate";
         }
         leaf flow-error-no-minor-session {
           type int32;
           description
             "No minor session";
         }
         leaf flow-error-no-session-gate {
           type int32;
           description
             "No session for a gate";
         }
         leaf flow-error-seq-outside-window {
           type int32;
           description
             "TCP sequence number out of window";
         }
         leaf flow-error-no-route-present {
           type int32;
           description
             "No route present";
         }
         leaf flow-error-authentication-failed {
           type int32;
           description
             "Authentication failed";
         }
         leaf flow-error-security-association-missing {
           type int32;
           description
             "Security association not active";
         }
         leaf flow-error-no-sa-for-spi {
           type int32;
           description
             "No SA for incoming SPI";
         }
         leaf flow-error-no-interest-self-packet {
           type int32;
           description
             "No one interested in self packets";
         }
       }
       container lag-traffic-statistics {
         container lag-multicast-statistics {
           leaf lag-multicast-statistics-header {
             type empty;
           }
           container lag-ipv4-multicast-statistics {
             leaf input-packets {
               type uint64;
             }
             leaf input-pps {
               type int32;
             }
             leaf input-bytes {
               type int32;
             }
             leaf input-bps {
               type int32;
             }
             leaf output-packets {
               type uint64;
             }
             leaf output-pps {
               type int32;
             }
             leaf output-bytes {
               type int32;
             }
             leaf output-bps {
               type int32;
             }
           }
           container lag-ipv6-multicast-statistics {
             leaf input-packets {
               type uint64;
             }
             leaf input-pps {
               type int32;
             }
             leaf input-bytes {
               type int32;
             }
             leaf input-bps {
               type int32;
             }
             leaf output-packets {
               type uint64;
             }
             leaf output-pps {
               type int32;
             }
             leaf output-bytes {
               type int32;
             }
             leaf output-bps {
               type int32;
             }
           }
         }
         list if-distribution-list-information {
         }
         container ifd-lag-traffic-statistics {
         }
       }
       container ifd-lag-traffic-statistics {
       }
       container layer2-input-policer-statistics {
         description
           "Layer 2 input policer statistics for interface";
         leaf policer-medium-low-frames {
           type int32;
           description
             "Number of loss priority medium low frames";
         }
         leaf policer-medium-low-bytes {
           type int32;
           description
             "Number of loss priority medium low bytes";
         }
         leaf policer-medium-low-rate {
           type int32;
           description
             "Rate of loss priority medium low pkts";
         }
       }
       container layer2-output-policer-statistics {
         description
           "Layer 2 output policer statistics for interface";
         leaf policer-medium-low-frames {
           type int32;
           description
             "Number of loss priority medium low frames";
         }
         leaf policer-medium-low-bytes {
           type int32;
           description
             "Number of loss priority medium low bytes";
         }
         leaf policer-medium-low-rate {
           type int32;
           description
             "Rate of loss priority medium low pkts";
         }
       }
       container mac-policer-information {
         container ether-policer-list {
         }
       }
       leaf vrfname {
         type string;
         description
           "Routing instance name";
       }
       leaf zonename {
         type string;
         description
           "Zone name";
       }
     }
   }
   grouping interface-port-profile-information-block {
     list physical-interface {
       key "name";
       description
         "Information about a single physical interface";
       leaf name {
         type string;
         description
           "Name of this item";
       }
       leaf speed {
         type string;
         description
           "Speed at which the interface is running";
       }
       leaf admin-status {
         type string;
         description
           "Desired state of the interface";
       }
       leaf oper-status {
         type string;
         description
           "Current operational state of the interface";
       }
       leaf esi-source-bmac {
         type jt:mac-addr;
         description
           "Ethernet segment source B-MAC for this interface";
       }
       leaf sonet-payload-pointer-curptr {
         type string;
         description
           "Value of the SONET/SDH payload pointer, derived from the H1 and 
           H2 overhead bytes";
       }
       leaf sonet-payload-pointer-ptrinc-count {
         type string;
         description
           "Number of times the value of the SONET/SDH payload pointer had 
           positive justification";
       }
       leaf sonet-payload-pointer-ptrdec-count {
         type string;
         description
           "Number of times the value of the SONET/SDH payload pointer had 
           negative justification";
       }
       leaf sonet-payload-pointer-newptr-ndf-count {
         type string;
         description
           "Number of times a new payload pointer was created with the New 
           Data Found flag set";
       }
       leaf link-partner-status {
         type string;
         description
           "Auto-negotiation status of link partner";
       }
       container optics-diagnostics {
         description
           "Optics diagnostics";
         leaf optic-diagnostics-not-available {
           type string;
           description
             "Optical diagnostics not supported by this transceiver";
         }
         leaf laser-bias-current-not-available {
           type string;
           description
             "Laser bias current measurement not available";
         }
         leaf soa-bias-current-not-available {
           type string;
           description
             "SOA bias current measurement not available";
         }
         leaf laser-tx-power-not-available {
           type string;
           description
             "Laser output power measurement not available";
         }
         leaf module-temperature-not-available {
           type string;
           description
             "Module temperature measurement not available";
         }
         leaf tx-module-temperature-not-available {
           type string;
           description
             "Tx module temperature measurement not available";
         }
         leaf rx-module-temperature-not-available {
           type string;
           description
             "Rx module temperature measurement not available";
         }
         leaf laser-rx-power-not-available {
           type string;
           description
             "Laser receiver optical power measurement not available";
         }
         leaf laser-tx-power-high-alarm-threshold-not-available {
           type string;
           description
             "Laser output power high alarm threshold not available";
         }
         leaf laser-tx-power-low-alarm-threshold-not-available {
           type string;
           description
             "Laser output power low alarm threshold not available";
         }
         leaf laser-tx-power-high-warning-threshold-not-available {
           type string;
           description
             "Laser output power high warning threshold not available";
         }
         leaf laser-tx-power-low-warning-threshold-not-available {
           type string;
           description
             "Laser output power low warning threshold not available";
         }
         leaf laser-bias-current-high-alarm-threshold-not-available {
           type string;
           description
             "Laser bias current high alarm threshold not available";
         }
         leaf laser-bias-current-low-alarm-threshold-not-available {
           type string;
           description
             "Laser bias current low alarm threshold not available";
         }
         leaf laser-bias-current-high-warning-threshold-not-available {
           type string;
           description
             "Laser bias current high warning threshold not available";
         }
         leaf laser-bias-current-low-warning-threshold-not-available {
           type string;
           description
             "Laser bias current low warning threshold not available";
         }
         leaf laser-bias-current {
           type string;
           description
             "Laser bias current (milliamperes)";
         }
         leaf soa-bias-current {
           type string;
           description
             "SOA bias current (milliamperes)";
         }
         leaf laser-output-power {
           type string;
           description
             "Laser output power (milliwatts)";
         }
         leaf laser-output-power-dbm {
           type string;
           description
             "Laser output power (dBm)";
         }
         leaf module-temperature {
           type string;
           description
             "Module temperature";
         }
         leaf tx-module-temperature {
           type string;
           description
             "Tx module temperature";
         }
         leaf rx-module-temperature {
           type string;
           description
             "Rx module temperature";
         }
         leaf host-id {
           type uint32;
           description
             "Host code of this interface";
         }
         leaf media-id {
           type uint32;
           description
             "Media code of this interface";
         }
         leaf host-code-desc {
           type string;
           description
             "Current optics host code";
         }
         leaf media-code-desc {
           type string;
           description
             "Current optics media code";
         }
         leaf module-voltage {
           type string;
           description
             "Module voltage";
         }
         leaf module-max-power {
           type string;
           description
             "Module max power";
         }
         leaf corrected-error-ratio {
           type string;
           description
             "Corrected error ratio";
         }
         leaf uncorrected-words-ratio {
           type string;
           description
             "Uncorrected words ratio";
         }
         leaf tx-module-voltage {
           type string;
           description
             "Tx module voltage";
         }
         leaf rx-module-voltage {
           type string;
           description
             "Rx module voltage";
         }
         leaf rx-signal-avg-optical-power {
           type string;
           description
             "Receiver signal average power (milliwatts)";
         }
         leaf rx-signal-avg-optical-power-dbm {
           type string;
           description
             "Receiver signal average power (dBm)";
         }
         leaf laser-rx-optical-power {
           type string;
           description
             "Laser receiver optical power (milliwatts)";
         }
         leaf laser-rx-optical-power-dbm {
           type string;
           description
             "Laser receiver optical power (dBm)";
         }
         leaf wavelength-channel {
           type string;
           description
             "Wavelength channel number set";
         }
         leaf wavelength-setpoint {
           type string;
           description
             "Wavelength point set";
         }
         leaf tx-dither {
           type string;
           description
             "Tx dither status";
         }
         leaf frequency-error {
           type string;
           description
             "Frequency error value";
         }
         leaf wavelength-error {
           type string;
           description
             "Wavelength error value";
         }
         leaf laser-bias-current-high-alarm {
           type string;
           description
             "Laser bias current high alarm";
         }
         leaf laser-bias-current-low-alarm {
           type string;
           description
             "Laser bias current low alarm";
         }
         leaf laser-bias-current-high-warn {
           type string;
           description
             "Laser bias current high warning";
         }
         leaf laser-bias-current-low-warn {
           type string;
           description
             "Laser bias current low warning";
         }
         leaf soa-bias-current-high-alarm {
           type string;
           description
             "SOA bias current high alarm";
         }
         leaf soa-bias-current-low-alarm {
           type string;
           description
             "SOA bias current low alarm";
         }
         leaf soa-bias-current-high-warn {
           type string;
           description
             "SOA bias current high warning";
         }
         leaf soa-bias-current-low-warn {
           type string;
           description
             "SOA bias current low warning";
         }
         leaf laser-tx-power-high-alarm {
           type string;
           description
             "Laser output power high alarm";
         }
         leaf laser-tx-power-low-alarm {
           type string;
           description
             "Laser output power low alarm";
         }
         leaf laser-tx-power-high-warn {
           type string;
           description
             "Laser output power high warning";
         }
         leaf laser-tx-power-low-warn {
           type string;
           description
             "Laser output power low warning";
         }
         leaf tx-power-high-alarm {
           type string;
           description
             "Tx power high alarm";
         }
         leaf tx-power-low-alarm {
           type string;
           description
             "Tx power low alarm";
         }
         leaf tx-power-high-warn {
           type string;
           description
             "Tx power high warning";
         }
         leaf tx-power-low-warn {
           type string;
           description
             "Tx power low warning";
         }
         leaf module-temperature-high-alarm {
           type string;
           description
             "Module temperature high alarm";
         }
         leaf module-temperature-low-alarm {
           type string;
           description
             "Module temperature low alarm";
         }
         leaf module-temperature-high-warn {
           type string;
           description
             "Module temperature high warning";
         }
         leaf module-temperature-low-warn {
           type string;
           description
             "Module temperature low warning";
         }
         leaf tx-module-temperature-high-alarm {
           type string;
           description
             "Tx module temperature high alarm";
         }
         leaf tx-module-temperature-low-alarm {
           type string;
           description
             "Tx module temperature low alarm";
         }
         leaf rx-module-temperature-high-alarm {
           type string;
           description
             "Rx module temperature high alarm";
         }
         leaf rx-module-temperature-low-alarm {
           type string;
           description
             "Rx module temperature low alarm";
         }
         leaf module-voltage-high-alarm {
           type string;
           description
             "Module voltage high alarm";
         }
         leaf module-voltage-low-alarm {
           type string;
           description
             "Module voltage low alarm";
         }
         leaf module-voltage-high-warn {
           type string;
           description
             "Module voltage high warning";
         }
         leaf module-voltage-low-warn {
           type string;
           description
             "Module voltage low warning";
         }
         leaf tx-module-voltage-high-alarm {
           type string;
           description
             "Tx module voltage high alarm";
         }
         leaf tx-module-voltage-low-alarm {
           type string;
           description
             "Tx module voltage low alarm";
         }
         leaf rx-module-voltage-high-alarm {
           type string;
           description
             "Rx module voltage high alarm";
         }
         leaf rx-module-voltage-low-alarm {
           type string;
           description
             "Rx module voltage low alarm";
         }
         leaf laser-rx-power-high-alarm {
           type string;
           description
             "Laser receiver power high alarm";
         }
         leaf laser-rx-power-low-alarm {
           type string;
           description
             "Laser receiver power low alarm";
         }
         leaf laser-rx-power-high-warn {
           type string;
           description
             "Laser receiver power high warning";
         }
         leaf laser-rx-power-low-warn {
           type string;
           description
             "Laser receiver power low warning";
         }
         leaf rx-power-high-alarm {
           type string;
           description
             "Receiver power high alarm";
         }
         leaf rx-power-low-alarm {
           type string;
           description
             "Receiver power low alarm";
         }
         leaf rx-power-high-warn {
           type string;
           description
             "Receiver power high warning";
         }
         leaf rx-power-low-warn {
           type string;
           description
             "Receiver power low warning";
         }
         leaf laser-end-of-life-alarm {
           type string;
           description
             "Laser end-of-life alarm";
         }
         leaf laser-wavelength-alarm {
           type string;
           description
             "Laser wavelength alarm";
         }
         leaf laser-bias-current-alarm {
           type string;
           description
             "Laser bias current alarm";
         }
         leaf module-temperature-alarm {
           type string;
           description
             "Module temperature alarm";
         }
         leaf laser-power-alarm {
           type string;
           description
             "Laser power alarm";
         }
         leaf modulator-temperature-alarm {
           type string;
           description
             "Modulator temperature alarm";
         }
         leaf modulator-bias-alarm {
           type string;
           description
             "Modulator bias alarm";
         }
         leaf module-not-ready-alarm {
           type string;
           description
             "Module not ready alarm";
         }
         leaf module-power-down-alarm {
           type string;
           description
             "Module power down alarm";
         }
         leaf module-not-init-done-alarm {
           type string;
           description
             "Module initialization not done alarm";
         }
         leaf module-not-high-power-on-alarm {
           type string;
           description
             "Module not high powered on alarm";
         }
         leaf module-fault-alarm {
           type string;
           description
             "Module in fault state alarm";
         }
         leaf pld-flash-init-fault-alarm {
           type string;
           description
             "PLD or Flash initialization fault alarm";
         }
         leaf power-supply-fault-alarm {
           type string;
           description
             "Power supply fault alarm";
         }
         leaf checksum-fault-alarm {
           type string;
           description
             "Checksum fault alarm";
         }
         leaf apd-supply-fault-alarm {
           type string;
           description
             "APD supply fault alarm";
         }
         leaf tec-fault-alarm {
           type string;
           description
             "TEC fault alarm";
         }
         leaf wavelength-unlocked-alarm {
           type string;
           description
             "Wavelength unlocked alarm";
         }
         leaf tx-tune-alarm {
           type string;
           description
             "Tx tune alarm";
         }
         leaf tx-mux-fifo-error-alarm {
           type string;
           description
             "Tx multiplexer fifo error alarm";
         }
         leaf tx-loss-of-pll-alarm {
           type string;
           description
             "Tx loss of PLL alarm";
         }
         leaf tx-data-not-ready-alarm {
           type string;
           description
             "Tx data not ready alarm";
         }
         leaf tx-not-ready-alarm {
           type string;
           description
             "Tx not ready alarm";
         }
         leaf tx-laser-fault-alarm {
           type string;
           description
             "Tx laser fault alarm";
         }
         leaf tx-laser-disabled-alarm {
           type string;
           description
             "Tx laser disabled alarm";
         }
         leaf tx-loss-of-signal-functionality-alarm {
           type string;
           description
             "Tx loss of signal functionality alarm";
         }
         leaf tx-cdr-loss-of-lock-alarm {
           type string;
           description
             "Tx CDR loss of lock alarm";
         }
         leaf rx-loss-avg-opt-power-alarm {
           type string;
           description
             "Receiver loss of average optical power alarm";
         }
         leaf rx-loss-ac-power-alarm {
           type string;
           description
             "Receiver loss of AC power alarm";
         }
         leaf rx-loss-of-pll-alarm {
           type string;
           description
             "Receiver loss of PLL alarm";
         }
         leaf rx-not-ready-alarm {
           type string;
           description
             "Receiver not ready alarm";
         }
         leaf rx-loss-of-signal-alarm {
           type string;
           description
             "Receiver loss of signal alarm";
         }
         leaf rx-cdr-loss-of-lock-alarm {
           type string;
           description
             "Receiver CDR loss of lock alarm";
         }
         leaf laser-bias-current-high-alarm-threshold {
           type string;
           description
             "Laser bias current high alarm threshold (milliamperes)";
         }
         leaf laser-bias-current-low-alarm-threshold {
           type string;
           description
             "Laser bias current low alarm threshold (milliamperes)";
         }
         leaf laser-bias-current-high-warn-threshold {
           type string;
           description
             "Laser bias current high warning threshold (milliamperes)";
         }
         leaf laser-bias-current-low-warn-threshold {
           type string;
           description
             "Laser bias current low warning threshold (milliamperes)";
         }
         leaf soa-bias-current-high-alarm-threshold {
           type string;
           description
             "SOA bias current high alarm threshold (milliamperes)";
         }
         leaf soa-bias-current-low-alarm-threshold {
           type string;
           description
             "SOA bias current low alarm threshold (milliamperes)";
         }
         leaf soa-bias-current-high-warn-threshold {
           type string;
           description
             "SOA bias current high warning threshold (milliamperes)";
         }
         leaf soa-bias-current-low-warn-threshold {
           type string;
           description
             "SOA bias current low warning threshold (milliamperes)";
         }
         leaf laser-tx-power-high-alarm-threshold {
           type string;
           description
             "Laser transmitter power high alarm threshold (milliwatts)";
         }
         leaf laser-tx-power-high-alarm-threshold-dbm {
           type string;
           description
             "Laser transmitter power high alarm threshold (dBm)";
         }
         leaf laser-tx-power-low-alarm-threshold {
           type string;
           description
             "Laser transmitter power low alarm threshold (milliwatts)";
         }
         leaf laser-tx-power-low-alarm-threshold-dbm {
           type string;
           description
             "Laser transmitter power low alarm threshold (dBm)";
         }
         leaf laser-tx-power-high-warn-threshold {
           type string;
           description
             "Laser transmitter power high warning threshold (milliwatts)";
         }
         leaf laser-tx-power-high-warn-threshold-dbm {
           type string;
           description
             "Laser transmitter power high warning threshold (dBm)";
         }
         leaf laser-tx-power-low-warn-threshold {
           type string;
           description
             "Laser transmitter power low warning threshold (milliwatts)";
         }
         leaf laser-tx-power-low-warn-threshold-dbm {
           type string;
           description
             "Laser transmitter power low warning threshold (dBm)";
         }
         leaf module-temperature-high-alarm-threshold {
           type string;
           description
             "Module temperature high alarm threshold";
         }
         leaf module-temperature-low-alarm-threshold {
           type string;
           description
             "Module temperature low alarm threshold";
         }
         leaf module-temperature-high-warn-threshold {
           type string;
           description
             "Module temperature high warning threshold";
         }
         leaf module-temperature-low-warn-threshold {
           type string;
           description
             "Module temperature low warning threshold";
         }
         leaf laser-temperature-high-alarm-threshold {
           type string;
           description
             "Laser temperature high alarm threshold";
         }
         leaf laser-temperature-low-alarm-threshold {
           type string;
           description
             "Laser temperature low alarm threshold";
         }
         leaf laser-temperature-high-warn-threshold {
           type string;
           description
             "Laser temperature high warning threshold";
         }
         leaf laser-temperature-low-warn-threshold {
           type string;
           description
             "Laser temperature low warning threshold";
         }
         leaf module-voltage-high-alarm-threshold {
           type string;
           description
             "Module voltage high alarm threshold (volts)";
         }
         leaf module-voltage-low-alarm-threshold {
           type string;
           description
             "Module voltage low alarm threshold (volts)";
         }
         leaf module-voltage-high-warn-threshold {
           type string;
           description
             "Module voltage high warning threshold (volts)";
         }
         leaf module-voltage-low-warn-threshold {
           type string;
           description
             "Module voltage low warning threshold (volts)";
         }
         leaf laser-rx-power-high-alarm-threshold {
           type string;
           description
             "Laser receiver power high alarm (milliwatts)";
         }
         leaf laser-rx-power-high-alarm-threshold-dbm {
           type string;
           description
             "Laser receiver power high alarm (dBm)";
         }
         leaf laser-rx-power-low-alarm-threshold {
           type string;
           description
             "Laser receiver power low alarm (milliwatts)";
         }
         leaf laser-rx-power-low-alarm-threshold-dbm {
           type string;
           description
             "Laser receiver power low alarm (dBm)";
         }
         leaf laser-rx-power-high-warn-threshold {
           type string;
           description
             "Laser receiver power high warning (milliwatts)";
         }
         leaf laser-rx-power-high-warn-threshold-dbm {
           type string;
           description
             "Laser receiver power high warning (dBm)";
         }
         leaf laser-rx-power-low-warn-threshold {
           type string;
           description
             "Laser receiver power low warning (milliwatts)";
         }
         leaf laser-rx-power-low-warn-threshold-dbm {
           type string;
           description
             "Laser receiver power low warning (dBm)";
         }
         leaf rx-power-high-alarm-threshold {
           type string;
           description
             "Receiver power high alarm (milliwatts)";
         }
         leaf rx-power-high-alarm-threshold-dbm {
           type string;
           description
             "Receiver power high alarm (dBm)";
         }
         leaf rx-power-low-alarm-threshold {
           type string;
           description
             "Receiver power low alarm (milliwatts)";
         }
         leaf rx-power-low-alarm-threshold-dbm {
           type string;
           description
             "Receiver power low alarm (dBm)";
         }
         leaf rx-power-high-warning-threshold {
           type string;
           description
             "Receiver power high warning (milliwatts)";
         }
         leaf rx-power-high-warning-threshold-dbm {
           type string;
           description
             "Receiver power high warning (dBm)";
         }
         leaf rx-power-low-warning-threshold {
           type string;
           description
             "Receiver power low warning (milliwatts)";
         }
         leaf rx-power-low-warning-threshold-dbm {
           type string;
           description
             "Receiver power low warning (dBm)";
         }
         leaf los-alarm-threshold {
           type string;
           description
             "LOS alarm threshold (milliwatts)";
         }
         leaf los-alarm-threshold-dbm {
           type string;
           description
             "LOS alarm threshold (dBm)";
         }
         leaf los-warning-threshold {
           type string;
           description
             "LOS warning threshold (milliwatts)";
         }
         leaf los-warning-threshold-dbm {
           type string;
           description
             "LOS warning threshold (dBm)";
         }
         leaf dsp-module-state {
           type string;
           description
             "DSP module state";
         }
         leaf rx-pow-manual-threshold-enabled {
           type string;
           description
             "Manual RX Power High Alarm Threshold";
         }
         leaf rx-pow-high-alarm-threshold-manual {
           type string;
           description
             "Manual RX Power High Alarm Threshold";
         }
         leaf rx-pow-high-warning-threshold-manual {
           type string;
           description
             "Manual RX Power High Warning Threshold";
         }
         leaf rx-pow-low-warning-threshold-manual {
           type string;
           description
             "Manual RX Power Low Warning Threshold";
         }
         leaf rx-pow-low-alarm-threshold-manual {
           type string;
           description
             "Manual RX Power Low Alarm Threshold";
         }
         leaf output-power {
           type string;
           description
             "Output power (milliwatts)";
         }
         leaf output-power-dbm {
           type string;
           description
             "Output power (dBm)";
         }
         leaf input-power {
           type string;
           description
             "Input power (milliwatts)";
         }
         leaf input-power-dbm {
           type string;
           description
             "Input power (dBm)";
         }
         leaf per-wave-rx-optical-power {
           type string;
           description
             "Per-wavelength receiver optical power (milliwatts)";
         }
         leaf per-wave-rx-optical-power-dbm {
           type string;
           description
             "Per-wavelength receiver optical power (dBm)";
         }
         leaf lane-laser-frequency-error {
           type string;
           description
             "Lane laser frequency error (MHz)";
         }
         leaf tec-current {
           type string;
           description
             "Tec current";
         }
         leaf residual-isi {
           type string;
           description
             "Residual ISI";
         }
         container optics-diagnostics-ot {
           description
             "OT interface optics diagnostics";
           leaf module-temp-fault {
             type string;
             description
               "Module temperature fault";
           }
           leaf specific-hw-fault {
             type string;
             description
               "Specific HW fault";
           }
           leaf internal-power-fault {
             type string;
             description
               "Internal power fault";
           }
           leaf post-therm-fault {
             type string;
             description
               "Power thermal fault";
           }
           leaf post-fault {
             type string;
             description
               "Post fault";
           }
           leaf command-error {
             type string;
             description
               "Command error";
           }
           leaf rx-pll-lock {
             type string;
             description
               "RX PLL lock";
           }
           leaf network-lane-los {
             type string;
             description
               "Network Lane LOS";
           }
           leaf network-lane-lof {
             type string;
             description
               "Network Lane LOF";
           }
           leaf network-lane-oof {
             type string;
             description
               "Network Lane OOF";
           }
           leaf network-lane-lom {
             type string;
             description
               "Network Lane LOM";
           }
           leaf network-lane-oom {
             type string;
             description
               "Network Lane OOM";
           }
           leaf network-lane-otu-bdi {
             type string;
             description
               "Network Lane OTU BDI";
           }
           leaf lane-rx-fifo-error {
             type string;
             description
               "Lane RX FIFO error";
           }
           leaf tx-reference-clock-fault {
             type string;
             description
               "TX reference clock fault";
           }
           leaf rx-modem-sync-fault {
             type string;
             description
               "Rx modem sync fault";
           }
           leaf rx-modem-loss-of-lock {
             type string;
             description
               "RX modem loss of lock";
           }
           leaf rx-loss-of-alignment {
             type string;
             description
               "RX loss of alignment";
           }
           leaf rx-out-of-alignment {
             type string;
             description
               "RX out of alignment";
           }
           leaf rx-timing-fault {
             type string;
             description
               "Rx timing fault";
           }
           leaf link-msg-data-available {
             type string;
             description
               "Link msg data available";
           }
           leaf modulator-bias-control-loop-fail {
             type string;
             description
               "Modulator Bias Control Loop Fail";
           }
           leaf itla-fault {
             type string;
             description
               "ITLA fault";
           }
           leaf dac-calib-fault {
             type string;
             description
               "DAC calib fault";
           }
           leaf adc-calib-fault {
             type string;
             description
               "ADC calib fault";
           }
           leaf prom-fault {
             type string;
             description
               "PROM fault";
           }
           leaf tx-mod-bias-voa-ctrl-loop-high-alarm {
             type string;
             description
               "TX mod bias VOA ctrl loop high alarm";
           }
           leaf tx-mod-bias-voa-ctrl-loop-low-alarm {
             type string;
             description
               "TX mod bias VOA ctrl loop low alarm";
           }
           leaf rx-phase-control-loop-high-alarm {
             type string;
             description
               "RX phase control loop high alarm";
           }
           leaf rx-phase-control-loop-low-alarm {
             type string;
             description
               "RX phase control loop low alarm";
           }
           leaf rx-phase-control-loop-high-warning {
             type string;
             description
               "RX phase control loop high warning";
           }
           leaf rx-phase-control-loop-low-warning {
             type string;
             description
               "RX phase control loop low warning";
           }
           leaf oa-pump-bias-current-high-alarm {
             type string;
             description
               "OA pump bias current high alarm";
           }
           leaf oa-pump-bias-current-low-alarm {
             type string;
             description
               "OA pump bias current low alarm";
           }
           leaf oa-pump-bias-current-high-warning {
             type string;
             description
               "OA pump bias current high warning";
           }
           leaf oa-pump-bias-current-low-warning {
             type string;
             description
               "OA pump bias current low warning";
           }
           leaf tx-jitter-pll-lol-input-nw-lane {
             type string;
             description
               "Tx jitter PLL LOL i/p nw lane";
           }
           leaf tx-out-of-alignment {
             type string;
             description
               "TX out of alignment";
           }
           leaf tx-cmu-lock-fault {
             type string;
             description
               "Tx CMU lock fault";
           }
           leaf adc-signal-below-threshold {
             type string;
             description
               "ADC signal below threshold";
           }
           leaf tx-output-power-adjustment-fault {
             type string;
             description
               "Tx output power adjustment fault";
           }
           leaf tx-output-mod-converge-fault {
             type string;
             description
               "TX output mod converge fault";
           }
           leaf tx-laser-ready-fault {
             type string;
             description
               "Tx laser ready fault";
           }
           leaf tx-laser-ready-off-fault {
             type string;
             description
               "Tx laser ready off fault";
           }
           leaf tx-asic-ready-fault {
             type string;
             description
               "Tx asic ready fault";
           }
           leaf tx-initialization-fault {
             type string;
             description
               "Tx initialization fault";
           }
           leaf rx-demodulator-lock-fault {
             type string;
             description
               "Rx demodulator lock fault";
           }
           leaf rx-dispersion-lock-fault {
             type string;
             description
               "Rx dispersion lock fault";
           }
           leaf rx-adc-output-fault {
             type string;
             description
               "Rx ADC output fault";
           }
           leaf rx-optical-input-fault {
             type string;
             description
               "Rx optical input fault";
           }
           leaf rx-asic-ready-fault {
             type string;
             description
               "Rx asic ready fault";
           }
           leaf rx-initialization-fault {
             type string;
             description
               "Rx initialization fault";
           }
           leaf tx-mod-bias-high-alarm {
             type string;
             description
               "TX modulator bias high alarm";
           }
           leaf tx-mod-bias-low-alarm {
             type string;
             description
               "TX modulator bias low alarm";
           }
           leaf tx-mod-bias-high-warning {
             type string;
             description
               "TX modulator bias high warning";
           }
           leaf tx-mod-bias-low-warning {
             type string;
             description
               "TX modulator bias low warning";
           }
           leaf rx-pwr-high-alarm {
             type string;
             description
               "RX power high alarm";
           }
           leaf rx-pwr-low-alarm {
             type string;
             description
               "RX power low alarm";
           }
           leaf rx-pwr-high-warn {
             type string;
             description
               "RX power high warning";
           }
           leaf rx-pwr-low-warn {
             type string;
             description
               "RX power low warning";
           }
           leaf tx-laser-power-high-alarm {
             type string;
             description
               "TX laser power high alarm";
           }
           leaf tx-laser-power-low-alarm {
             type string;
             description
               "TX laser power low alarm";
           }
           leaf tx-laser-power-high-warn {
             type string;
             description
               "TX laser power high warning";
           }
           leaf tx-laser-power-low-warn {
             type string;
             description
               "TX laser power low warning";
           }
           leaf tx-bias-high-alarm {
             type string;
             description
               "TX laser current high alarm";
           }
           leaf tx-bias-low-alarm {
             type string;
             description
               "TX laser current low alarm";
           }
           leaf tx-bias-high-warn {
             type string;
             description
               "TX laser current high warning";
           }
           leaf tx-bias-low-warn {
             type string;
             description
               "TX laser current low warning";
           }
           leaf tx-laser-temp-high-alarm {
             type string;
             description
               "TX laser temperature high alarm";
           }
           leaf tx-laser-temp-low-alarm {
             type string;
             description
               "TX laser temperature low alarm";
           }
           leaf tx-laser-temp-high-warn {
             type string;
             description
               "TX laser temperature high warning";
           }
           leaf tx-laser-temp-low-warn {
             type string;
             description
               "TX laser temperature low warning";
           }
         }
         list optics-diagnostics-lane-values {
           key "lane-index";
           leaf lane-index {
             type int32;
           }
           leaf laser-bias-current {
             type string;
             description
               "Laser bias current (milliamperes)";
           }
           leaf laser-bias-current-not-available {
             type string;
             description
               "Laser bias current measurement not available";
           }
           leaf laser-output-power {
             type string;
             description
               "Laser output power (milliwatts)";
           }
           leaf laser-output-power-dbm {
             type string;
             description
               "Laser output power (dBm)";
           }
           leaf output-power {
             type string;
             description
               "Output power (milliwatts)";
           }
           leaf output-power-dbm {
             type string;
             description
               "Output power (dBm)";
           }
           leaf laser-temperature {
             type string;
             description
               "Laser temperature";
           }
           leaf laser-module-temperature {
             type string;
             description
               "Module temperature";
           }
           leaf laser-tx-optical-power {
             type string;
             description
               "Laser transmitter optical power (milliwatts)";
           }
           leaf laser-tx-optical-power-dbm {
             type string;
             description
               "Laser transmitter optical power (dBm)";
           }
           leaf laser-rx-optical-power {
             type string;
             description
               "Laser receiver optical power (milliwatts)";
           }
           leaf laser-rx-optical-power-dbm {
             type string;
             description
               "Laser receiver optical power (dBm)";
           }
           leaf input-power {
             type string;
             description
               "Input power (milliwatts)";
           }
           leaf input-power-dbm {
             type string;
             description
               "Input power (dBm)";
           }
           leaf input-total-power {
             type string;
             description
               "Input power (total) (milliwatts)";
           }
           leaf input-total-power-dbm {
             type string;
             description
               "Input power (dBm)";
           }
           leaf per-wave-rx-optical-power {
             type string;
             description
               "Per-wavelength receiver optical power (milliwatts)";
           }
           leaf per-wave-rx-optical-power-dbm {
             type string;
             description
               "Per-wavelength receiver optical power (dBm)";
           }
           leaf lane-configured-cd {
             type string;
             description
               "Lane configured chromatic dispersion (ps/nm)";
           }
           leaf lane-chromatic-dispersion {
             type string;
             description
               "Lane chromatic dispersion (ps/nm)";
           }
           leaf lane-avg-chromatic-dispersion {
             type string;
             description
               "Lane avg chromatic dispersion (ps/nm)";
           }
           leaf lane-min-chromatic-dispersion {
             type string;
             description
               "Lane min chromatic dispersion (ps/nm)";
           }
           leaf lane-max-chromatic-dispersion {
             type string;
             description
               "Lane max chromatic dispersion (ps/nm)";
           }
           leaf lane-differential-group-delay {
             type string;
             description
               "Lane differential group delay (ps)";
           }
           leaf lane-avg-differential-group-delay {
             type string;
             description
               "Lane avg differential group delay (ps)";
           }
           leaf lane-min-differential-group-delay {
             type string;
             description
               "Lane min differential group delay (ps)";
           }
           leaf lane-max-differential-group-delay {
             type string;
             description
               "Lane max differential group delay (ps)";
           }
           leaf lane-sopmd {
             type string;
             description
               "Lane sopmd";
           }
           leaf lane-avg-sopmd {
             type string;
             description
               "Lane avg sopmd";
           }
           leaf lane-min-sopmd {
             type string;
             description
               "Lane min sopmd";
           }
           leaf lane-max-sopmd {
             type string;
             description
               "Lane max sopmd";
           }
           leaf q-factor {
             type string;
             description
               "Lane q-factor";
           }
           leaf q-factor-not-available {
             type string;
             description
               "Lane q-factor not available";
           }
           leaf q-margin {
             type string;
             description
               "Lane q-margin";
           }
           leaf q-margin-not-available {
             type string;
             description
               "Lane q-margin not available";
           }
           leaf lane-state-of-polarization {
             type string;
             description
               "Lane state of polarization (rad/s)";
           }
           leaf lane-avg-state-of-polarization {
             type string;
             description
               "Lane avg state of polarization (rad/s)";
           }
           leaf lane-min-state-of-polarization {
             type string;
             description
               "Lane min state of polarization (rad/s)";
           }
           leaf lane-max-state-of-polarization {
             type string;
             description
               "Lane max state of polarization (rad/s)";
           }
           leaf lane-polarization-dependent-loss {
             type string;
             description
               "Lane polarization dependent loss (dB)";
           }
           leaf lane-avg-polarization-dependent-loss {
             type string;
             description
               "Lane avg polarization dependent loss (dB)";
           }
           leaf lane-min-polarization-dependent-loss {
             type string;
             description
               "Lane min polarization dependent loss (dB)";
           }
           leaf lane-max-polarization-dependent-loss {
             type string;
             description
               "Lane max polarization dependent loss (dB)";
           }
           leaf lane-q2-factor {
             type string;
             description
               "Lane Q2 factor (dB)";
           }
           leaf lane-q-value {
             type string;
             description
               "Lane q value (dB)";
           }
           leaf lane-avg-q-value {
             type string;
             description
               "Lane avg q value (dB)";
           }
           leaf lane-min-q-value {
             type string;
             description
               "Lane min q value (dB)";
           }
           leaf lane-max-q-value {
             type string;
             description
               "Lane max q value (dB)";
           }
           leaf lane-carrier-frequency-offset {
             type string;
             description
               "Lane carrier frequency offset (MHz)";
           }
           leaf lane-avg-carrier-frequency-offset {
             type string;
             description
               "Lane avg carrier frequency offset (MHz)";
           }
           leaf lane-min-carrier-frequency-offset {
             type string;
             description
               "Lane min carrier frequency offset (MHz)";
           }
           leaf lane-max-carrier-frequency-offset {
             type string;
             description
               "Lane max carrier frequency offset (MHz)";
           }
           leaf lane-electrical-snr {
             type string;
             description
               "Lane electrical SNR (dB)";
           }
           leaf lane-snr {
             type string;
             description
               "Lane snr (dB)";
           }
           leaf lane-avg-snr {
             type string;
             description
               "Lane avg snr (dB)";
           }
           leaf lane-min-snr {
             type string;
             description
               "Lane min snr (dB)";
           }
           leaf lane-max-snr {
             type string;
             description
               "Lane max snr (dB)";
           }
           leaf lane-rx-laser-bias {
             type string;
             description
               "Lane rx laser bias (mA)";
           }
           leaf lane-rx-laser-power {
             type string;
             description
               "Lane rx laser power (dBm)";
           }
           leaf lane-rx-laser-temp {
             type string;
             description
               "Lane rx laser temp (C)";
           }
           leaf lane-tx-modulator-bias-x-i {
             type string;
             description
               "Lane tx modulator bias x i (mV)";
           }
           leaf lane-tx-modulator-bias-x-q {
             type string;
             description
               "Lane tx modulator bias x q (mV)";
           }
           leaf lane-tx-modulator-bias-y-i {
             type string;
             description
               "Lane tx modulator bias y i (mV)";
           }
           leaf lane-tx-modulator-bias-y-q {
             type string;
             description
               "Lane tx modulator bias y q (mV)";
           }
           leaf lane-tx-modulator-bias-x-phase {
             type string;
             description
               "Lane tx modulator bias x phase (mV)";
           }
           leaf lane-tx-modulator-bias-y-phase {
             type string;
             description
               "Lane tx modulator bias y phase (mV)";
           }
           leaf tx-input-equalization {
             type string;
             description
               "Tx input equalization";
           }
           leaf rx-output-amplitude {
             type string;
             description
               "Rx output amplitude";
           }
           leaf rx-output-pre-emphasis {
             type string;
             description
               "Rx output pre epmhasis";
           }
           leaf lane-laser-frequency-error {
             type string;
             description
               "Lane laser frequency error (MHz)";
           }
           leaf tec-current {
             type string;
             description
               "Tec current";
           }
           leaf residual-isi {
             type string;
             description
               "Residual ISI";
           }
           leaf pam-histogram {
             type string;
             description
               "PAM histogram";
           }
           leaf laser-bias-current-high-alarm {
             type string;
             description
               "Laser bias current high alarm";
           }
           leaf laser-bias-current-low-alarm {
             type string;
             description
               "Laser bias current low alarm";
           }
           leaf laser-bias-current-high-warn {
             type string;
             description
               "Laser bias current high warning";
           }
           leaf laser-bias-current-low-warn {
             type string;
             description
               "Laser bias current low warning";
           }
           leaf laser-tx-power-high-alarm {
             type string;
             description
               "Laser output power high alarm";
           }
           leaf laser-tx-power-low-alarm {
             type string;
             description
               "Laser output power low alarm";
           }
           leaf laser-tx-power-high-warn {
             type string;
             description
               "Laser output power high warning";
           }
           leaf laser-tx-power-low-warn {
             type string;
             description
               "Laser output power low warning";
           }
           leaf tx-power-high-alarm {
             type string;
             description
               "Tx power high alarm";
           }
           leaf tx-power-low-alarm {
             type string;
             description
               "Tx power low alarm";
           }
           leaf tx-power-high-warn {
             type string;
             description
               "Tx power high warning";
           }
           leaf tx-power-low-warn {
             type string;
             description
               "Tx power low warning";
           }
           leaf laser-temp-high-alarm {
             type string;
             description
               "Laser temperature high alarm";
           }
           leaf laser-temp-low-alarm {
             type string;
             description
               "Laser temperature low alarm";
           }
           leaf laser-temp-high-warn {
             type string;
             description
               "Laser temperature high warning";
           }
           leaf laser-temp-low-warn {
             type string;
             description
               "Laser temperature low warning";
           }
           leaf laser-rx-power-high-alarm {
             type string;
             description
               "Laser receiver power high alarm";
           }
           leaf laser-rx-power-low-alarm {
             type string;
             description
               "Laser receiver power low alarm";
           }
           leaf laser-rx-power-high-warn {
             type string;
             description
               "Laser receiver power high warning";
           }
           leaf laser-rx-power-low-warn {
             type string;
             description
               "Laser receiver power low warning";
           }
           leaf rx-power-high-alarm {
             type string;
             description
               "Receiver power high alarm";
           }
           leaf rx-power-low-alarm {
             type string;
             description
               "Receiver power low alarm";
           }
           leaf rx-power-high-warn {
             type string;
             description
               "Receiver power high warning";
           }
           leaf rx-power-low-warn {
             type string;
             description
               "Receiver power low warning";
           }
           leaf tx-loss-of-signal-functionality-alarm {
             type string;
             description
               "Tx loss of signal functionality alarm";
           }
           leaf rx-loss-of-signal-functionality-alarm {
             type string;
             description
               "Rx loss of signal functionality alarm";
           }
           leaf tx-cdr-loss-of-lock-alarm {
             type string;
             description
               "Tx CDR loss of lock alarm";
           }
           leaf tx-loss-of-signal-alarm {
             type string;
             description
               "Transmitter loss of signal alarm";
           }
           leaf rx-loss-of-signal-alarm {
             type string;
             description
               "Receiver loss of signal alarm";
           }
           leaf tx-laser-disabled-alarm {
             type string;
             description
               "Tx laser disabled alarm";
           }
           leaf rx-cdr-loss-of-lock-alarm {
             type string;
             description
               "Receiver CDR loss of lock alarm";
           }
           leaf tec-fault-alarm {
             type string;
             description
               "TEC fault alarm";
           }
           leaf wavelength-unlocked-alarm {
             type string;
             description
               "Wavelength unlocked alarm";
           }
           leaf apd-supply-fault-alarm {
             type string;
             description
               "APD supply fault alarm";
           }
           leaf tx-channel-disabled-alarm {
             type string;
             description
               "Tx channel disabled alarm";
           }
           leaf rx-channel-disabled-alarm {
             type string;
             description
               "Rx channel disabled alarm";
           }
           leaf tx-output-disabled-alarm {
             type string;
             description
               "Rx laser disabled alarm";
           }
           leaf rx-output-disabled-alarm {
             type string;
             description
               "Rx laser disabled alarm";
           }
           leaf tx-squelch-disabled-alarm {
             type string;
             description
               "Tx squelch disabled alarm";
           }
           leaf rx-squelch-disabled-alarm {
             type string;
             description
               "Rx squelch disabled alarm";
           }
           leaf laser-end-of-life-alarm {
             type string;
             description
               "Laser end-of-life alarm";
           }
           leaf lane-cd {
             type string;
             description
               "Lane chromatic dispersion";
           }
           leaf lane-dgd {
             type string;
             description
               "Lane differential group delay";
           }
           leaf lane-cfo {
             type string;
             description
               "Lane carrier frequency offset";
           }
           leaf lane-pdl {
             type string;
             description
               "Lane polarization dependent loss";
           }
           leaf lane-osnr {
             type string;
             description
               "Optical signal-to-noise ratio(dB)";
           }
         }
       }
       container optics-diagnostics-vendor-extension {
         description
           "Optics diagnostics vendor extension";
         leaf optics-vendor-part-number {
           type string;
           description
             "Optics component vendor part number";
         }
         leaf optics-vendor-material-number {
           type string;
           description
             "Optic component vendor material number";
         }
       }
       list optics-chromatics {
         key "optics-chromatic-diagnostics-support";
         leaf optics-chromatic-diagnostics-support {
           type string;
           description
             "Optics chromatic not supported for interface";
         }
         leaf opticstype {
           type string;
           description
             "Type of optical module";
         }
         list optics-chromatic {
           key "supported-cd supported-mediaid";
           leaf supported-speed {
             type string;
             description
               "Supported Speed";
           }
           leaf supported-cd {
             type string;
             description
               "Supported Chromatic Dispersion";
           }
           leaf supported-distance {
             type string;
             description
               "Supported Distance";
           }
           leaf supported-mediaid {
             type string;
             description
               "Supported Mediaid";
           }
         }
       }
       list jrr-optics-diagnostics {
         description
           "Optics diagnostics";
         leaf jrr-optics-diagnostics-not-available {
           type string;
           description
             "Optical diagnostics not available at this time for this 
             transceiver";
         }
         leaf laser-bias-current {
           type string;
           description
             "Laser bias current (milliamperes)";
         }
         leaf laser-output-power {
           type string;
           description
             "Laser output power (milliwatts)";
         }
         leaf module-temperature {
           type string;
           description
             "Module temperature";
         }
         leaf module-voltage {
           type string;
           description
             "Module voltage";
         }
         leaf module-max-power {
           type string;
           description
             "Module max power";
         }
         leaf rx-signal-avg-optical-power {
           type string;
           description
             "Receiver signal average power (milliwatts)";
         }
         leaf laser-bias-current-high-alarm {
           type string;
           description
             "Laser bias current high alarm";
         }
         leaf laser-bias-current-low-alarm {
           type string;
           description
             "Laser bias current low alarm";
         }
         leaf laser-bias-current-high-warn {
           type string;
           description
             "Laser bias current high warning";
         }
         leaf laser-bias-current-low-warn {
           type string;
           description
             "Laser bias current low warning";
         }
         leaf laser-tx-power-high-alarm {
           type string;
           description
             "Laser output power high alarm";
         }
         leaf laser-tx-power-low-alarm {
           type string;
           description
             "Laser output power low alarm";
         }
         leaf laser-tx-power-high-warn {
           type string;
           description
             "Laser output power high warning";
         }
         leaf laser-tx-power-low-warn {
           type string;
           description
             "Laser output power low warning";
         }
         leaf module-temperature-high-alarm {
           type string;
           description
             "Module temperature high alarm";
         }
         leaf module-temperature-low-alarm {
           type string;
           description
             "Module temperature low alarm";
         }
         leaf module-temperature-high-warn {
           type string;
           description
             "Module temperature high warning";
         }
         leaf module-temperature-low-warn {
           type string;
           description
             "Module temperature low warning";
         }
         leaf module-voltage-high-alarm {
           type string;
           description
             "Module voltage high alarm";
         }
         leaf module-voltage-low-alarm {
           type string;
           description
             "Module voltage low alarm";
         }
         leaf module-voltage-high-warn {
           type string;
           description
             "Module voltage high warning";
         }
         leaf module-voltage-low-warn {
           type string;
           description
             "Module voltage low warning";
         }
         leaf laser-rx-power-high-alarm {
           type string;
           description
             "Laser receiver power high alarm";
         }
         leaf laser-rx-power-low-alarm {
           type string;
           description
             "Laser receiver power low alarm";
         }
         leaf laser-rx-power-high-warn {
           type string;
           description
             "Laser receiver power high warning";
         }
         leaf laser-rx-power-low-warn {
           type string;
           description
             "Laser receiver power low warning";
         }
         leaf laser-bias-current-high-alarm-threshold {
           type string;
           description
             "Laser bias current high alarm threshold (milliamperes)";
         }
         leaf laser-bias-current-low-alarm-threshold {
           type string;
           description
             "Laser bias current low alarm threshold (milliamperes)";
         }
         leaf laser-bias-current-high-warn-threshold {
           type string;
           description
             "Laser bias current high warning threshold (milliamperes)";
         }
         leaf laser-bias-current-low-warn-threshold {
           type string;
           description
             "Laser bias current low warning threshold (milliamperes)";
         }
         leaf laser-tx-power-high-alarm-threshold {
           type string;
           description
             "Laser transmitter power high alarm threshold (milliwatts)";
         }
         leaf laser-tx-power-low-alarm-threshold {
           type string;
           description
             "Laser transmitter power low alarm threshold (milliwatts)";
         }
         leaf laser-tx-power-high-warn-threshold {
           type string;
           description
             "Laser transmitter power high warning threshold (milliwatts)";
         }
         leaf laser-tx-power-low-warn-threshold {
           type string;
           description
             "Laser transmitter power low warning threshold (milliwatts)";
         }
         leaf module-temperature-high-alarm-threshold {
           type string;
           description
             "Module temperature high alarm threshold";
         }
         leaf module-temperature-low-alarm-threshold {
           type string;
           description
             "Module temperature low alarm threshold";
         }
         leaf module-temperature-high-warn-threshold {
           type string;
           description
             "Module temperature high warning threshold";
         }
         leaf module-temperature-low-warn-threshold {
           type string;
           description
             "Module temperature low warning threshold";
         }
         leaf module-voltage-high-alarm-threshold {
           type string;
           description
             "Module voltage high alarm threshold (volts)";
         }
         leaf module-voltage-low-alarm-threshold {
           type string;
           description
             "Module voltage low alarm threshold (volts)";
         }
         leaf module-voltage-high-warn-threshold {
           type string;
           description
             "Module voltage high warning threshold (volts)";
         }
         leaf module-voltage-low-warn-threshold {
           type string;
           description
             "Module voltage low warning threshold (volts)";
         }
         leaf laser-rx-power-high-alarm-threshold {
           type string;
           description
             "Laser receiver power high alarm (milliwatts)";
         }
         leaf laser-rx-power-low-alarm-threshold {
           type string;
           description
             "Laser receiver power low alarm (milliwatts)";
         }
         leaf laser-rx-power-high-warn-threshold {
           type string;
           description
             "Laser receiver power high warning (milliwatts)";
         }
         leaf laser-rx-power-low-warn-threshold {
           type string;
           description
             "Laser receiver power low warning (milliwatts)";
         }
       }
       container optics-properties {
         description
           "Optics properties";
         leaf wavelength {
           type string;
           description
             "Wavelength of optics in nanometers";
         }
         leaf frequency {
           type string;
           description
             "Frequency of optics in terahertz";
         }
         leaf optic-loopback {
           type string;
           description
             "Optic loopback status";
         }
         leaf optic-loopback-type {
           type string;
           description
             "Optic loopback type";
         }
         leaf media-code-desc {
           type string;
           description
             "Current optics media code";
         }
         leaf host-code-desc {
           type string;
           description
             "Current optics host code";
         }
       }
       container queue-counters {
         description
           "Queue counter statistics";
         leaf queue-counters-error-message {
           type string;
           description
             "Queue statistics not available for this interface";
         }
         container interface-cos-short-summary {
           description
             "Summary of queue information on an interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
         }
         list queue {
           key "queue-number";
           description
             "Counters for a single queue";
           leaf queue-number {
             type uint32;
             description
               "Queue number";
           }
           leaf queue-counters-queued-packets {
             type int32;
             description
               "Queued packet count";
           }
           leaf queue-counters-trans-packets {
             type int32;
             description
               "Total number of transmitted packets";
           }
           leaf queue-counters-total-drop-packets {
             type int32;
             description
               "Number of total packets dropped at the queue";
           }
           leaf forwarding-class-name {
             type string;
             description
               "Forwarding class name associated with queue";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-queued-packets-na {
             type string;
             description
               "Queued packets not available";
           }
           leaf queue-counters-queued-bytes-na {
             type string;
             description
               "Queued bytes not available";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets-na {
             type string;
             description
               "Number of packets dropped due to tail drop not available";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of packets dropped at tail drop of the queue";
           }
           leaf queue-counters-tail-drop-bytes-rate {
             type int32;
             description
               "Number of packets dropped at tail drop of the queue";
           }
           leaf queue-counters-ecn-ce-packets {
             type int32;
             description
               "Total number of ECN CE packets";
           }
           leaf queue-counters-ecn-ce-packets-rate {
             type int32;
             description
               "Rate at which ECN CE packets are transmitted";
           }
           leaf queue-counters-ecn-ce-bytes {
             type int32;
             description
               "Total number of ECN CE bytes";
           }
           leaf queue-counters-ecn-ce-bytes-rate {
             type int32;
             description
               "Rate at which ECN CE bytes are transmitted";
           }
           leaf queue-counters-rate-limit-drop-packets-na {
             type string;
             description
               "Number of packets dropped due to rate-limit drop not 
               available";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes-na {
             type string;
             description
               "Number of bytes dropped due to tail drop not available";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets-na {
             type string;
             description
               "Number of packets dropped due to RED not available";
           }
           leaf queue-counters-red-packets {
             type int32;
             description
               "Number of packets dropped due to RED";
           }
           leaf queue-counters-red-packets-rate {
             type int32;
             description
               "Rate at which packets are dropped due to RED";
           }
           leaf queue-counters-red-packets-ln {
             type int32;
             description
               "Number of RED dropped low-loss, non-TCP packets";
           }
           leaf queue-counters-red-packets-rate-ln {
             type int32;
             description
               "RED drop rate for low-loss, non-TCP packets";
           }
           leaf queue-counters-red-packets-lt {
             type int32;
             description
               "Number of RED dropped of low-loss, TCP packets";
           }
           leaf queue-counters-red-packets-rate-lt {
             type int32;
             description
               "RED drop rate for low-loss, TCP packets";
           }
           leaf queue-counters-red-packets-hn {
             type int32;
             description
               "Number of RED dropped high-loss, non-TCP packets";
           }
           leaf queue-counters-red-packets-rate-hn {
             type int32;
             description
               "RED drop rate for high-loss, non-TCP packets";
           }
           leaf queue-counters-red-packets-ht {
             type int32;
             description
               "Number of RED dropped high-loss, TCP packets";
           }
           leaf queue-counters-red-packets-rate-ht {
             type int32;
             description
               "RED drop rate for high-loss, TCP packets";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-medium {
             type int32;
             description
               "Number of RED dropped medium-loss packets";
           }
           leaf queue-counters-red-packets-rate-medium {
             type int32;
             description
               "RED drop rate for medium-loss packets";
           }
           leaf queue-counters-red-packets-high {
             type int32;
             description
               "Number of RED dropped high-loss packets";
           }
           leaf queue-counters-red-packets-rate-high {
             type int32;
             description
               "RED drop rate for high-loss packets";
           }
           leaf queue-counters-red-bytes-na {
             type string;
             description
               "Number of bytes dropped due to RED not available";
           }
           leaf queue-counters-red-bytes {
             type int32;
             description
               "Number of bytes dropped due to RED";
           }
           leaf queue-counters-red-bytes-rate {
             type int32;
             description
               "Rate at which bytes are dropped due to RED";
           }
           leaf queue-counters-red-bytes-ln {
             type int32;
             description
               "Number of RED dropped low-loss, non-TCP bytes";
           }
           leaf queue-counters-red-bytes-rate-ln {
             type int32;
             description
               "RED drop rate for low-loss, non-TCP bytes";
           }
           leaf queue-counters-red-bytes-lt {
             type int32;
             description
               "Number of RED dropped low-loss, TCP bytes";
           }
           leaf queue-counters-red-bytes-rate-lt {
             type int32;
             description
               "RED drop rate for low-loss, TCP bytes";
           }
           leaf queue-counters-red-bytes-hn {
             type int32;
             description
               "Number of RED dropped high-loss, non-TCP bytes";
           }
           leaf queue-counters-red-bytes-rate-hn {
             type int32;
             description
               "RED drop rate for high-loss, non-TCP bytes";
           }
           leaf queue-counters-red-bytes-ht {
             type int32;
             description
               "Number of RED dropped high-loss, TCP bytes";
           }
           leaf queue-counters-red-bytes-rate-ht {
             type int32;
             description
               "RED drop rate for high-loss, TCP bytes";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-medium {
             type int32;
             description
               "Number of RED dropped medium-loss bytes";
           }
           leaf queue-counters-red-bytes-rate-medium {
             type int32;
             description
               "RED drop rate for medium-loss bytes";
           }
           leaf queue-counters-red-bytes-high {
             type int32;
             description
               "Number of RED dropped high-loss bytes";
           }
           leaf queue-counters-red-bytes-rate-high {
             type int32;
             description
               "RED drop rate for high-loss bytes";
           }
           leaf queue-counters-timestamp {
             type int32;
             description
               "Last packet enqueued timestamp";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
           leaf queue-counters-reserved-buffer-packets {
             type int32;
             description
               "Queues's usage of reserved buffer pool in pkts";
           }
           leaf queue-counters-reserved-buffer-bytes {
             type int32;
             description
               "Queues's usage of reserved buffer pool in bytes";
           }
           leaf queue-counters-shared-buffer-packets {
             type int32;
             description
               "Queues's usage of shared buffer pool in pkts";
           }
           leaf queue-counters-shared-buffer-bytes {
             type int32;
             description
               "Queues's usage of shared buffer pool in bytes";
           }
           leaf queue-counters-depth-average {
             type int32;
             description
               "Time averaged queue depth";
           }
           leaf queue-counters-depth-current {
             type int32;
             description
               "Current instantaneous queue depth";
           }
           leaf queue-counters-depth-peak {
             type int32;
             description
               "Peak queue depth";
           }
           leaf queue-counters-depth-max {
             type int32;
             description
               "Maximum queue depth attained";
           }
           leaf queue-counters-srx-reserved-buffer-bytes {
             type int32;
             description
               "Queues's usage of reserved buffer pool in bytes";
           }
           leaf queue-counters-srx-depth-current {
             type int32;
             description
               "Current instantaneous queue depth";
           }
         }
         container interface-cos-summary {
           description
             "Summary of forwarding class and queue information on an 
             interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
           leaf intf-cos-burst-size-for-ifl {
             type int32;
             description
               "Burst size for the logical interface";
           }
         }
       }
       container voq-counters {
         description
           "VOQ counter statistics";
         leaf voq-counters-error-message {
           type string;
           description
             "VOQ statistics not available for this interface";
         }
         container voq {
           description
             "Counters for a single voq";
           container fpc {
             description
               "Counters for a single FPC";
             leaf fpc-no {
               type int32;
               description
                 "FPC number";
             }
             container pfe {
               description
                 "Counters for a single PFE";
               leaf-list pfe-no {
                 type int32;
                 description
                   "PFE number";
               }
               leaf voq-counters-tail-drop-packets {
                 type int32;
                 description
                   "Tail DROP packet count";
               }
               leaf voq-counters-tail-drop-packets-rate {
                 type int32;
                 description
                   "Rate at which tail packets are dropped";
               }
               leaf voq-counters-tail-drop-bytes {
                 type int32;
                 description
                   "Tail DROP bytes count";
               }
               leaf voq-counters-tail-drop-bytes-rate {
                 type int32;
                 description
                   "Rate at which tail bytes are dropped";
               }
               leaf voq-counters-drop-packets {
                 type int32;
                 description
                   "DROP packet count";
               }
               leaf voq-counters-drop-packets-rate {
                 type int32;
                 description
                   "Rate at which packets are dropped";
               }
               leaf voq-counters-drop-bytes {
                 type int32;
                 description
                   "DROP bytes count";
               }
               leaf voq-counters-drop-bytes-rate {
                 type int32;
                 description
                   "Rate at which bytes are dropped";
               }
               leaf voq-counters-queued-packets {
                 type int32;
                 description
                   "QUEUED packets count";
               }
               leaf voq-counters-queued-packets-rate {
                 type int32;
                 description
                   "Rate at which packets are queued";
               }
               leaf voq-counters-queued-bytes {
                 type int32;
                 description
                   "QUEUED bytes count";
               }
               leaf voq-counters-queued-bytes-rate {
                 type int32;
                 description
                   "Rate at which bytes are queued";
               }
               leaf voq-counters-transmitted-packets {
                 type int32;
                 description
                   "Transmitted packets count";
               }
               leaf voq-counters-transmitted-packets-rate {
                 type int32;
                 description
                   "Rate at which packets are transmitted";
               }
               leaf voq-counters-transmitted-bytes {
                 type int32;
                 description
                   "Transmitted bytes count";
               }
               leaf voq-counters-transmitted-bytes-rate {
                 type int32;
                 description
                   "Rate at which bytes are transmitted";
               }
               leaf voq-counters-queue-depth-bytes-current {
                 type int32;
                 description
                   "Current queue length";
               }
               leaf voq-counters-queue-depth-bytes-peak {
                 type int32;
                 description
                   "Peak queue length";
               }
               leaf voq-counters-queue-depth-bytes-average {
                 type int32;
                 description
                   "Average queue length";
               }
             }
           }
           leaf queue-number {
             type uint32;
             description
               "Queue number";
           }
           leaf forwarding-class-name {
             type string;
             description
               "Forwarding class name associated with queue";
           }
           leaf restricted-forwarding-class-name {
             type string;
           }
         }
       }
       container smart-sfp-av-titan-statistics {
         description
           "AimValley Smart SFP statistics";
         leaf smart-sfp-av-titan-error-message {
           type string;
           description
             "AV Smart SFP un-available";
         }
         container smart-sfp-av-titan-eth-port-statistics {
           leaf rx-crct-frames {
             type uint32;
           }
           leaf rx-crct-bytes {
             type uint32;
           }
           leaf rx-fragments {
             type uint32;
           }
           leaf rx-crct-unicast-frames {
             type uint32;
           }
           leaf rx-crct-multicast-frames {
             type uint32;
           }
           leaf rx-crct-broadcast-frames {
             type uint32;
           }
           leaf rx-err-fcs-frames {
             type uint32;
           }
           leaf rx-len-err-frames {
             type uint32;
           }
           leaf rx-undersize-frames {
             type uint32;
           }
           leaf rx-oversize-frames {
             type uint32;
           }
           leaf rx-inv-vlan-mismatch-frames {
             type uint32;
           }
           leaf rx-discarded-frames {
             type uint32;
           }
           leaf rx-dropped-q-overflow-frames {
             type uint32;
           }
           leaf tx-frames {
             type uint32;
           }
           leaf tx-bytes {
             type uint32;
           }
           leaf tx-unicast-frames {
             type uint32;
           }
           leaf tx-multicast-frames {
             type uint32;
           }
           leaf tx-broadcast-frames {
             type uint32;
           }
         }
         container smart-sfp-av-titan-iwf-statistics {
           leaf rx-packets {
             type uint32;
           }
           leaf tx-packets {
             type uint32;
           }
           leaf malformed-packets {
             type uint32;
           }
           leaf reordered-packets {
             type uint32;
           }
           leaf misordered-dropped-packets {
             type uint32;
           }
           leaf missing-packets {
             type uint32;
           }
           leaf played-out-packets {
             type uint32;
           }
           leaf jb-overrun {
             type uint32;
           }
           leaf jb-underrun {
             type uint32;
           }
         }
         container smart-sfp-av-titan-ds3-statistics {
           leaf rx-bpvexzerrors {
             type uint32;
           }
           leaf rx-cvperrors {
             type uint32;
           }
           leaf b3-errors {
             type uint32;
           }
         }
         container smart-sfp-av-titan-stm-statistics {
           leaf rx-b1-errors {
             type uint32;
           }
           leaf tx-b1-errors {
             type uint32;
           }
         }
       }
       container smart-sfp-av-titan-defects {
         description
           "AimValley Smart SFP defects";
         container smart-sfp-av-titan-defect-list {
           leaf sfp-tdm-defects {
             type string;
           }
           leaf sfp-system-defects {
             type string;
           }
         }
       }
       container forwarding-class-counters {
         description
           "Forwarding-class counter statistics";
         leaf forwarding-class-counters-error-message {
           type string;
           description
             "Forwarding-class statistics not available for this interface";
         }
         container ipv4-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container ipv6-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container mpls-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container layer2-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container other-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container protocol-aggregate-forwarding-class-counters {
           leaf forwarding-class-stats-type {
             type string;
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container forwarding-class-statistics {
           container protocol-aggregate-forwarding-class-counters {
           }
           container ipv4-forwarding-class-counters {
           }
           container ipv6-forwarding-class-counters {
           }
           container mpls-forwarding-class-counters {
           }
           container layer2-forwarding-class-counters {
           }
           container other-forwarding-class-counters {
           }
         }
         container forwarding-class-accounting-parameters {
           leaf forwarding-class-accounting-for-protocol {
             type string;
           }
           leaf forwarding-class-accounting-for-traffic-direction {
             type string;
           }
           leaf forwarding-class-accounting-for-traffic-type {
             type string;
           }
           leaf forwarding-class-accounting-overhead-bytes {
             type uint32;
           }
         }
         container per-forwarding-class-counters {
           leaf fc_name_header {
             type string;
           }
           leaf forwarding-class-name {
             type string;
             description
               "Forwarding class name associated with queue";
           }
           leaf fc-input-bytes {
             type int32;
           }
           leaf fc-input-bytes-rate {
             type int32;
             description
               "Input bytes rate";
           }
           leaf fc-output-bytes {
             type int32;
           }
           leaf fc-output-bytes-rate {
             type int32;
             description
               "Output bytes rate";
           }
           leaf fc-input-packets {
             type int32;
           }
           leaf fc-input-packets-rate {
             type int32;
             description
               "Input packets rate";
           }
           leaf fc-output-packets {
             type int32;
           }
           leaf fc-output-packets-rate {
             type int32;
             description
               "Output packets rate";
           }
           leaf input-unicast-bytes {
             type int32;
           }
           leaf output-unicast-bytes {
             type int32;
           }
           leaf input-unicast-packets {
             type int32;
           }
           leaf output-unicast-packets {
             type int32;
           }
           leaf input-multicast-bytes {
             type int32;
           }
           leaf output-multicast-bytes {
             type int32;
           }
           leaf input-multicast-packets {
             type int32;
           }
           leaf output-multicast-packets {
             type int32;
           }
         }
       }
       container keepalive-statistics {
         description
           "Keepalive statistics for this interface";
         leaf keepalive-lmi-descriptor {
           type string;
         }
         leaf keepalive-input-count {
           type int32;
         }
         leaf keepalive-input-time {
           type string;
         }
         leaf keepalive-output-count {
           type int32;
         }
         leaf keepalive-output-time {
           type string;
         }
       }
       container optics-bit-rate {
         leaf bit-rate {
           type string;
           description
             " Optics Bit Rate";
         }
       }
       container optics-fec-statistics {
         leaf fec-corrected-errors {
           type int32;
         }
         leaf fec-valid-time {
           type int32;
         }
         leaf fec-corrected-error-ratio {
           type int32;
         }
         leaf fec-uncorrected-words {
           type int32;
         }
       }
       container optic-fec-mode {
         leaf fec-mode {
           type string;
           description
             "Optics FEC mode";
         }
       }
       container optic-fec-statistics {
         leaf fec-corrected-errors {
           type int32;
         }
         leaf fec-uncorrected-words {
           type int32;
         }
         leaf fec-corrected-error-rate {
           type int32;
         }
         leaf fec-uncorrected-error-rate {
           type int32;
         }
         leaf optic-fec-uncorrected-error-ratio {
           type string;
         }
         leaf fec-valid-time {
           type int32;
         }
         leaf optic-fec-corrected-error-ratio {
           type string;
         }
       }
       container ngpe-ep-vxlan-info {
         leaf ngpe-ep-vtep-address-family {
           type uint32;
           description
             "NGPE EP VxLAN Endpoint IP Address Familiy";
         }
       }
       container traffic-statistics {
         leaf input-bps {
           type int32;
         }
         leaf input-pps {
           type int32;
         }
         leaf output-bps {
           type int32;
         }
         leaf output-pps {
           type int32;
         }
         leaf input-packets {
           type uint64;
         }
         leaf output-packets {
           type uint64;
         }
         container ipv4-traffic-statistics {
           leaf input-bps {
             type int32;
           }
           leaf output-bps {
             type int32;
           }
           leaf input-pps {
             type int32;
           }
           leaf output-pps {
             type int32;
           }
           leaf input-bytes {
             type int32;
           }
           leaf output-bytes {
             type int32;
           }
           leaf input-packets {
             type uint64;
           }
           leaf output-packets {
             type uint64;
           }
         }
         leaf input-bytes {
           type int32;
         }
         leaf output-bytes {
           type int32;
         }
         container ipv6-transit-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-traffic-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-total-statistics {
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
       }
       container multicast-statistics {
         description
           "Multicast statistics for interface";
         leaf multicast-statistics-header {
           type empty;
         }
         container ipv4-multicast-statistics {
           description
             "IPV4 multicast statistics for interface";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
         container ipv6-multicast-statistics {
           description
             "IPV6 multicast statistics for interface";
           leaf input-bytes {
             type int32;
           }
           leaf input-bps {
             type int32;
           }
           leaf output-bytes {
             type int32;
           }
           leaf output-bps {
             type int32;
           }
           leaf input-packets {
             type uint64;
           }
           leaf input-pps {
             type int32;
           }
           leaf output-packets {
             type uint64;
           }
           leaf output-pps {
             type int32;
           }
         }
       }
       container ingress-traffic-statistics {
         description
           "Traffic statistics at ingress before entering Packet Forwarding 
           Engine";
         leaf input-bps {
           type int32;
         }
         leaf input-pps {
           type int32;
         }
         leaf input-drop-bps {
           type int32;
           description
             "Drop rate at ingress in bits per second ";
         }
         leaf input-drop-pps {
           type int32;
           description
             "Drop rate at ingress in packets per second ";
         }
         leaf input-bytes {
           type int32;
         }
         leaf input-packets {
           type uint64;
         }
         leaf input-drop-bytes {
           type int32;
           description
             "Drop statistics at ingress in bytes";
         }
         leaf input-drop-packets {
           type int32;
           description
             "Drop statistics at ingress in packets";
         }
       }
       container active-alarms {
       }
       container active-defects {
       }
       container media-state-information {
       }
       container sonet-errors {
         list media-alarm {
           leaf media-alarm-name {
             type string;
           }
           leaf media-alarm-count {
             type int32;
           }
         }
       }
       container sonet-physical-information {
         list media-alarm {
           leaf media-alarm-name {
             type string;
           }
           leaf media-alarm-seconds {
             type int32;
           }
           leaf media-alarm-count {
             type int32;
           }
           leaf media-alarm-state {
             type string;
           }
         }
       }
       container sonet-section-information {
         list media-alarm {
           leaf media-alarm-name {
             type string;
           }
           leaf media-alarm-seconds {
             type int32;
           }
           leaf media-alarm-count {
             type int32;
           }
           leaf media-alarm-state {
             type string;
           }
         }
       }
       container sonet-line-information {
         list media-alarm {
           leaf media-alarm-name {
             type string;
           }
           leaf media-alarm-seconds {
             type int32;
           }
           leaf media-alarm-count {
             type int32;
           }
           leaf media-alarm-state {
             type string;
           }
         }
       }
       container sonet-path-information {
         list media-alarm {
           leaf media-alarm-name {
             type string;
           }
           leaf media-alarm-seconds {
             type int32;
           }
           leaf media-alarm-count {
             type int32;
           }
           leaf media-alarm-state {
             type string;
           }
         }
       }
       container sonet-vt-information {
         list media-alarm {
           leaf media-alarm-name {
             type string;
           }
           leaf media-alarm-seconds {
             type int32;
           }
           leaf media-alarm-count {
             type int32;
           }
           leaf media-alarm-state {
             type string;
           }
         }
       }
       container otn-errors {
         list media-alarm {
           leaf media-alarm-name {
             type string;
           }
           leaf media-alarm-count {
             type int32;
           }
         }
       }
       container otn-fec-statistics {
         leaf fec-corrected-errors {
           type int32;
         }
         leaf fec-valid-time {
           type int32;
         }
         leaf fec-corrected-error-ratio {
           type int32;
         }
         leaf fec-uncorrected-words {
           type int32;
         }
       }
       container otn-fec-alarms {
         description
           "OTN degraded and excessive FEC error rates";
         list media-alarm {
           leaf media-alarm-name {
             type string;
           }
           leaf media-alarm-seconds {
             type int32;
           }
           leaf media-alarm-count {
             type int32;
           }
           leaf media-alarm-state {
             type string;
           }
         }
       }
       container otn-fec-mode {
         leaf fec-mode {
           type string;
           description
             "Optics FEC mode";
         }
       }
       container otn-otn-mode {
         leaf otn-mode {
           type string;
         }
       }
       container otn-otn-rate {
         leaf otn-rate {
           type string;
         }
       }
       container otn-otn-loopback {
         leaf otn-loopback {
           type string;
         }
       }
       container otn-local-loopback {
         leaf local-loopback {
           type string;
         }
       }
       container otn-payload-prbs {
         leaf payload-prbs {
           type string;
         }
       }
       container otn-laser-enable {
         leaf laser-enable {
           type string;
           description
             "Optics laser status";
         }
       }
       container media-information {
         description
           "Information about media alarms";
         leaf media-type {
           type string;
           description
             "Type of media this information is for";
         }
         list media-alarm {
           leaf media-alarm-name {
             type string;
           }
           leaf media-alarm-count {
             type int32;
           }
           leaf media-alarm-seconds {
             type int32;
           }
           leaf media-alarm-state {
             type string;
           }
           leaf ce-counter-name {
             type string;
             description
               "Circuit Emulation counter information";
           }
           leaf ce-counter-packets {
             type int32;
             description
               "Circuit Emulation number of packets";
           }
           leaf ce-counter-bytes {
             type int32;
             description
               "Circuit Emulation number of bytes";
           }
           leaf ce-counter-count {
             type int32;
             description
               "Circuit Emulation number of event occurrences";
           }
         }
         leaf ds1-timeslots {
           type string;
         }
         leaf ds1-line-encoding {
           type string;
         }
         leaf ds1-byte-encoding {
           type string;
         }
         leaf ds1-data-inversion {
           type string;
         }
         leaf idle-cycle-flag {
           type string;
         }
         leaf start-end-flag {
           type string;
         }
         leaf ds0-byte-encoding {
           type string;
         }
         leaf ds0-data-inversion {
           type string;
         }
         leaf e3-data-inversion {
           type string;
         }
         leaf ds1-buildout {
           type string;
           description
             "Number of feet";
         }
       }
       container ethernet-pcs-statistics {
         description
           "Ethernet PCS statistics";
         leaf bit-error-seconds {
           type int32;
           description
             "Bit error duration";
         }
         leaf errored-blocks-seconds {
           type int32;
           description
             "Errored blocks duration";
         }
       }
       container ethernet-fec-mode {
         description
           "Ethernet FEC Mode";
         leaf enabled_fec_mode {
           type string;
           description
             "Enabled FEC mode: <NONE/FEC74/FEC91/FEC108/FEC161>";
         }
         leaf fec_codeword_size {
           type uint32;
           description
             "FEC Codeword size";
         }
         leaf fec_codeword_rate {
           type jt:unsigned-float;
           description
             "FEC Codeword rate";
         }
       }
       container ethernet-fec-statistics {
         description
           "Ethernet FEC statistics";
         leaf fec_ccw_count {
           type int32;
           description
             "FEC Corrected Error Count";
         }
         leaf fec_nccw_count {
           type int32;
           description
             "FEC Uncorrected Error Count";
         }
         leaf fec_ccw_error_rate {
           type int32;
           description
             "FEC Corrected Error Rate (errors/sec)";
         }
         leaf fec_nccw_error_rate {
           type int32;
           description
             "FEC Uncorrected Error Rate (errors/sec)";
         }
         leaf pre-fec-ber {
           type jt:unsigned-float;
           description
             "PRE_FEC BER";
         }
       }
       container ethernet-fechistogram-statistics {
         description
           "Ethernet Fec Histogram stats";
         leaf bin-num {
           type int32;
           description
             "Bin number";
         }
         leaf sym-live-err {
           type int32;
           description
             "Sym Live Err";
         }
         leaf sym-harvest-err {
           type int32;
           description
             "Sym harvested Err";
         }
         leaf sym-harvest-last-update {
           type string;
           description
             "Sym harvested last update";
         }
       }
       container ctle {
         description
           "Ctle ";
         leaf ctle_value {
           type int32;
           description
             "Ctle value";
         }
       }
       container pre-emphasis {
         description
           "Pre-emphasis ";
         leaf pre_emphasis_value {
           type int32;
           description
             "Pre-emphasis value";
         }
       }
       container differential-amplitude {
         description
           "Differential-amplitude ";
         leaf differential_amplitude_value {
           type int32;
           description
             "Differential-amplitude value";
         }
       }
       container ethernet-mac-statistics {
         description
           "Ethernet MAC statistics";
         leaf input-bytes {
           type int32;
         }
         leaf input-packets {
           type uint64;
         }
         leaf output-bytes {
           type int32;
         }
         leaf output-packets {
           type uint64;
         }
         leaf input-unicasts {
           type int32;
         }
         leaf output-unicasts {
           type int32;
         }
         leaf input-broadcasts {
           type int32;
         }
         leaf output-broadcasts {
           type int32;
         }
         leaf input-multicasts {
           type int32;
         }
         leaf output-multicasts {
           type int32;
         }
         leaf input-crc-errors {
           type int32;
         }
         leaf output-crc-errors {
           type int32;
         }
         leaf input-fifo-errors {
           type int32;
         }
         leaf output-fifo-errors {
           type int32;
         }
         leaf input-dma-errors {
           type int32;
         }
         leaf output-dma-errors {
           type int32;
         }
         leaf input-mac-control-frames {
           type int32;
         }
         leaf output-mac-control-frames {
           type int32;
         }
         leaf input-mac-pause-frames {
           type int32;
         }
         leaf output-mac-pause-frames {
           type int32;
         }
         leaf input-oversized-frames {
           type int32;
         }
         leaf input-jabber-frames {
           type int32;
         }
         leaf input-fragment-frames {
           type int32;
         }
         leaf input-vlan-tagged-frames {
           type int32;
         }
         leaf input-code-violations {
           type int32;
         }
         leaf input-total-errors {
           type int32;
         }
         leaf output-total-errors {
           type int32;
         }
         leaf input-policer-frame-drops {
           type int32;
         }
         leaf input-policer-byte-drops {
           type int32;
         }
       }
       container ethernet-prbs-mode {
         description
           "PRBS Mode";
         leaf prbs-mode {
           type string;
           description
             "PRBS Mode: <Enabled/Disabled>";
         }
       }
       container ethernet-prbs-pattern {
         description
           "PRBS Pattern";
         leaf prbs-pattern {
           type int32;
           description
             "PRBS Pattern";
         }
       }
       container ethernet-prbs-statistics {
         description
           "Ethernet PRBS statistics";
         leaf prbs-lane {
           type int32;
           description
             "PRBS Lane";
         }
         leaf prbs-error-count {
           type int32;
           description
             "PRBS Error Count";
         }
         leaf prbs-loop-count {
           type int32;
           description
             "PRBS Loop Count";
         }
         leaf prbs-ber-sec {
           type int32;
           description
             "PRBS BER seconds";
         }
         leaf prbs-bits {
           type int32;
           description
             "PRBS Bits";
         }
         leaf prbs-run-sec {
           type int32;
           description
             "PRBS Run seconds";
         }
         leaf prbs-state {
           type string;
           description
             "PRBS State";
         }
         leaf prbs-ber-rate {
           type string;
           description
             "PRBS BER rate";
         }
       }
       container smart-sfp-configurable-type {
         leaf smart-sfp-tdm-management {
           type string;
         }
         leaf smart-sfp-mac {
           type jt:mac-addr;
         }
       }
       container smart-sfp-type {
         leaf smart-sfp-module-type {
           type string;
         }
         leaf smart-sfp-present {
           type string;
         }
       }
       container smart-sfp-config {
         leaf tdm-loopback {
           type string;
         }
         leaf dmac-check-enable {
           type string;
         }
         leaf encap-ecid {
           type int32;
         }
         leaf decap-ecid {
           type int32;
         }
         leaf vlan-id-1 {
           type int32;
         }
         leaf vlan-id-2 {
           type int32;
         }
         leaf mode {
           type string;
         }
         leaf chan-dmac {
           type jt:mac-addr;
         }
         leaf ces-psn-port-channel-id-state {
           type string;
         }
         leaf tdm-intf-signal {
           type string;
         }
       }
       list smart-sfp-channel-config {
         key "channel-num";
         description
           "Smart SFP channel config";
         leaf channel-num {
           type uint32;
           description
             "Channel number";
         }
         leaf channel-klm {
           type string;
           description
             "K (TUG3), L (TUG2), M (TU-12/VC-12/E1) Mapping";
         }
         leaf encap-ecid {
           type int32;
         }
         leaf encap-rtp-freq {
           type string;
         }
         leaf decap-ecid {
           type int32;
         }
         leaf decap-timing {
           type string;
         }
         leaf decap-rtp-freq {
           type string;
         }
         leaf ces-psn-mode {
           type string;
         }
         leaf ces-psn-dmac {
           type jt:mac-addr;
         }
         leaf ces-psn-vlan-1 {
           type int32;
         }
         leaf ces-psn-vlan-2 {
           type int32;
         }
         leaf encap-rtphdr-insert {
           type string;
         }
         leaf decap-rtphdr {
           type string;
         }
       }
       container smart-sfp-oc3-statistics {
         leaf fcs-error-count {
           type uint32;
         }
         leaf sec-sefs {
           type uint32;
         }
         leaf sec-es {
           type uint32;
         }
         leaf sec-es-min15 {
           type uint32;
         }
         leaf sec-ses {
           type uint32;
         }
         leaf sec-ses-min15 {
           type uint32;
         }
         leaf sec-cv {
           type uint32;
         }
         leaf sec-cv-min15 {
           type uint32;
         }
         leaf line-es {
           type uint32;
         }
         leaf line-es-min15 {
           type uint32;
         }
         leaf line-ses {
           type uint32;
         }
         leaf line-ses-min15 {
           type uint32;
         }
         leaf line-cv {
           type uint32;
         }
         leaf line-cv-min15 {
           type uint32;
         }
         leaf line-uas {
           type uint32;
         }
         leaf line-uas-min15 {
           type uint32;
         }
         leaf path-es {
           type uint32;
         }
         leaf path-es-min15 {
           type uint32;
         }
         leaf path-ses {
           type uint32;
         }
         leaf path-ses-min15 {
           type uint32;
         }
         leaf path-cv {
           type uint32;
         }
         leaf path-cv-min15 {
           type uint32;
         }
         leaf path-uas {
           type uint32;
         }
         leaf path-uas-min15 {
           type uint32;
         }
       }
       container smart-sfp-e1t1-statistics {
         leaf e1t1-es {
           type uint32;
         }
         leaf e1t1-es-min15 {
           type uint32;
         }
         leaf e1t1-ses {
           type uint32;
         }
         leaf e1t1-ses-min15 {
           type uint32;
         }
         leaf e1t1-uas {
           type uint32;
         }
         leaf e1t1-uas-min15 {
           type uint32;
         }
         leaf e1t1-bes {
           type uint32;
         }
         leaf e1t1-bes-min15 {
           type uint32;
         }
         leaf e1t1-les {
           type uint32;
         }
         leaf e1t1-les-min15 {
           type uint32;
         }
         leaf e1t1-pes {
           type uint32;
         }
         leaf e1t1-pes-min15 {
           type uint32;
         }
         leaf e1t1-psess {
           type uint32;
         }
         leaf e1t1-psess-min15 {
           type uint32;
         }
         leaf e1t1-ces {
           type uint32;
         }
         leaf e1t1-ces-min15 {
           type uint32;
         }
         leaf e1t1-cses {
           type uint32;
         }
         leaf e1t1-cses-min15 {
           type uint32;
         }
         leaf e1t1-sefs {
           type uint32;
         }
         leaf e1t1-sefs-min15 {
           type uint32;
         }
       }
       container smart-sfp-e3t3-statistics {
         leaf e3t3-les {
           type uint32;
         }
         leaf e3t3-les-min15 {
           type uint32;
         }
         leaf e3t3-pes {
           type uint32;
         }
         leaf e3t3-pes-min15 {
           type uint32;
         }
         leaf e3t3-psess {
           type uint32;
         }
         leaf e3t3-psess-min15 {
           type uint32;
         }
         leaf e3t3-ces {
           type uint32;
         }
         leaf e3t3-ces-min15 {
           type uint32;
         }
         leaf e3t3-cses {
           type uint32;
         }
         leaf e3t3-cses-min15 {
           type uint32;
         }
         leaf e3t3-sefs {
           type uint32;
         }
         leaf e3t3-sefs-min15 {
           type uint32;
         }
         leaf e3t3-uas {
           type uint32;
         }
         leaf e3t3-uas-min15 {
           type uint32;
         }
       }
       container fibrechannel-port-flow-control {
         description
           "Fibre Channel interface flow control";
         leaf fibrechannel-port-flow-control-mode {
           type string;
         }
         list fibrechannel-port-flow-control-credits {
           description
             "Generic flow control credits";
           leaf fibrechannel-port-flow-control-credits-subject {
             type string;
           }
           leaf fibrechannel-port-flow-control-credits-assigned {
             type uint64;
           }
           leaf fibrechannel-port-flow-control-credits-available {
             type uint64;
           }
         }
       }
       container fibrechannel-mac-statistics {
         description
           "Fibre Channel MAC statistics";
         container fibrechannel-mac-statistics-generic {
           leaf link-failures {
             type uint64;
           }
           leaf loss-of-sync {
             type uint64;
           }
           leaf loss-of-signal {
             type uint64;
           }
           leaf sw-link-resets {
             type uint64;
           }
           leaf buffer-to-buffer-credit-recovery-lost-frames {
             type uint64;
           }
           leaf buffer-to-buffer-credit-recovery-lost-rrdys {
             type uint64;
           }
         }
         container fibrechannel-mac-statistics-received {
           leaf rx-class-2-frames {
             type uint64;
           }
           leaf rx-class-2-octets {
             type uint64;
           }
           leaf rx-class-3-frames {
             type uint64;
           }
           leaf rx-class-3-octets {
             type uint64;
           }
           leaf rx-class-f-frames {
             type uint64;
           }
           leaf rx-class-f-octets {
             type uint64;
           }
           leaf class-2-discards {
             type uint64;
           }
           leaf class-3-discards {
             type uint64;
           }
           leaf class-f-discards {
             type uint64;
           }
           leaf rx-frames-too-long {
             type uint64;
           }
           leaf rx-frames-too-short {
             type uint64;
           }
           leaf rx-missing-eof {
             type uint64;
           }
           leaf rx-invalid-crcs {
             type uint64;
           }
           leaf rx-link-resets {
             type uint64;
           }
           leaf rx-link-reset-responses {
             type uint64;
           }
           leaf rx-offlines {
             type uint64;
           }
           leaf rx-not-operationals {
             type uint64;
           }
           leaf rx-invalid-tx-words {
             type uint64;
           }
           leaf rx-encoding-disparity-errors {
             type uint64;
           }
           leaf rx-delimiter-errors {
             type uint64;
           }
           leaf rx-input-buffers-full {
             type uint64;
           }
           leaf rx-invalid-ordered-sets {
             type uint64;
           }
           leaf rx-prim-seq-protocol-errors {
             type uint64;
           }
           leaf rx-other-errors {
             type uint64;
           }
         }
         container fibrechannel-mac-statistics-transmitted {
           leaf tx-class-2-frames {
             type uint64;
           }
           leaf tx-class-2-octets {
             type uint64;
           }
           leaf tx-class-3-frames {
             type uint64;
           }
           leaf tx-class-3-octets {
             type uint64;
           }
           leaf tx-class-f-frames {
             type uint64;
           }
           leaf tx-class-f-octets {
             type uint64;
           }
           leaf tx-link-resets {
             type uint64;
           }
           leaf tx-link-reset-responses {
             type uint64;
           }
           leaf tx-offlines {
             type uint64;
           }
           leaf tx-not-operationals {
             type uint64;
           }
           leaf tx-bb-credit-zeroes {
             type uint64;
           }
           leaf tx-other-errors {
             type uint64;
           }
         }
       }
       container ethernet-filter-statistics {
         description
           "Ethernet filter statistics";
         leaf input-reject-count {
           type int32;
         }
         leaf output-packet-pad-count {
           type int32;
         }
         leaf output-packet-error-count {
           type int32;
         }
         leaf input-packets {
           type uint64;
         }
         leaf input-reject-destination-address-count {
           type int32;
         }
         leaf input-reject-source-address-count {
           type int32;
         }
         leaf output-packets {
           type uint64;
         }
         leaf cam-destination-filter-count {
           type int32;
         }
         leaf cam-source-filter-count {
           type int32;
         }
       }
       container ethernet-autonegotiation {
         description
           "Ethernet autonegotiation information";
       }
       container mac-database {
       }
       container dsl-information {
         description
           "Operational information and statistics for ADSL interfaces";
         container dsl-statistics {
           leaf interleaved-rx-cells {
             type int32;
             description
               "Interleaved receiver cells";
           }
           leaf fast-rx-cells {
             type int32;
             description
               "Fast receiver cells";
           }
           leaf interleaved-tx-cells {
             type int32;
             description
               "Interleaved transmitter cells";
           }
           leaf fast-tx-cells {
             type int32;
             description
               "Fast transmitter cells";
           }
         }
       }
       container vdsl-information {
         description
           "Operational information and statistics for VDSL interfaces";
       }
       container dsl-sfp-information {
         description
           "Operational information and statistics for DSL SFP interfaces";
       }
       container shdsl-information {
         description
           "Operational information and statistics for SHDSL interfaces";
       }
       container efm-information {
         description
           "Operational information and statistics for EFM interfaces";
         container efm-line-statistics {
           container active-alarms-efm {
           }
           container active-defects-efm {
           }
           container media-information {
             description
               "Information about media alarms";
             leaf media-type {
               type string;
               description
                 "Type of media this information is for";
             }
             list media-alarm {
               leaf media-alarm-name {
                 type string;
               }
               leaf media-alarm-count {
                 type int32;
               }
               leaf media-alarm-seconds {
                 type int32;
               }
               leaf media-alarm-state {
                 type string;
               }
               leaf ce-counter-name {
                 type string;
                 description
                   "Circuit Emulation counter information";
               }
               leaf ce-counter-packets {
                 type int32;
                 description
                   "Circuit Emulation number of packets";
               }
               leaf ce-counter-bytes {
                 type int32;
                 description
                   "Circuit Emulation number of bytes";
               }
               leaf ce-counter-count {
                 type int32;
                 description
                   "Circuit Emulation number of event occurrences";
               }
             }
             leaf ds1-timeslots {
               type string;
             }
             leaf ds1-line-encoding {
               type string;
             }
             leaf ds1-byte-encoding {
               type string;
             }
             leaf ds1-data-inversion {
               type string;
             }
             leaf idle-cycle-flag {
               type string;
             }
             leaf start-end-flag {
               type string;
             }
             leaf ds0-byte-encoding {
               type string;
             }
             leaf ds0-data-inversion {
               type string;
             }
             leaf e3-data-inversion {
               type string;
             }
             leaf ds1-buildout {
               type string;
               description
                 "Number of feet";
             }
           }
           container shdsl-information {
             description
               "Operational information and statistics for SHDSL interfaces";
           }
         }
       }
       container atm-information {
         description
           "Operational information and statistics for ATM interfaces";
         container plcp-defects {
         }
         container atm-defects {
         }
       }
       container serial-information {
         description
           "Serial interfaces information and statistics";
         leaf dce-loopback-override {
           type string;
         }
         container eia530-control-signal {
         }
       }
       container virtual-path-information {
         description
           "Operational information and statistics for a virtual path";
         leaf cdvt {
           type int32;
         }
         container traffic-statistics {
           leaf input-bps {
             type int32;
           }
           leaf input-pps {
             type int32;
           }
           leaf output-bps {
             type int32;
           }
           leaf output-pps {
             type int32;
           }
           leaf input-packets {
             type uint64;
           }
           leaf output-packets {
             type uint64;
           }
           container ipv4-traffic-statistics {
             leaf input-bps {
               type int32;
             }
             leaf output-bps {
               type int32;
             }
             leaf input-pps {
               type int32;
             }
             leaf output-pps {
               type int32;
             }
             leaf input-bytes {
               type int32;
             }
             leaf output-bytes {
               type int32;
             }
             leaf input-packets {
               type uint64;
             }
             leaf output-packets {
               type uint64;
             }
           }
           leaf input-bytes {
             type int32;
           }
           leaf output-bytes {
             type int32;
           }
           container ipv6-transit-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-traffic-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-total-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
         }
       }
       container ct3-information {
         list interface-tx-queue {
           leaf output-drops-bytes {
             type int32;
           }
         }
       }
       container cds1-information {
         list interface-tx-queue {
           leaf output-drops-bytes {
             type int32;
           }
         }
       }
       container nxds0-information {
         list interface-tx-queue {
           leaf output-drops-bytes {
             type int32;
           }
         }
       }
       list logical-interface {
         description
           "Information about a single logical interface";
         leaf logical-interface-zone-name {
           type string;
           description
             "Zone name for this interface";
         }
         leaf subunit {
           type int32;
           description
             "Subunit for this interface";
         }
         leaf dialer-time-to-disconnect {
           type string;
           description
             "Time for dialer to disconnect due to idle timeout";
         }
         leaf lcp-state {
           type string;
           description
             "State of the Line Control Protocol";
         }
         leaf chap-state {
           type string;
           description
             "State of the Challenge Handshake Authentication Protocol";
         }
         leaf pap-state {
           type string;
           description
             "State of the Password Authentication Protocol";
         }
         container pppoe-information {
           description
             "PPPoE information";
           list pppoe-interface {
             leaf state {
               type string;
               description
                 "State";
             }
             leaf session-id {
               type string;
               description
                 "Session ID";
             }
             leaf ac-name-session {
               type string;
               description
                 "Session AC name";
             }
             leaf remote-mac {
               type string;
               description
                 "Remote MAC address";
             }
             leaf ac-name-config {
               type string;
               description
                 "Configured AC name";
             }
             leaf service-name {
               type string;
               description
                 "Service name";
             }
             leaf auto-reconnect {
               type string;
               description
                 "Autoreconnect timeout";
             }
             leaf idle-timeout {
               type string;
               description
                 "Idle timeout";
             }
             leaf underlying-interface-name {
               type string;
               description
                 "Underlying interface name";
             }
             leaf underlying-interface-index {
               type string;
               description
                 "Underlying interface index";
             }
             leaf padg-credits {
               type int32;
               description
                 "PADG transmit credits";
             }
             leaf pppoe-credit-scale-factor {
               type string;
               description
                 "Scaling factor";
             }
             leaf ignore-eol-tag {
               type string;
               description
                 "Ignore End-of-List TAG";
             }
             leaf ppp-max-payload-tag {
               type int32;
               description
                 "PPP-Max-Payload TAG";
             }
             leaf interface-name {
               type string;
               description
                 "Interface name";
             }
             leaf interface-index {
               type string;
               description
                 "Index";
             }
             leaf aci-iflset-name {
               type string;
               description
                 "ACI Interface Set name";
             }
             leaf aci-iflset-index {
               type string;
               description
                 "ACI Interface Set index";
             }
             leaf ifl-type {
               type string;
               description
                 "Type";
             }
             leaf session-uptime {
               type string;
               description
                 "Duration for which the session has been up";
             }
             leaf dynamic-profile {
               type string;
               description
                 "Dynamic Profile name";
             }
             leaf pppoe-credits {
               type string;
               description
                 "Forwarding credit balances";
             }
             leaf dynamic-interface-bandwidth {
               type string;
               description
                 "Dynamic interface bandwidth";
             }
             leaf agent-circuit-id {
               type string;
               description
                 "Agent Circuit ID";
             }
             leaf agent-remote-id {
               type string;
               description
                 "Agent Remote ID";
             }
             leaf padm-motm {
               type string;
               description
                 "PADM Message of the Moment tag";
             }
             leaf padm-hurl {
               type string;
               description
                 "PADM HTTP URL tag";
             }
             leaf pppoe-relay-session-id {
               type string;
               description
                 "PPPoE Relay Session ID";
             }
           }
         }
         container pppoe-underlying-information {
           description
             "PPPoE Underlying information";
           list pppoe-underlying-interface {
             leaf dynamic-profile {
               type string;
               description
                 "Dynamic Profile name";
             }
             leaf service-name-table {
               type string;
               description
                 "Name of Service Name Table";
             }
             leaf max-sessions {
               type int32;
               description
                 "Maximum number of PPPoE sessions";
             }
             leaf max-sessions-vsa-ignore {
               type string;
               description
                 "Ignore max-sessions VSA";
             }
             leaf duplicate-protection {
               type string;
               description
                 "Duplicate protection mode";
             }
             leaf short-cycle-protection {
               type string;
               description
                 "Short cycle protection mode";
             }
             leaf direct-connect {
               type string;
               description
                 "Direct connect mode";
             }
             leaf ac-name {
               type string;
               description
                 "Access Concentrator name";
             }
             leaf underlying-interface-name {
               type string;
               description
                 "Underlying interface name";
             }
             leaf underlying-interface-index {
               type string;
               description
                 "Underlying interface index";
             }
             leaf encapsulation-type-identifier {
               type string;
               description
                 "Encapsulation type identifier";
             }
             leaf state {
               type string;
               description
                 "State";
             }
             leaf active-sessions {
               type int32;
               description
                 "Number of active PPPoE sessions";
             }
             leaf aci-autosensing {
               type string;
               description
                 "ACI VLAN Autosensing mode";
             }
             leaf line-identity-autosensing {
               type string;
               description
                 "Line Identity Autosensing mode";
             }
           }
         }
         container aci-vlan-information {
           leaf dynamic-profile {
             type string;
             description
               "Dynamic Profile name";
           }
         }
         container line-identity-information {
           leaf dynamic-profile {
             type string;
             description
               "Dynamic Profile name";
           }
           leaf circuit-id {
             type string;
             description
               "Aci vlan attribute";
           }
           leaf remote-id {
             type string;
             description
               "Aci vlan attribute";
           }
           leaf accept-no-ids {
             type string;
             description
               "Aci vlan attribute";
           }
         }
         container demux-information {
           description
             "Demux information";
           container demux-interface {
             leaf demux-underlying-interface-name {
               type string;
               description
                 "Underlying interface name";
             }
             leaf demux-underlying-interface-index {
               type string;
               description
                 "Underlying interface index";
             }
             leaf demux-inet-prefix-type {
               type string;
               description
                 "Prefix type";
             }
             leaf demux-inet-prefix-count {
               type string;
               description
                 "IPv4 Prefix count";
             }
             leaf demux-inet-prefix {
               type string;
               description
                 "IPv4 Prefix";
             }
             leaf demux-inet6-prefix-type {
               type string;
               description
                 "Prefix type";
             }
             leaf demux-inet6-prefix-count {
               type string;
               description
                 "IPv6 Prefix count";
             }
             leaf demux-inet6-prefix {
               type string;
               description
                 "IPv6 Prefix";
             }
           }
         }
         container dual-ad-icl-color-information {
           container dual-ad-icl-color-info {
             description
               "Dual-AD ICL Color Information";
             leaf dual-ad-icl-color-type {
               type uint32;
               description
                 "Dual-AD ICL Color Type";
             }
             leaf dual-ad-icl-color {
               type uint32;
               description
                 "Dual-AD ICL Color";
             }
           }
         }
         container dialer-information {
           description
             "Dialer information";
           leaf dialer-time-to-disconnect {
             type string;
             description
               "Time for dialer to disconnect due to idle timeout";
           }
           container dialer-interface {
             list dial-string-list {
               leaf dial-string {
                 type string;
                 description
                   "Dial string";
               }
             }
             list sub-interface-list {
               leaf sub-interface-name {
                 type string;
                 description
                   "Subordinate interface name";
               }
             }
             list watch-list {
               leaf watch-route {
                 type string;
                 description
                   "Watch route";
               }
             }
           }
         }
         container shared-interface-information {
           description
             "Shared interface information";
           container shared-interface-logical-interface {
             description
               "Shared interface logical interface";
             leaf peer-interface-name {
               type string;
               description
                 "Peer interface name";
             }
             leaf interface-shared-with {
               type string;
               description
                 "Logical interface owner";
             }
             leaf rx-fe {
               type string;
               description
                 "Rx tunnel token forwarding element";
             }
             leaf rx-nhid {
               type string;
               description
                 "Rx tunnel token next hop index";
             }
             leaf tx-fe {
               type string;
               description
                 "Tx tunnel token forwarding element";
             }
             leaf tx-nhid {
               type string;
               description
                 "Tx tunnel token next hop index";
             }
           }
         }
         container mac-database {
         }
         container queue-counters {
           description
             "Queue counter statistics";
           leaf queue-counters-error-message {
             type string;
             description
               "Queue statistics not available for this interface";
           }
           container interface-cos-short-summary {
             description
               "Summary of queue information on an interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           list queue {
             key "queue-number";
             description
               "Counters for a single queue";
             leaf queue-number {
               type uint32;
               description
                 "Queue number";
             }
             leaf queue-counters-queued-packets {
               type int32;
               description
                 "Queued packet count";
             }
             leaf queue-counters-trans-packets {
               type int32;
               description
                 "Total number of transmitted packets";
             }
             leaf queue-counters-total-drop-packets {
               type int32;
               description
                 "Number of total packets dropped at the queue";
             }
             leaf forwarding-class-name {
               type string;
               description
                 "Forwarding class name associated with queue";
             }
             leaf queue-counters-queued-packets-rate {
               type int32;
               description
                 "Rate at which packets are queued";
             }
             leaf queue-counters-queued-bytes {
               type int32;
               description
                 "Queued bytes count";
             }
             leaf queue-counters-queued-bytes-rate {
               type int32;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets-rate {
               type int32;
               description
                 "Rate at which packets are transmitted";
             }
             leaf queue-counters-trans-bytes {
               type int32;
               description
                 "Total number of transmitted bytes";
             }
             leaf queue-counters-trans-bytes-rate {
               type int32;
               description
                 "Rate at which bytes are transmitted";
             }
             leaf queue-counters-tail-drop-packets-na {
               type string;
               description
                 "Number of packets dropped due to tail drop not available";
             }
             leaf queue-counters-tail-drop-packets {
               type int32;
               description
                 "Number of packets dropped at the tail of the queue";
             }
             leaf queue-counters-tail-drop-packets-rate {
               type int32;
               description
                 "Rate at which packets are dropped at tail of queue";
             }
             leaf queue-counters-tail-drop-bytes {
               type int32;
               description
                 "Number of packets dropped at tail drop of the queue";
             }
             leaf queue-counters-tail-drop-bytes-rate {
               type int32;
               description
                 "Number of packets dropped at tail drop of the queue";
             }
             leaf queue-counters-ecn-ce-packets {
               type int32;
               description
                 "Total number of ECN CE packets";
             }
             leaf queue-counters-ecn-ce-packets-rate {
               type int32;
               description
                 "Rate at which ECN CE packets are transmitted";
             }
             leaf queue-counters-ecn-ce-bytes {
               type int32;
               description
                 "Total number of ECN CE bytes";
             }
             leaf queue-counters-ecn-ce-bytes-rate {
               type int32;
               description
                 "Rate at which ECN CE bytes are transmitted";
             }
             leaf queue-counters-rate-limit-drop-packets-na {
               type string;
               description
                 "Number of packets dropped due to rate-limit drop not 
                 available";
             }
             leaf queue-counters-rate-limit-drop-packets {
               type int32;
               description
                 "Number of packets dropped by rate-limit for the queue";
             }
             leaf queue-counters-rate-limit-drop-packets-rate {
               type int32;
               description
                 "Rate at which packets are dropped by rate-limit for the 
                 queue";
             }
             leaf queue-counters-rate-limit-drop-bytes-na {
               type string;
               description
                 "Number of bytes dropped due to tail drop not available";
             }
             leaf queue-counters-rate-limit-drop-bytes {
               type int32;
               description
                 "Number of bytes dropped at the tail of the queue";
             }
             leaf queue-counters-rate-limit-drop-bytes-rate {
               type int32;
               description
                 "Rate at which bytes are dropped at the tail of the queue";
             }
             leaf queue-counters-red-packets-na {
               type string;
               description
                 "Number of packets dropped due to RED not available";
             }
             leaf queue-counters-red-packets {
               type int32;
               description
                 "Number of packets dropped due to RED";
             }
             leaf queue-counters-red-packets-rate {
               type int32;
               description
                 "Rate at which packets are dropped due to RED";
             }
             leaf queue-counters-red-packets-ln {
               type int32;
               description
                 "Number of RED dropped low-loss, non-TCP packets";
             }
             leaf queue-counters-red-packets-rate-ln {
               type int32;
               description
                 "RED drop rate for low-loss, non-TCP packets";
             }
             leaf queue-counters-red-packets-lt {
               type int32;
               description
                 "Number of RED dropped of low-loss, TCP packets";
             }
             leaf queue-counters-red-packets-rate-lt {
               type int32;
               description
                 "RED drop rate for low-loss, TCP packets";
             }
             leaf queue-counters-red-packets-hn {
               type int32;
               description
                 "Number of RED dropped high-loss, non-TCP packets";
             }
             leaf queue-counters-red-packets-rate-hn {
               type int32;
               description
                 "RED drop rate for high-loss, non-TCP packets";
             }
             leaf queue-counters-red-packets-ht {
               type int32;
               description
                 "Number of RED dropped high-loss, TCP packets";
             }
             leaf queue-counters-red-packets-rate-ht {
               type int32;
               description
                 "RED drop rate for high-loss, TCP packets";
             }
             leaf queue-counters-red-packets-low {
               type int32;
               description
                 "Number of RED dropped low-loss packets";
             }
             leaf queue-counters-red-packets-rate-low {
               type int32;
               description
                 "RED drop rate for low-loss packets";
             }
             leaf queue-counters-red-packets-medium-low {
               type int32;
               description
                 "Number of RED dropped medium-low-loss packets";
             }
             leaf queue-counters-red-packets-rate-medium-low {
               type int32;
               description
                 "RED drop rate for medium-low-loss packets";
             }
             leaf queue-counters-red-packets-medium-high {
               type int32;
               description
                 "Number of RED dropped medium-high-loss packets";
             }
             leaf queue-counters-red-packets-rate-medium-high {
               type int32;
               description
                 "RED drop rate for medium-high-loss packets";
             }
             leaf queue-counters-red-packets-medium {
               type int32;
               description
                 "Number of RED dropped medium-loss packets";
             }
             leaf queue-counters-red-packets-rate-medium {
               type int32;
               description
                 "RED drop rate for medium-loss packets";
             }
             leaf queue-counters-red-packets-high {
               type int32;
               description
                 "Number of RED dropped high-loss packets";
             }
             leaf queue-counters-red-packets-rate-high {
               type int32;
               description
                 "RED drop rate for high-loss packets";
             }
             leaf queue-counters-red-bytes-na {
               type string;
               description
                 "Number of bytes dropped due to RED not available";
             }
             leaf queue-counters-red-bytes {
               type int32;
               description
                 "Number of bytes dropped due to RED";
             }
             leaf queue-counters-red-bytes-rate {
               type int32;
               description
                 "Rate at which bytes are dropped due to RED";
             }
             leaf queue-counters-red-bytes-ln {
               type int32;
               description
                 "Number of RED dropped low-loss, non-TCP bytes";
             }
             leaf queue-counters-red-bytes-rate-ln {
               type int32;
               description
                 "RED drop rate for low-loss, non-TCP bytes";
             }
             leaf queue-counters-red-bytes-lt {
               type int32;
               description
                 "Number of RED dropped low-loss, TCP bytes";
             }
             leaf queue-counters-red-bytes-rate-lt {
               type int32;
               description
                 "RED drop rate for low-loss, TCP bytes";
             }
             leaf queue-counters-red-bytes-hn {
               type int32;
               description
                 "Number of RED dropped high-loss, non-TCP bytes";
             }
             leaf queue-counters-red-bytes-rate-hn {
               type int32;
               description
                 "RED drop rate for high-loss, non-TCP bytes";
             }
             leaf queue-counters-red-bytes-ht {
               type int32;
               description
                 "Number of RED dropped high-loss, TCP bytes";
             }
             leaf queue-counters-red-bytes-rate-ht {
               type int32;
               description
                 "RED drop rate for high-loss, TCP bytes";
             }
             leaf queue-counters-red-bytes-low {
               type int32;
               description
                 "Number of RED dropped low-loss bytes";
             }
             leaf queue-counters-red-bytes-rate-low {
               type int32;
               description
                 "RED drop rate for low-loss bytes";
             }
             leaf queue-counters-red-bytes-medium-low {
               type int32;
               description
                 "Number of RED dropped medium-low-loss bytes";
             }
             leaf queue-counters-red-bytes-rate-medium-low {
               type int32;
               description
                 "RED drop rate for medium-low-loss bytes";
             }
             leaf queue-counters-red-bytes-medium-high {
               type int32;
               description
                 "Number of RED dropped medium-high-loss bytes";
             }
             leaf queue-counters-red-bytes-rate-medium-high {
               type int32;
               description
                 "RED drop rate for medium-high-loss bytes";
             }
             leaf queue-counters-red-bytes-medium {
               type int32;
               description
                 "Number of RED dropped medium-loss bytes";
             }
             leaf queue-counters-red-bytes-rate-medium {
               type int32;
               description
                 "RED drop rate for medium-loss bytes";
             }
             leaf queue-counters-red-bytes-high {
               type int32;
               description
                 "Number of RED dropped high-loss bytes";
             }
             leaf queue-counters-red-bytes-rate-high {
               type int32;
               description
                 "RED drop rate for high-loss bytes";
             }
             leaf queue-counters-timestamp {
               type int32;
               description
                 "Last packet enqueued timestamp";
             }
             leaf queue-counters-total-drop-packets-rate {
               type int32;
               description
                 "Number of total packets dropped at the queue";
             }
             leaf queue-counters-total-drop-bytes {
               type int32;
               description
                 "Number of total packets dropped at the queue";
             }
             leaf queue-counters-total-drop-bytes-rate {
               type int32;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
         }
         container voq-counters {
           description
             "VOQ counter statistics";
           leaf voq-counters-error-message {
             type string;
             description
               "VOQ statistics not available for this interface";
           }
           container voq {
             description
               "Counters for a single voq";
             container fpc {
               description
                 "Counters for a single FPC";
               leaf fpc-no {
                 type int32;
                 description
                   "FPC number";
               }
               container pfe {
                 description
                   "Counters for a single PFE";
                 leaf-list pfe-no {
                   type int32;
                   description
                     "PFE number";
                 }
                 leaf voq-counters-tail-drop-packets {
                   type int32;
                   description
                     "Tail DROP packet count";
                 }
                 leaf voq-counters-tail-drop-packets-rate {
                   type int32;
                   description
                     "Rate at which tail packets are dropped";
                 }
                 leaf voq-counters-tail-drop-bytes {
                   type int32;
                   description
                     "Tail DROP bytes count";
                 }
                 leaf voq-counters-tail-drop-bytes-rate {
                   type int32;
                   description
                     "Rate at which tail bytes are dropped";
                 }
                 leaf voq-counters-drop-packets {
                   type int32;
                   description
                     "DROP packet count";
                 }
                 leaf voq-counters-drop-packets-rate {
                   type int32;
                   description
                     "Rate at which packets are dropped";
                 }
                 leaf voq-counters-drop-bytes {
                   type int32;
                   description
                     "DROP bytes count";
                 }
                 leaf voq-counters-drop-bytes-rate {
                   type int32;
                   description
                     "Rate at which bytes are dropped";
                 }
                 leaf voq-counters-queued-packets {
                   type int32;
                   description
                     "QUEUED packets count";
                 }
                 leaf voq-counters-queued-packets-rate {
                   type int32;
                   description
                     "Rate at which packets are queued";
                 }
                 leaf voq-counters-queued-bytes {
                   type int32;
                   description
                     "QUEUED bytes count";
                 }
                 leaf voq-counters-queued-bytes-rate {
                   type int32;
                   description
                     "Rate at which bytes are queued";
                 }
                 leaf voq-counters-transmitted-packets {
                   type int32;
                   description
                     "Transmitted packets count";
                 }
                 leaf voq-counters-transmitted-packets-rate {
                   type int32;
                   description
                     "Rate at which packets are transmitted";
                 }
                 leaf voq-counters-transmitted-bytes {
                   type int32;
                   description
                     "Transmitted bytes count";
                 }
                 leaf voq-counters-transmitted-bytes-rate {
                   type int32;
                   description
                     "Rate at which bytes are transmitted";
                 }
                 leaf voq-counters-queue-depth-bytes-current {
                   type int32;
                   description
                     "Current queue length";
                 }
                 leaf voq-counters-queue-depth-bytes-peak {
                   type int32;
                   description
                     "Peak queue length";
                 }
                 leaf voq-counters-queue-depth-bytes-average {
                   type int32;
                   description
                     "Average queue length";
                 }
               }
             }
             leaf queue-number {
               type uint32;
               description
                 "Queue number";
             }
             leaf forwarding-class-name {
               type string;
               description
                 "Forwarding class name associated with queue";
             }
             leaf restricted-forwarding-class-name {
               type string;
             }
           }
         }
         container ingress-queue-counters {
           description
             "Ingress queue counter statistics";
           list queue {
             key "queue-number";
             description
               "Counters for a single queue";
             leaf queue-number {
               type uint32;
               description
                 "Queue number";
             }
             leaf forwarding-class-name {
               type string;
               description
                 "Forwarding class name associated with queue";
             }
             leaf queue-counters-queued-packets {
               type int32;
               description
                 "Queued packet count";
             }
             leaf queue-counters-queued-packets-rate {
               type int32;
               description
                 "Rate at which packets are queued";
             }
             leaf queue-counters-queued-bytes {
               type int32;
               description
                 "Queued bytes count";
             }
             leaf queue-counters-queued-bytes-rate {
               type int32;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets {
               type int32;
               description
                 "Total number of transmitted packets";
             }
             leaf queue-counters-trans-packets-rate {
               type int32;
               description
                 "Rate at which packets are transmitted";
             }
             leaf queue-counters-trans-bytes {
               type int32;
               description
                 "Total number of transmitted bytes";
             }
             leaf queue-counters-trans-bytes-rate {
               type int32;
               description
                 "Rate at which bytes are transmitted";
             }
             leaf queue-counters-tail-drop-packets-na {
               type string;
               description
                 "Number of packets dropped due to tail drop not available";
             }
             leaf queue-counters-tail-drop-packets {
               type int32;
               description
                 "Number of packets dropped at the tail of the queue";
             }
             leaf queue-counters-tail-drop-packets-rate {
               type int32;
               description
                 "Rate at which packets are dropped at tail of queue";
             }
             leaf queue-counters-tail-drop-bytes {
               type int32;
               description
                 "Number of packets dropped at tail drop of the queue";
             }
             leaf queue-counters-tail-drop-bytes-rate {
               type int32;
               description
                 "Number of packets dropped at tail drop of the queue";
             }
             leaf queue-counters-ecn-ce-packets {
               type int32;
               description
                 "Total number of ECN CE packets";
             }
             leaf queue-counters-ecn-ce-packets-rate {
               type int32;
               description
                 "Rate at which ECN CE packets are transmitted";
             }
             leaf queue-counters-ecn-ce-bytes {
               type int32;
               description
                 "Total number of ECN CE bytes";
             }
             leaf queue-counters-ecn-ce-bytes-rate {
               type int32;
               description
                 "Rate at which ECN CE bytes are transmitted";
             }
             leaf queue-counters-rate-limit-drop-packets-na {
               type string;
               description
                 "Number of packets dropped due to rate-limit drop not 
                 available";
             }
             leaf queue-counters-rate-limit-drop-packets {
               type int32;
               description
                 "Number of packets dropped by rate-limit for the queue";
             }
             leaf queue-counters-rate-limit-drop-packets-rate {
               type int32;
               description
                 "Rate at which packets are dropped by rate-limit for the 
                 queue";
             }
             leaf queue-counters-rate-limit-drop-bytes-na {
               type string;
               description
                 "Number of bytes dropped due to tail drop not available";
             }
             leaf queue-counters-rate-limit-drop-bytes {
               type int32;
               description
                 "Number of bytes dropped at the tail of the queue";
             }
             leaf queue-counters-rate-limit-drop-bytes-rate {
               type int32;
               description
                 "Rate at which bytes are dropped at the tail of the queue";
             }
             leaf queue-counters-red-packets-na {
               type string;
               description
                 "Number of packets dropped due to RED not available";
             }
             leaf queue-counters-red-packets {
               type int32;
               description
                 "Number of packets dropped due to RED";
             }
             leaf queue-counters-red-packets-rate {
               type int32;
               description
                 "Rate at which packets are dropped due to RED";
             }
             leaf queue-counters-red-packets-ln {
               type int32;
               description
                 "Number of RED dropped low-loss, non-TCP packets";
             }
             leaf queue-counters-red-packets-rate-ln {
               type int32;
               description
                 "RED drop rate for low-loss, non-TCP packets";
             }
             leaf queue-counters-red-packets-lt {
               type int32;
               description
                 "Number of RED dropped of low-loss, TCP packets";
             }
             leaf queue-counters-red-packets-rate-lt {
               type int32;
               description
                 "RED drop rate for low-loss, TCP packets";
             }
             leaf queue-counters-red-packets-hn {
               type int32;
               description
                 "Number of RED dropped high-loss, non-TCP packets";
             }
             leaf queue-counters-red-packets-rate-hn {
               type int32;
               description
                 "RED drop rate for high-loss, non-TCP packets";
             }
             leaf queue-counters-red-packets-ht {
               type int32;
               description
                 "Number of RED dropped high-loss, TCP packets";
             }
             leaf queue-counters-red-packets-rate-ht {
               type int32;
               description
                 "RED drop rate for high-loss, TCP packets";
             }
             leaf queue-counters-red-packets-low {
               type int32;
               description
                 "Number of RED dropped low-loss packets";
             }
             leaf queue-counters-red-packets-rate-low {
               type int32;
               description
                 "RED drop rate for low-loss packets";
             }
             leaf queue-counters-red-packets-medium-low {
               type int32;
               description
                 "Number of RED dropped medium-low-loss packets";
             }
             leaf queue-counters-red-packets-rate-medium-low {
               type int32;
               description
                 "RED drop rate for medium-low-loss packets";
             }
             leaf queue-counters-red-packets-medium-high {
               type int32;
               description
                 "Number of RED dropped medium-high-loss packets";
             }
             leaf queue-counters-red-packets-rate-medium-high {
               type int32;
               description
                 "RED drop rate for medium-high-loss packets";
             }
             leaf queue-counters-red-packets-medium {
               type int32;
               description
                 "Number of RED dropped medium-loss packets";
             }
             leaf queue-counters-red-packets-rate-medium {
               type int32;
               description
                 "RED drop rate for medium-loss packets";
             }
             leaf queue-counters-red-packets-high {
               type int32;
               description
                 "Number of RED dropped high-loss packets";
             }
             leaf queue-counters-red-packets-rate-high {
               type int32;
               description
                 "RED drop rate for high-loss packets";
             }
             leaf queue-counters-red-bytes-na {
               type string;
               description
                 "Number of bytes dropped due to RED not available";
             }
             leaf queue-counters-red-bytes {
               type int32;
               description
                 "Number of bytes dropped due to RED";
             }
             leaf queue-counters-red-bytes-rate {
               type int32;
               description
                 "Rate at which bytes are dropped due to RED";
             }
             leaf queue-counters-red-bytes-ln {
               type int32;
               description
                 "Number of RED dropped low-loss, non-TCP bytes";
             }
             leaf queue-counters-red-bytes-rate-ln {
               type int32;
               description
                 "RED drop rate for low-loss, non-TCP bytes";
             }
             leaf queue-counters-red-bytes-lt {
               type int32;
               description
                 "Number of RED dropped low-loss, TCP bytes";
             }
             leaf queue-counters-red-bytes-rate-lt {
               type int32;
               description
                 "RED drop rate for low-loss, TCP bytes";
             }
             leaf queue-counters-red-bytes-hn {
               type int32;
               description
                 "Number of RED dropped high-loss, non-TCP bytes";
             }
             leaf queue-counters-red-bytes-rate-hn {
               type int32;
               description
                 "RED drop rate for high-loss, non-TCP bytes";
             }
             leaf queue-counters-red-bytes-ht {
               type int32;
               description
                 "Number of RED dropped high-loss, TCP bytes";
             }
             leaf queue-counters-red-bytes-rate-ht {
               type int32;
               description
                 "RED drop rate for high-loss, TCP bytes";
             }
             leaf queue-counters-red-bytes-low {
               type int32;
               description
                 "Number of RED dropped low-loss bytes";
             }
             leaf queue-counters-red-bytes-rate-low {
               type int32;
               description
                 "RED drop rate for low-loss bytes";
             }
             leaf queue-counters-red-bytes-medium-low {
               type int32;
               description
                 "Number of RED dropped medium-low-loss bytes";
             }
             leaf queue-counters-red-bytes-rate-medium-low {
               type int32;
               description
                 "RED drop rate for medium-low-loss bytes";
             }
             leaf queue-counters-red-bytes-medium-high {
               type int32;
               description
                 "Number of RED dropped medium-high-loss bytes";
             }
             leaf queue-counters-red-bytes-rate-medium-high {
               type int32;
               description
                 "RED drop rate for medium-high-loss bytes";
             }
             leaf queue-counters-red-bytes-medium {
               type int32;
               description
                 "Number of RED dropped medium-loss bytes";
             }
             leaf queue-counters-red-bytes-rate-medium {
               type int32;
               description
                 "RED drop rate for medium-loss bytes";
             }
             leaf queue-counters-red-bytes-high {
               type int32;
               description
                 "Number of RED dropped high-loss bytes";
             }
             leaf queue-counters-red-bytes-rate-high {
               type int32;
               description
                 "RED drop rate for high-loss bytes";
             }
             leaf queue-counters-timestamp {
               type int32;
               description
                 "Last packet enqueued timestamp";
             }
             leaf queue-counters-total-drop-packets {
               type int32;
               description
                 "Number of total packets dropped at the queue";
             }
             leaf queue-counters-total-drop-packets-rate {
               type int32;
               description
                 "Number of total packets dropped at the queue";
             }
             leaf queue-counters-total-drop-bytes {
               type int32;
               description
                 "Number of total packets dropped at the queue";
             }
             leaf queue-counters-total-drop-bytes-rate {
               type int32;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
           container interface-cos-short-summary {
             description
               "Summary of queue information on an interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           list queue-num-forwarding-class-name-map {
             key "queue-number";
             leaf queue-number {
               type uint32;
               description
                 "Queue number";
             }
             leaf forwarding-class-name {
               type string;
               description
                 "Forwarding class name associated with queue";
             }
           }
         }
         container forwarding-class-counters {
           description
             "Forwarding-class counter statistics";
           leaf forwarding-class-counters-error-message {
             type string;
             description
               "Forwarding-class statistics not available for this interface";
           }
           container ipv4-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container ipv6-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container mpls-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container layer2-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container other-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container protocol-aggregate-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container forwarding-class-statistics {
             container protocol-aggregate-forwarding-class-counters {
             }
             container ipv4-forwarding-class-counters {
             }
             container ipv6-forwarding-class-counters {
             }
             container mpls-forwarding-class-counters {
             }
             container layer2-forwarding-class-counters {
             }
             container other-forwarding-class-counters {
             }
           }
           container forwarding-class-accounting-parameters {
             leaf forwarding-class-accounting-for-protocol {
               type string;
             }
             leaf forwarding-class-accounting-for-traffic-direction {
               type string;
             }
             leaf forwarding-class-accounting-for-traffic-type {
               type string;
             }
             leaf forwarding-class-accounting-overhead-bytes {
               type uint32;
             }
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container multilink-traffic-statistics {
           container bundle {
           }
           container class {
             description
               "Multilink class traffic statistics";
           }
           container multilink-detail-statistics {
             container bundle-detail {
             }
             container class-detail {
             }
           }
           container crtp {
             container crtp-sessions {
               leaf input-frames {
                 type int32;
               }
               leaf output-frames {
                 type int32;
               }
             }
             list crtp-statistics {
               key "name";
               leaf name {
                 type string;
                 description
                   "Name of this item";
               }
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
           }
         }
         container traffic-statistics {
           leaf input-bps {
             type int32;
           }
           leaf input-pps {
             type int32;
           }
           leaf output-bps {
             type int32;
           }
           leaf output-pps {
             type int32;
           }
           leaf input-packets {
             type uint64;
           }
           leaf output-packets {
             type uint64;
           }
           container ipv4-traffic-statistics {
             leaf input-bps {
               type int32;
             }
             leaf output-bps {
               type int32;
             }
             leaf input-pps {
               type int32;
             }
             leaf output-pps {
               type int32;
             }
             leaf input-bytes {
               type int32;
             }
             leaf output-bytes {
               type int32;
             }
             leaf input-packets {
               type uint64;
             }
             leaf output-packets {
               type uint64;
             }
           }
           leaf input-bytes {
             type int32;
           }
           leaf output-bytes {
             type int32;
           }
           container ipv6-transit-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-traffic-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-total-statistics {
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
         }
         container multicast-statistics {
           description
             "Multicast statistics for interface";
           leaf multicast-statistics-header {
             type empty;
           }
           container ipv4-multicast-statistics {
             description
               "IPV4 multicast statistics for interface";
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
           container ipv6-multicast-statistics {
             description
               "IPV6 multicast statistics for interface";
             leaf input-bytes {
               type int32;
             }
             leaf input-bps {
               type int32;
             }
             leaf output-bytes {
               type int32;
             }
             leaf output-bps {
               type int32;
             }
             leaf input-packets {
               type uint64;
             }
             leaf input-pps {
               type int32;
             }
             leaf output-packets {
               type uint64;
             }
             leaf output-pps {
               type int32;
             }
           }
         }
         container ingress-traffic-statistics {
           description
             "Traffic statistics at ingress before entering Packet 
             Forwarding Engine";
           leaf input-bps {
             type int32;
           }
           leaf input-pps {
             type int32;
           }
           leaf input-drop-bps {
             type int32;
             description
               "Drop rate at ingress in bits per second ";
           }
           leaf input-drop-pps {
             type int32;
             description
               "Drop rate at ingress in packets per second ";
           }
           leaf input-bytes {
             type int32;
           }
           leaf input-packets {
             type uint64;
           }
           leaf input-drop-bytes {
             type int32;
             description
               "Drop statistics at ingress in bytes";
           }
           leaf input-drop-packets {
             type int32;
             description
               "Drop statistics at ingress in packets";
           }
         }
         container local-traffic-statistics {
           description
             "Statistics for locally originated traffic";
         }
         container transit-traffic-statistics {
           description
             "Statistics for traffic passing through the Packet Forwarding 
             Engine";
         }
         container layer3-statistics {
         }
         container keepalive-statistics {
           description
             "Keepalive statistics for this interface";
           leaf keepalive-lmi-descriptor {
             type string;
           }
           leaf keepalive-input-count {
             type int32;
           }
           leaf keepalive-input-time {
             type string;
           }
           leaf keepalive-output-count {
             type int32;
           }
           leaf keepalive-output-time {
             type string;
           }
         }
         container virtual-circuit-information {
           description
             "Operational information and statistics for a virtual circuit";
           container traffic-statistics {
             leaf input-bps {
               type int32;
             }
             leaf input-pps {
               type int32;
             }
             leaf output-bps {
               type int32;
             }
             leaf output-pps {
               type int32;
             }
             leaf input-packets {
               type uint64;
             }
             leaf output-packets {
               type uint64;
             }
             container ipv4-traffic-statistics {
               leaf input-bps {
                 type int32;
               }
               leaf output-bps {
                 type int32;
               }
               leaf input-pps {
                 type int32;
               }
               leaf output-pps {
                 type int32;
               }
               leaf input-bytes {
                 type int32;
               }
               leaf output-bytes {
                 type int32;
               }
               leaf input-packets {
                 type uint64;
               }
               leaf output-packets {
                 type uint64;
               }
             }
             leaf input-bytes {
               type int32;
             }
             leaf output-bytes {
               type int32;
             }
             container ipv6-transit-statistics {
               leaf input-bytes {
                 type int32;
               }
               leaf input-bps {
                 type int32;
               }
               leaf output-bytes {
                 type int32;
               }
               leaf output-bps {
                 type int32;
               }
               leaf input-packets {
                 type uint64;
               }
               leaf input-pps {
                 type int32;
               }
               leaf output-packets {
                 type uint64;
               }
               leaf output-pps {
                 type int32;
               }
             }
             container ipv6-traffic-statistics {
               leaf input-bytes {
                 type int32;
               }
               leaf input-bps {
                 type int32;
               }
               leaf output-bytes {
                 type int32;
               }
               leaf output-bps {
                 type int32;
               }
               leaf input-packets {
                 type uint64;
               }
               leaf input-pps {
                 type int32;
               }
               leaf output-packets {
                 type uint64;
               }
               leaf output-pps {
                 type int32;
               }
             }
             container ipv6-total-statistics {
               leaf input-bytes {
                 type int32;
               }
               leaf input-bps {
                 type int32;
               }
               leaf output-bytes {
                 type int32;
               }
               leaf output-bps {
                 type int32;
               }
               leaf input-packets {
                 type uint64;
               }
               leaf input-pps {
                 type int32;
               }
               leaf output-packets {
                 type uint64;
               }
               leaf output-pps {
                 type int32;
               }
             }
           }
           container atm-cos-information {
             leaf vc-cos-mode {
               type string;
               description
                 "Virtual circuit CoS scheduling mode";
             }
             list atm-cos-queue {
               container atm-cos-queue-parameters {
                 leaf cos-forwarding-class-name {
                   type string;
                   description
                     "Forwarding class name associated with queue";
                 }
                 leaf cos-queue-number {
                   type int32;
                   description
                     "Queue number";
                 }
                 leaf scheduling-priority {
                   type string;
                   description
                     "Scheduling priority";
                 }
                 leaf transmit-weight-cells {
                   type int32;
                   description
                     "Weight to apply to scheduling as number of cells";
                 }
                 leaf transmit-weight-percent {
                   type int32;
                   description
                     "Weight to apply to scheduling as fill percentage";
                 }
                 leaf epd-threshold {
                   type int32;
                   description
                     "Early packet drop threshold";
                 }
                 leaf epd-threshold-plp0 {
                   type int32;
                   description
                     "Early packet drop threshold for PLP 0";
                 }
                 leaf epd-threshold-plp1 {
                   type int32;
                   description
                     "Early packet drop threshold for PLP 1";
                 }
                 container linear-red-drop-profile {
                   leaf queue-depth {
                     type int32;
                     description
                       "Maximum queue depth";
                   }
                   leaf low-red {
                     type int32;
                     description
                       "Fill level percentage when linear RED is applied for
                       low PLP";
                   }
                   leaf high-red {
                     type int32;
                     description
                       "Fill level percentage when linear RED is applied for
                       high PLP";
                   }
                   leaf max-low-red {
                     type int32;
                     description
                       "Fill level percentage with 100% packet drop for low 
                       PLP";
                   }
                   leaf max-high-red {
                     type int32;
                     description
                       "Fill level percentage with 100% packet drop for high
                       PLP";
                   }
                 }
               }
               container atm-cos-queue-statistics {
                 leaf atm-output-bytes {
                   type int32;
                 }
                 leaf atm-output-packets {
                   type int32;
                 }
                 leaf atm-packet-drops {
                   type int32;
                 }
               }
               container atm-cos-plp-statistics {
                 leaf atm-plp0-output-bytes {
                   type int32;
                 }
                 leaf atm-plp1-output-bytes {
                   type int32;
                 }
                 leaf atm-plp0-output-packets {
                   type int32;
                 }
                 leaf atm-plp1-output-packets {
                   type int32;
                 }
                 leaf atm-plp0-byte-drops {
                   type int32;
                 }
                 leaf atm-plp1-byte-drops {
                   type int32;
                 }
                 leaf atm-plp0-packet-drops {
                   type int32;
                 }
                 leaf atm-plp1-packet-drops {
                   type int32;
                 }
               }
             }
           }
         }
         container allowed-host-inbound-traffic {
           description
             "List of allowed system services and protocols";
           leaf inbound-all-protocols {
             type empty;
             description
               "All protocols";
           }
           leaf inbound-any-service {
             type empty;
             description
               "Any service";
           }
           leaf inbound-bootp {
             type empty;
             description
               "Bootp and dhcp relay-agent service";
           }
           leaf inbound-bfd {
             type empty;
             description
               "Bidirectional Forwarding Detection";
           }
           leaf inbound-bgp {
             type empty;
             description
               "Border Gateway Protocol";
           }
           leaf inbound-dns {
             type empty;
             description
               "DNS and DNS-proxy service";
           }
           leaf inbound-dvmrp {
             type empty;
             description
               "Distance Vector Multicast Routing Protocol";
           }
           leaf inbound-igmp {
             type empty;
             description
               "Internet Group Management Protocol";
           }
           leaf inbound-ldp {
             type empty;
             description
               "Label Distribution Protocol";
           }
           leaf inbound-msdp {
             type empty;
             description
               "Multicast Source Discovery Protocol";
           }
           leaf inbound-nhrp {
             type empty;
             description
               "Next Hop Resolution Protocol";
           }
           leaf inbound-ospf {
             type empty;
             description
               "Open Shortest Path First";
           }
           leaf inbound-ospf3 {
             type empty;
             description
               "Open Shortest Path First version 3";
           }
           leaf inbound-pgm {
             type empty;
             description
               "Pragmatic General Multicast";
           }
           leaf inbound-pim {
             type empty;
             description
               "Protocol Independent Multicast";
           }
           leaf inbound-rip {
             type empty;
             description
               "Routing Information Protocol";
           }
           leaf inbound-ripng {
             type empty;
             description
               "Routing Information Protocol next generation";
           }
           leaf inbound-router-discovery {
             type empty;
             description
               "Router Discovery";
           }
           leaf inbound-rsvp {
             type empty;
             description
               "Resource Reservation Protocol";
           }
           leaf inbound-sap {
             type empty;
             description
               "Session Announcement Protocol";
           }
           leaf inbound-vrrp {
             type empty;
             description
               "Virtual Router Redundancy Protocol";
           }
           leaf inbound-all-services {
             type empty;
             description
               "All system services";
           }
           leaf inbound-dhcp {
             type empty;
             description
               "Dynamic Host Configuration Protocol";
           }
           leaf inbound-finger {
             type empty;
             description
               "Finger service";
           }
           leaf inbound-ftp {
             type empty;
             description
               "File Transfer Protocol";
           }
           leaf inbound-tftp {
             type empty;
             description
               "Trivial File Transfer Protocol";
           }
           leaf ident-reset {
             type empty;
             description
               "Send back TCP RST to IDENT request for port 113";
           }
           leaf inbound-http {
             type empty;
             description
               "Web management service using HTTP";
           }
           leaf inbound-https {
             type empty;
             description
               "Web management service using HTTP secured by SSL";
           }
           leaf inbound-ike {
             type empty;
             description
               "Internet Key Exchange";
           }
           leaf inbound-netconf {
             type empty;
             description
               "NETCONF service";
           }
           leaf inbound-ping {
             type empty;
             description
               "Internet Control Message Protocol echo requests";
           }
           leaf inbound-reverse-telnet {
             type empty;
             description
               "Reverse telnet service";
           }
           leaf inbound-reverse-ssh {
             type empty;
             description
               "Reverse SSH service";
           }
           leaf inbound-rlogin {
             type empty;
             description
               "Rlogin service";
           }
           leaf inbound-rpm {
             type empty;
             description
               "Real-time performance monitoring";
           }
           leaf inbound-rsh {
             type empty;
             description
               "Rsh service";
           }
           leaf inbound-snmp {
             type empty;
             description
               "Simple Network Management Protocol service";
           }
           leaf inbound-snmp-trap {
             type empty;
             description
               "Simple Network Management Protocol traps";
           }
           leaf inbound-ssh {
             type empty;
             description
               "SSH service";
           }
           leaf inbound-telnet {
             type empty;
             description
               "Telnet service";
           }
           leaf inbound-traceroute {
             type empty;
             description
               "Traceroute service";
           }
           leaf inbound-xnm-clear-text {
             type empty;
             description
               "JUNOScript API for unencrypted traffic over TCP";
           }
           leaf inbound-xnm-ssl {
             type empty;
             description
               "JUNOScript API service over SSL";
           }
           leaf inbound-lsping {
             type empty;
             description
               "Label Switched Path ping service";
           }
           leaf inbound-lsselfping {
             type empty;
             description
               "Label Switched Path self ping service";
           }
           leaf inbound-ntp {
             type empty;
             description
               "Network Time Protocol service";
           }
           leaf inbound-sip {
             type empty;
             description
               "Session Initiation Protocol service";
           }
           leaf inbound-dhcpv6 {
             type empty;
             description
               "Dynamic Host Configuration Protocol for IPv6 service";
           }
           leaf inbound-r2cp {
             type empty;
             description
               "Radio Router Control Protocol service";
           }
           leaf inbound-webapi-clear-text {
             type empty;
             description
               "Webapi service using http";
           }
           leaf inbound-webapi-ssl {
             type empty;
             description
               "Webapi service using HTTP secured by SSL";
           }
           leaf inbound-tcp-encap {
             type empty;
             description
               "Tcp encapsulation service";
           }
           leaf inbound-sdwan-appqoe {
             type empty;
             description
               "Sdwan Appqoe service";
           }
           leaf inbound-high-availability {
             type empty;
             description
               "High Availability  service";
           }
         }
         list address-family {
           container pppoe-underlying-information {
             description
               "PPPoE Underlying information";
             list pppoe-underlying-interface {
               leaf dynamic-profile {
                 type string;
                 description
                   "Dynamic Profile name";
               }
               leaf service-name-table {
                 type string;
                 description
                   "Name of Service Name Table";
               }
               leaf max-sessions {
                 type int32;
                 description
                   "Maximum number of PPPoE sessions";
               }
               leaf max-sessions-vsa-ignore {
                 type string;
                 description
                   "Ignore max-sessions VSA";
               }
               leaf duplicate-protection {
                 type string;
                 description
                   "Duplicate protection mode";
               }
               leaf short-cycle-protection {
                 type string;
                 description
                   "Short cycle protection mode";
               }
               leaf direct-connect {
                 type string;
                 description
                   "Direct connect mode";
               }
               leaf ac-name {
                 type string;
                 description
                   "Access Concentrator name";
               }
               leaf underlying-interface-name {
                 type string;
                 description
                   "Underlying interface name";
               }
               leaf underlying-interface-index {
                 type string;
                 description
                   "Underlying interface index";
               }
               leaf encapsulation-type-identifier {
                 type string;
                 description
                   "Encapsulation type identifier";
               }
               leaf state {
                 type string;
                 description
                   "State";
               }
               leaf active-sessions {
                 type int32;
                 description
                   "Number of active PPPoE sessions";
               }
               leaf aci-autosensing {
                 type string;
                 description
                   "ACI VLAN Autosensing mode";
               }
               leaf line-identity-autosensing {
                 type string;
                 description
                   "Line Identity Autosensing mode";
               }
             }
           }
           list interface-address {
           }
           container destination-class-statistics {
             description
               "Destination class usage (DCU) statistics";
           }
           container source-class-statistics {
             description
               "Source class usage (SCU) statistics";
           }
           list local-bias-information {
             leaf local-bias-vtep-ifl-name {
               type string;
               description
                 "Interface name";
             }
             leaf local-bias-vtep-ifl-index {
               type uint32;
               description
                 "Interface index";
             }
             leaf local-bias-vtep-address {
               type string;
               description
                 "Protocol address of the connection";
             }
           }
         }
         list bridge-iff-properties {
           description
             "Information about Ethernet-switching address family";
         }
         container l2circuit-info {
           leaf out-of-sequence {
             type int32;
           }
           leaf denied-packets {
             type int32;
           }
           leaf cell-bundle-size {
             type int32;
           }
           leaf cell-bundle-timeout {
             type int32;
           }
           leaf cell-timeout-count {
             type int32;
           }
         }
         container media-information {
           description
             "Information about media alarms";
           leaf media-type {
             type string;
             description
               "Type of media this information is for";
           }
           list media-alarm {
             leaf media-alarm-name {
               type string;
             }
             leaf media-alarm-count {
               type int32;
             }
             leaf media-alarm-seconds {
               type int32;
             }
             leaf media-alarm-state {
               type string;
             }
             leaf ce-counter-name {
               type string;
               description
                 "Circuit Emulation counter information";
             }
             leaf ce-counter-packets {
               type int32;
               description
                 "Circuit Emulation number of packets";
             }
             leaf ce-counter-bytes {
               type int32;
               description
                 "Circuit Emulation number of bytes";
             }
             leaf ce-counter-count {
               type int32;
               description
                 "Circuit Emulation number of event occurrences";
             }
           }
           leaf ds1-timeslots {
             type string;
           }
           leaf ds1-line-encoding {
             type string;
           }
           leaf ds1-byte-encoding {
             type string;
           }
           leaf ds1-data-inversion {
             type string;
           }
           leaf idle-cycle-flag {
             type string;
           }
           leaf start-end-flag {
             type string;
           }
           leaf ds0-byte-encoding {
             type string;
           }
           leaf ds0-data-inversion {
             type string;
           }
           leaf e3-data-inversion {
             type string;
           }
           leaf ds1-buildout {
             type string;
             description
               "Number of feet";
           }
         }
         container macsec-statistics {
           description
             "MACSec Statistics ";
           leaf macsec-tx-sc-protected {
             type int32;
             description
               "Protected Secure Channel MACSec packets transmitted";
           }
           leaf macsec-tx-sc-encrypted {
             type int32;
             description
               "Encrypted Secure Channel MACSec packets transmitted";
           }
           leaf macsec-tx-sc-protectedbytes {
             type int32;
             description
               "Protected Secure Channel MACSec bytes transmitted";
           }
           leaf macsec-tx-sc-encryptedbytes {
             type int32;
             description
               "Encrypted Secure Channel MACSec bytes transmitted";
           }
           leaf macsec-rx-sc-ok {
             type int32;
             description
               "OK Secure Association MACSec packets received";
           }
           leaf macsec-rx-sc-validatedbytes {
             type int32;
             description
               "Validated Secure Association MACSec bytes received";
           }
           leaf macsec-rx-sc-decryptedbytes {
             type int32;
             description
               "Validated Secure Association MACSec bytes received";
           }
         }
         container security-input-flow-statistics {
           description
             "Flow input statistics for the interface";
           leaf flow-input-self-packets {
             type int32;
             description
               "Input Self packets";
           }
           leaf flow-input-icmp-packets {
             type int32;
             description
               "Input ICMP packets";
           }
           leaf flow-input-vpn-packets {
             type int32;
             description
               "Input VPN packets";
           }
           leaf flow-input-multicast-packets {
             type int32;
             description
               "Input multicast packets";
           }
           leaf flow-input-policy-bytes {
             type int32;
             description
               "Input policy bytes";
           }
           leaf flow-input-connections {
             type int32;
             description
               "Input connections";
           }
         }
         container security-output-flow-statistics {
           description
             "Flow output statistics for the interface";
           leaf flow-output-multicast-packets {
             type int32;
             description
               "Output multicast packets";
           }
           leaf flow-output-policy-bytes {
             type int32;
             description
               "Output bytes permitted by policy";
           }
         }
         container security-error-flow-statistics {
           description
             "Flow error statistics for the interface";
           leaf flow-error-policy-denied {
             type int32;
             description
               "Policy denied";
           }
           leaf flow-error-no-gate-parent {
             type int32;
             description
               "No parent for gate";
           }
           leaf flow-error-syn-protection {
             type int32;
             description
               "Syn-attack protection";
           }
           leaf flow-error-incoming-nat {
             type int32;
             description
               "Incoming NAT errors";
           }
           leaf flow-error-no-tunnel {
             type int32;
             description
               "No tunnel found";
           }
           leaf flow-error-no-more-session {
             type int32;
             description
               "No more sessions";
           }
           leaf flow-error-invalid-zone {
             type int32;
             description
               "Invalid zone received packet";
           }
           leaf flow-error-user-authentication {
             type int32;
             description
               "User authentication errors";
           }
           leaf flow-error-multiple-auth {
             type int32;
             description
               "Multiple user authentications";
           }
           leaf flow-error-multiple-incoming-nat {
             type int32;
             description
               "Multiple incoming NAT";
           }
           leaf flow-error-address-spoofing {
             type int32;
             description
               "Address spoofing";
           }
           leaf flow-error-null-zone {
             type int32;
             description
               "No zone or NULL zone binding";
           }
           leaf flow-error-no-nat-gate {
             type int32;
             description
               "No NAT gate";
           }
           leaf flow-error-no-minor-session {
             type int32;
             description
               "No minor session";
           }
           leaf flow-error-no-session-gate {
             type int32;
             description
               "No session for a gate";
           }
           leaf flow-error-seq-outside-window {
             type int32;
             description
               "TCP sequence number out of window";
           }
           leaf flow-error-no-route-present {
             type int32;
             description
               "No route present";
           }
           leaf flow-error-authentication-failed {
             type int32;
             description
               "Authentication failed";
           }
           leaf flow-error-security-association-missing {
             type int32;
             description
               "Security association not active";
           }
           leaf flow-error-no-sa-for-spi {
             type int32;
             description
               "No SA for incoming SPI";
           }
           leaf flow-error-no-interest-self-packet {
             type int32;
             description
               "No one interested in self packets";
           }
         }
         container lag-traffic-statistics {
           container lag-multicast-statistics {
             leaf lag-multicast-statistics-header {
               type empty;
             }
             container lag-ipv4-multicast-statistics {
               leaf input-packets {
                 type uint64;
               }
               leaf input-pps {
                 type int32;
               }
               leaf input-bytes {
                 type int32;
               }
               leaf input-bps {
                 type int32;
               }
               leaf output-packets {
                 type uint64;
               }
               leaf output-pps {
                 type int32;
               }
               leaf output-bytes {
                 type int32;
               }
               leaf output-bps {
                 type int32;
               }
             }
             container lag-ipv6-multicast-statistics {
               leaf input-packets {
                 type uint64;
               }
               leaf input-pps {
                 type int32;
               }
               leaf input-bytes {
                 type int32;
               }
               leaf input-bps {
                 type int32;
               }
               leaf output-packets {
                 type uint64;
               }
               leaf output-pps {
                 type int32;
               }
               leaf output-bytes {
                 type int32;
               }
               leaf output-bps {
                 type int32;
               }
             }
           }
           list if-distribution-list-information {
           }
           container ifd-lag-traffic-statistics {
           }
         }
         container ifd-lag-traffic-statistics {
         }
         container layer2-input-policer-statistics {
           description
             "Layer 2 input policer statistics for interface";
           leaf policer-medium-low-frames {
             type int32;
             description
               "Number of loss priority medium low frames";
           }
           leaf policer-medium-low-bytes {
             type int32;
             description
               "Number of loss priority medium low bytes";
           }
           leaf policer-medium-low-rate {
             type int32;
             description
               "Rate of loss priority medium low pkts";
           }
         }
         container layer2-output-policer-statistics {
           description
             "Layer 2 output policer statistics for interface";
           leaf policer-medium-low-frames {
             type int32;
             description
               "Number of loss priority medium low frames";
           }
           leaf policer-medium-low-bytes {
             type int32;
             description
               "Number of loss priority medium low bytes";
           }
           leaf policer-medium-low-rate {
             type int32;
             description
               "Rate of loss priority medium low pkts";
           }
         }
         container mac-policer-information {
           container ether-policer-list {
           }
         }
       }
       container active-alarms-otn {
       }
       container active-defects-otn {
       }
       container active-alarms-optics {
       }
       container active-defects-optics {
       }
       container optics-defect-information {
         list media-alarm {
           leaf media-alarm-name {
             type string;
           }
           leaf media-alarm-seconds {
             type int32;
           }
           leaf media-alarm-count {
             type int32;
           }
           leaf media-alarm-state {
             type string;
           }
         }
       }
       container optics-fec-information {
         list media-alarm {
           leaf media-alarm-name {
             type string;
           }
           leaf media-alarm-seconds {
             type int32;
           }
           leaf media-alarm-count {
             type int32;
           }
           leaf media-alarm-state {
             type string;
           }
         }
       }
       container active-alerts-otn {
       }
       container links {
         description
           "Aggregated SONET/SDH link information";
         list link-entry {
           description
             "SONET/SDH link information";
           leaf sonet-payload-pointer-curptr {
             type string;
             description
               "Value of the SONET/SDH payload pointer, derived from the H1 
               and H2 overhead bytes";
           }
           leaf sonet-payload-pointer-ptrinc-count {
             type string;
             description
               "Number of times the value of the SONET/SDH payload pointer 
               had positive justification";
           }
           leaf sonet-payload-pointer-ptrdec-count {
             type string;
             description
               "Number of times the value of the SONET/SDH payload pointer 
               had negative justification";
           }
           leaf sonet-payload-pointer-newptr-ndf-count {
             type string;
             description
               "Number of times a new payload pointer was created with the 
               New Data Found flag set";
           }
           leaf sonet-rx-overhead {
             type string;
           }
           leaf sonet-tx-overhead {
             type string;
           }
           leaf sonet-rx-path-trace {
             type string;
             description
               "Received SONET path trace";
           }
           leaf sonet-tx-path-trace {
             type string;
             description
               "Transmitted SONET path trace";
           }
           container active-alarms {
           }
           container active-defects {
           }
           container sonet-errors {
             list media-alarm {
               leaf media-alarm-name {
                 type string;
               }
               leaf media-alarm-count {
                 type int32;
               }
             }
           }
           container sonet-physical-information {
             list media-alarm {
               leaf media-alarm-name {
                 type string;
               }
               leaf media-alarm-seconds {
                 type int32;
               }
               leaf media-alarm-count {
                 type int32;
               }
               leaf media-alarm-state {
                 type string;
               }
             }
           }
           container sonet-section-information {
             list media-alarm {
               leaf media-alarm-name {
                 type string;
               }
               leaf media-alarm-seconds {
                 type int32;
               }
               leaf media-alarm-count {
                 type int32;
               }
               leaf media-alarm-state {
                 type string;
               }
             }
           }
           container sonet-line-information {
             list media-alarm {
               leaf media-alarm-name {
                 type string;
               }
               leaf media-alarm-seconds {
                 type int32;
               }
               leaf media-alarm-count {
                 type int32;
               }
               leaf media-alarm-state {
                 type string;
               }
             }
           }
           container sonet-path-information {
             list media-alarm {
               leaf media-alarm-name {
                 type string;
               }
               leaf media-alarm-seconds {
                 type int32;
               }
               leaf media-alarm-count {
                 type int32;
               }
               leaf media-alarm-state {
                 type string;
               }
             }
           }
           container sonet-vt-information {
             list media-alarm {
               leaf media-alarm-name {
                 type string;
               }
               leaf media-alarm-seconds {
                 type int32;
               }
               leaf media-alarm-count {
                 type int32;
               }
               leaf media-alarm-state {
                 type string;
               }
             }
           }
           container optics-diagnostics {
             description
               "Optics diagnostics";
             leaf output-power {
               type string;
               description
                 "Output power (milliwatts)";
             }
             leaf output-power-dbm {
               type string;
               description
                 "Output power (dBm)";
             }
             leaf input-power {
               type string;
               description
                 "Input power (milliwatts)";
             }
             leaf input-power-dbm {
               type string;
               description
                 "Input power (dBm)";
             }
             leaf per-wave-rx-optical-power {
               type string;
               description
                 "Per-wavelength receiver optical power (milliwatts)";
             }
             leaf per-wave-rx-optical-power-dbm {
               type string;
               description
                 "Per-wavelength receiver optical power (dBm)";
             }
             leaf lane-laser-frequency-error {
               type string;
               description
                 "Lane laser frequency error (MHz)";
             }
             leaf tec-current {
               type string;
               description
                 "Tec current";
             }
             leaf residual-isi {
               type string;
               description
                 "Residual ISI";
             }
             container optics-diagnostics-ot {
               description
                 "OT interface optics diagnostics";
               leaf module-temp-fault {
                 type string;
                 description
                   "Module temperature fault";
               }
               leaf specific-hw-fault {
                 type string;
                 description
                   "Specific HW fault";
               }
               leaf internal-power-fault {
                 type string;
                 description
                   "Internal power fault";
               }
               leaf post-therm-fault {
                 type string;
                 description
                   "Power thermal fault";
               }
               leaf post-fault {
                 type string;
                 description
                   "Post fault";
               }
               leaf command-error {
                 type string;
                 description
                   "Command error";
               }
               leaf rx-pll-lock {
                 type string;
                 description
                   "RX PLL lock";
               }
               leaf network-lane-los {
                 type string;
                 description
                   "Network Lane LOS";
               }
               leaf network-lane-lof {
                 type string;
                 description
                   "Network Lane LOF";
               }
               leaf network-lane-oof {
                 type string;
                 description
                   "Network Lane OOF";
               }
               leaf network-lane-lom {
                 type string;
                 description
                   "Network Lane LOM";
               }
               leaf network-lane-oom {
                 type string;
                 description
                   "Network Lane OOM";
               }
               leaf network-lane-otu-bdi {
                 type string;
                 description
                   "Network Lane OTU BDI";
               }
               leaf lane-rx-fifo-error {
                 type string;
                 description
                   "Lane RX FIFO error";
               }
               leaf tx-reference-clock-fault {
                 type string;
                 description
                   "TX reference clock fault";
               }
               leaf rx-modem-sync-fault {
                 type string;
                 description
                   "Rx modem sync fault";
               }
               leaf rx-modem-loss-of-lock {
                 type string;
                 description
                   "RX modem loss of lock";
               }
               leaf rx-loss-of-alignment {
                 type string;
                 description
                   "RX loss of alignment";
               }
               leaf rx-out-of-alignment {
                 type string;
                 description
                   "RX out of alignment";
               }
               leaf rx-timing-fault {
                 type string;
                 description
                   "Rx timing fault";
               }
               leaf link-msg-data-available {
                 type string;
                 description
                   "Link msg data available";
               }
               leaf modulator-bias-control-loop-fail {
                 type string;
                 description
                   "Modulator Bias Control Loop Fail";
               }
               leaf itla-fault {
                 type string;
                 description
                   "ITLA fault";
               }
               leaf dac-calib-fault {
                 type string;
                 description
                   "DAC calib fault";
               }
               leaf adc-calib-fault {
                 type string;
                 description
                   "ADC calib fault";
               }
               leaf prom-fault {
                 type string;
                 description
                   "PROM fault";
               }
               leaf tx-mod-bias-voa-ctrl-loop-high-alarm {
                 type string;
                 description
                   "TX mod bias VOA ctrl loop high alarm";
               }
               leaf tx-mod-bias-voa-ctrl-loop-low-alarm {
                 type string;
                 description
                   "TX mod bias VOA ctrl loop low alarm";
               }
               leaf rx-phase-control-loop-high-alarm {
                 type string;
                 description
                   "RX phase control loop high alarm";
               }
               leaf rx-phase-control-loop-low-alarm {
                 type string;
                 description
                   "RX phase control loop low alarm";
               }
               leaf rx-phase-control-loop-high-warning {
                 type string;
                 description
                   "RX phase control loop high warning";
               }
               leaf rx-phase-control-loop-low-warning {
                 type string;
                 description
                   "RX phase control loop low warning";
               }
               leaf oa-pump-bias-current-high-alarm {
                 type string;
                 description
                   "OA pump bias current high alarm";
               }
               leaf oa-pump-bias-current-low-alarm {
                 type string;
                 description
                   "OA pump bias current low alarm";
               }
               leaf oa-pump-bias-current-high-warning {
                 type string;
                 description
                   "OA pump bias current high warning";
               }
               leaf oa-pump-bias-current-low-warning {
                 type string;
                 description
                   "OA pump bias current low warning";
               }
               leaf tx-jitter-pll-lol-input-nw-lane {
                 type string;
                 description
                   "Tx jitter PLL LOL i/p nw lane";
               }
               leaf tx-out-of-alignment {
                 type string;
                 description
                   "TX out of alignment";
               }
               leaf tx-cmu-lock-fault {
                 type string;
                 description
                   "Tx CMU lock fault";
               }
               leaf adc-signal-below-threshold {
                 type string;
                 description
                   "ADC signal below threshold";
               }
               leaf tx-output-power-adjustment-fault {
                 type string;
                 description
                   "Tx output power adjustment fault";
               }
               leaf tx-output-mod-converge-fault {
                 type string;
                 description
                   "TX output mod converge fault";
               }
               leaf tx-laser-ready-fault {
                 type string;
                 description
                   "Tx laser ready fault";
               }
               leaf tx-laser-ready-off-fault {
                 type string;
                 description
                   "Tx laser ready off fault";
               }
               leaf tx-asic-ready-fault {
                 type string;
                 description
                   "Tx asic ready fault";
               }
               leaf tx-initialization-fault {
                 type string;
                 description
                   "Tx initialization fault";
               }
               leaf rx-demodulator-lock-fault {
                 type string;
                 description
                   "Rx demodulator lock fault";
               }
               leaf rx-dispersion-lock-fault {
                 type string;
                 description
                   "Rx dispersion lock fault";
               }
               leaf rx-adc-output-fault {
                 type string;
                 description
                   "Rx ADC output fault";
               }
               leaf rx-optical-input-fault {
                 type string;
                 description
                   "Rx optical input fault";
               }
               leaf rx-asic-ready-fault {
                 type string;
                 description
                   "Rx asic ready fault";
               }
               leaf rx-initialization-fault {
                 type string;
                 description
                   "Rx initialization fault";
               }
               leaf tx-mod-bias-high-alarm {
                 type string;
                 description
                   "TX modulator bias high alarm";
               }
               leaf tx-mod-bias-low-alarm {
                 type string;
                 description
                   "TX modulator bias low alarm";
               }
               leaf tx-mod-bias-high-warning {
                 type string;
                 description
                   "TX modulator bias high warning";
               }
               leaf tx-mod-bias-low-warning {
                 type string;
                 description
                   "TX modulator bias low warning";
               }
               leaf rx-pwr-high-alarm {
                 type string;
                 description
                   "RX power high alarm";
               }
               leaf rx-pwr-low-alarm {
                 type string;
                 description
                   "RX power low alarm";
               }
               leaf rx-pwr-high-warn {
                 type string;
                 description
                   "RX power high warning";
               }
               leaf rx-pwr-low-warn {
                 type string;
                 description
                   "RX power low warning";
               }
               leaf tx-laser-power-high-alarm {
                 type string;
                 description
                   "TX laser power high alarm";
               }
               leaf tx-laser-power-low-alarm {
                 type string;
                 description
                   "TX laser power low alarm";
               }
               leaf tx-laser-power-high-warn {
                 type string;
                 description
                   "TX laser power high warning";
               }
               leaf tx-laser-power-low-warn {
                 type string;
                 description
                   "TX laser power low warning";
               }
               leaf tx-bias-high-alarm {
                 type string;
                 description
                   "TX laser current high alarm";
               }
               leaf tx-bias-low-alarm {
                 type string;
                 description
                   "TX laser current low alarm";
               }
               leaf tx-bias-high-warn {
                 type string;
                 description
                   "TX laser current high warning";
               }
               leaf tx-bias-low-warn {
                 type string;
                 description
                   "TX laser current low warning";
               }
               leaf tx-laser-temp-high-alarm {
                 type string;
                 description
                   "TX laser temperature high alarm";
               }
               leaf tx-laser-temp-low-alarm {
                 type string;
                 description
                   "TX laser temperature low alarm";
               }
               leaf tx-laser-temp-high-warn {
                 type string;
                 description
                   "TX laser temperature high warning";
               }
               leaf tx-laser-temp-low-warn {
                 type string;
                 description
                   "TX laser temperature low warning";
               }
             }
             list optics-diagnostics-lane-values {
               key "lane-index";
               leaf lane-index {
                 type int32;
               }
               leaf laser-bias-current {
                 type string;
                 description
                   "Laser bias current (milliamperes)";
               }
               leaf laser-bias-current-not-available {
                 type string;
                 description
                   "Laser bias current measurement not available";
               }
               leaf laser-output-power {
                 type string;
                 description
                   "Laser output power (milliwatts)";
               }
               leaf laser-output-power-dbm {
                 type string;
                 description
                   "Laser output power (dBm)";
               }
               leaf output-power {
                 type string;
                 description
                   "Output power (milliwatts)";
               }
               leaf output-power-dbm {
                 type string;
                 description
                   "Output power (dBm)";
               }
               leaf laser-temperature {
                 type string;
                 description
                   "Laser temperature";
               }
               leaf laser-module-temperature {
                 type string;
                 description
                   "Module temperature";
               }
               leaf laser-tx-optical-power {
                 type string;
                 description
                   "Laser transmitter optical power (milliwatts)";
               }
               leaf laser-tx-optical-power-dbm {
                 type string;
                 description
                   "Laser transmitter optical power (dBm)";
               }
               leaf laser-rx-optical-power {
                 type string;
                 description
                   "Laser receiver optical power (milliwatts)";
               }
               leaf laser-rx-optical-power-dbm {
                 type string;
                 description
                   "Laser receiver optical power (dBm)";
               }
               leaf input-power {
                 type string;
                 description
                   "Input power (milliwatts)";
               }
               leaf input-power-dbm {
                 type string;
                 description
                   "Input power (dBm)";
               }
               leaf input-total-power {
                 type string;
                 description
                   "Input power (total) (milliwatts)";
               }
               leaf input-total-power-dbm {
                 type string;
                 description
                   "Input power (dBm)";
               }
               leaf per-wave-rx-optical-power {
                 type string;
                 description
                   "Per-wavelength receiver optical power (milliwatts)";
               }
               leaf per-wave-rx-optical-power-dbm {
                 type string;
                 description
                   "Per-wavelength receiver optical power (dBm)";
               }
               leaf lane-configured-cd {
                 type string;
                 description
                   "Lane configured chromatic dispersion (ps/nm)";
               }
               leaf lane-chromatic-dispersion {
                 type string;
                 description
                   "Lane chromatic dispersion (ps/nm)";
               }
               leaf lane-avg-chromatic-dispersion {
                 type string;
                 description
                   "Lane avg chromatic dispersion (ps/nm)";
               }
               leaf lane-min-chromatic-dispersion {
                 type string;
                 description
                   "Lane min chromatic dispersion (ps/nm)";
               }
               leaf lane-max-chromatic-dispersion {
                 type string;
                 description
                   "Lane max chromatic dispersion (ps/nm)";
               }
               leaf lane-differential-group-delay {
                 type string;
                 description
                   "Lane differential group delay (ps)";
               }
               leaf lane-avg-differential-group-delay {
                 type string;
                 description
                   "Lane avg differential group delay (ps)";
               }
               leaf lane-min-differential-group-delay {
                 type string;
                 description
                   "Lane min differential group delay (ps)";
               }
               leaf lane-max-differential-group-delay {
                 type string;
                 description
                   "Lane max differential group delay (ps)";
               }
               leaf lane-sopmd {
                 type string;
                 description
                   "Lane sopmd";
               }
               leaf lane-avg-sopmd {
                 type string;
                 description
                   "Lane avg sopmd";
               }
               leaf lane-min-sopmd {
                 type string;
                 description
                   "Lane min sopmd";
               }
               leaf lane-max-sopmd {
                 type string;
                 description
                   "Lane max sopmd";
               }
               leaf q-factor {
                 type string;
                 description
                   "Lane q-factor";
               }
               leaf q-factor-not-available {
                 type string;
                 description
                   "Lane q-factor not available";
               }
               leaf q-margin {
                 type string;
                 description
                   "Lane q-margin";
               }
               leaf q-margin-not-available {
                 type string;
                 description
                   "Lane q-margin not available";
               }
               leaf lane-state-of-polarization {
                 type string;
                 description
                   "Lane state of polarization (rad/s)";
               }
               leaf lane-avg-state-of-polarization {
                 type string;
                 description
                   "Lane avg state of polarization (rad/s)";
               }
               leaf lane-min-state-of-polarization {
                 type string;
                 description
                   "Lane min state of polarization (rad/s)";
               }
               leaf lane-max-state-of-polarization {
                 type string;
                 description
                   "Lane max state of polarization (rad/s)";
               }
               leaf lane-polarization-dependent-loss {
                 type string;
                 description
                   "Lane polarization dependent loss (dB)";
               }
               leaf lane-avg-polarization-dependent-loss {
                 type string;
                 description
                   "Lane avg polarization dependent loss (dB)";
               }
               leaf lane-min-polarization-dependent-loss {
                 type string;
                 description
                   "Lane min polarization dependent loss (dB)";
               }
               leaf lane-max-polarization-dependent-loss {
                 type string;
                 description
                   "Lane max polarization dependent loss (dB)";
               }
               leaf lane-q2-factor {
                 type string;
                 description
                   "Lane Q2 factor (dB)";
               }
               leaf lane-q-value {
                 type string;
                 description
                   "Lane q value (dB)";
               }
               leaf lane-avg-q-value {
                 type string;
                 description
                   "Lane avg q value (dB)";
               }
               leaf lane-min-q-value {
                 type string;
                 description
                   "Lane min q value (dB)";
               }
               leaf lane-max-q-value {
                 type string;
                 description
                   "Lane max q value (dB)";
               }
               leaf lane-carrier-frequency-offset {
                 type string;
                 description
                   "Lane carrier frequency offset (MHz)";
               }
               leaf lane-avg-carrier-frequency-offset {
                 type string;
                 description
                   "Lane avg carrier frequency offset (MHz)";
               }
               leaf lane-min-carrier-frequency-offset {
                 type string;
                 description
                   "Lane min carrier frequency offset (MHz)";
               }
               leaf lane-max-carrier-frequency-offset {
                 type string;
                 description
                   "Lane max carrier frequency offset (MHz)";
               }
               leaf lane-electrical-snr {
                 type string;
                 description
                   "Lane electrical SNR (dB)";
               }
               leaf lane-snr {
                 type string;
                 description
                   "Lane snr (dB)";
               }
               leaf lane-avg-snr {
                 type string;
                 description
                   "Lane avg snr (dB)";
               }
               leaf lane-min-snr {
                 type string;
                 description
                   "Lane min snr (dB)";
               }
               leaf lane-max-snr {
                 type string;
                 description
                   "Lane max snr (dB)";
               }
               leaf lane-rx-laser-bias {
                 type string;
                 description
                   "Lane rx laser bias (mA)";
               }
               leaf lane-rx-laser-power {
                 type string;
                 description
                   "Lane rx laser power (dBm)";
               }
               leaf lane-rx-laser-temp {
                 type string;
                 description
                   "Lane rx laser temp (C)";
               }
               leaf lane-tx-modulator-bias-x-i {
                 type string;
                 description
                   "Lane tx modulator bias x i (mV)";
               }
               leaf lane-tx-modulator-bias-x-q {
                 type string;
                 description
                   "Lane tx modulator bias x q (mV)";
               }
               leaf lane-tx-modulator-bias-y-i {
                 type string;
                 description
                   "Lane tx modulator bias y i (mV)";
               }
               leaf lane-tx-modulator-bias-y-q {
                 type string;
                 description
                   "Lane tx modulator bias y q (mV)";
               }
               leaf lane-tx-modulator-bias-x-phase {
                 type string;
                 description
                   "Lane tx modulator bias x phase (mV)";
               }
               leaf lane-tx-modulator-bias-y-phase {
                 type string;
                 description
                   "Lane tx modulator bias y phase (mV)";
               }
               leaf tx-input-equalization {
                 type string;
                 description
                   "Tx input equalization";
               }
               leaf rx-output-amplitude {
                 type string;
                 description
                   "Rx output amplitude";
               }
               leaf rx-output-pre-emphasis {
                 type string;
                 description
                   "Rx output pre epmhasis";
               }
               leaf lane-laser-frequency-error {
                 type string;
                 description
                   "Lane laser frequency error (MHz)";
               }
               leaf tec-current {
                 type string;
                 description
                   "Tec current";
               }
               leaf residual-isi {
                 type string;
                 description
                   "Residual ISI";
               }
               leaf pam-histogram {
                 type string;
                 description
                   "PAM histogram";
               }
               leaf laser-bias-current-high-alarm {
                 type string;
                 description
                   "Laser bias current high alarm";
               }
               leaf laser-bias-current-low-alarm {
                 type string;
                 description
                   "Laser bias current low alarm";
               }
               leaf laser-bias-current-high-warn {
                 type string;
                 description
                   "Laser bias current high warning";
               }
               leaf laser-bias-current-low-warn {
                 type string;
                 description
                   "Laser bias current low warning";
               }
               leaf laser-tx-power-high-alarm {
                 type string;
                 description
                   "Laser output power high alarm";
               }
               leaf laser-tx-power-low-alarm {
                 type string;
                 description
                   "Laser output power low alarm";
               }
               leaf laser-tx-power-high-warn {
                 type string;
                 description
                   "Laser output power high warning";
               }
               leaf laser-tx-power-low-warn {
                 type string;
                 description
                   "Laser output power low warning";
               }
               leaf tx-power-high-alarm {
                 type string;
                 description
                   "Tx power high alarm";
               }
               leaf tx-power-low-alarm {
                 type string;
                 description
                   "Tx power low alarm";
               }
               leaf tx-power-high-warn {
                 type string;
                 description
                   "Tx power high warning";
               }
               leaf tx-power-low-warn {
                 type string;
                 description
                   "Tx power low warning";
               }
               leaf laser-temp-high-alarm {
                 type string;
                 description
                   "Laser temperature high alarm";
               }
               leaf laser-temp-low-alarm {
                 type string;
                 description
                   "Laser temperature low alarm";
               }
               leaf laser-temp-high-warn {
                 type string;
                 description
                   "Laser temperature high warning";
               }
               leaf laser-temp-low-warn {
                 type string;
                 description
                   "Laser temperature low warning";
               }
               leaf laser-rx-power-high-alarm {
                 type string;
                 description
                   "Laser receiver power high alarm";
               }
               leaf laser-rx-power-low-alarm {
                 type string;
                 description
                   "Laser receiver power low alarm";
               }
               leaf laser-rx-power-high-warn {
                 type string;
                 description
                   "Laser receiver power high warning";
               }
               leaf laser-rx-power-low-warn {
                 type string;
                 description
                   "Laser receiver power low warning";
               }
               leaf rx-power-high-alarm {
                 type string;
                 description
                   "Receiver power high alarm";
               }
               leaf rx-power-low-alarm {
                 type string;
                 description
                   "Receiver power low alarm";
               }
               leaf rx-power-high-warn {
                 type string;
                 description
                   "Receiver power high warning";
               }
               leaf rx-power-low-warn {
                 type string;
                 description
                   "Receiver power low warning";
               }
               leaf tx-loss-of-signal-functionality-alarm {
                 type string;
                 description
                   "Tx loss of signal functionality alarm";
               }
               leaf rx-loss-of-signal-functionality-alarm {
                 type string;
                 description
                   "Rx loss of signal functionality alarm";
               }
               leaf tx-cdr-loss-of-lock-alarm {
                 type string;
                 description
                   "Tx CDR loss of lock alarm";
               }
               leaf tx-loss-of-signal-alarm {
                 type string;
                 description
                   "Transmitter loss of signal alarm";
               }
               leaf rx-loss-of-signal-alarm {
                 type string;
                 description
                   "Receiver loss of signal alarm";
               }
               leaf tx-laser-disabled-alarm {
                 type string;
                 description
                   "Tx laser disabled alarm";
               }
               leaf rx-cdr-loss-of-lock-alarm {
                 type string;
                 description
                   "Receiver CDR loss of lock alarm";
               }
               leaf tec-fault-alarm {
                 type string;
                 description
                   "TEC fault alarm";
               }
               leaf wavelength-unlocked-alarm {
                 type string;
                 description
                   "Wavelength unlocked alarm";
               }
               leaf apd-supply-fault-alarm {
                 type string;
                 description
                   "APD supply fault alarm";
               }
               leaf tx-channel-disabled-alarm {
                 type string;
                 description
                   "Tx channel disabled alarm";
               }
               leaf rx-channel-disabled-alarm {
                 type string;
                 description
                   "Rx channel disabled alarm";
               }
               leaf tx-output-disabled-alarm {
                 type string;
                 description
                   "Rx laser disabled alarm";
               }
               leaf rx-output-disabled-alarm {
                 type string;
                 description
                   "Rx laser disabled alarm";
               }
               leaf tx-squelch-disabled-alarm {
                 type string;
                 description
                   "Tx squelch disabled alarm";
               }
               leaf rx-squelch-disabled-alarm {
                 type string;
                 description
                   "Rx squelch disabled alarm";
               }
               leaf laser-end-of-life-alarm {
                 type string;
                 description
                   "Laser end-of-life alarm";
               }
               leaf lane-cd {
                 type string;
                 description
                   "Lane chromatic dispersion";
               }
               leaf lane-dgd {
                 type string;
                 description
                   "Lane differential group delay";
               }
               leaf lane-cfo {
                 type string;
                 description
                   "Lane carrier frequency offset";
               }
               leaf lane-pdl {
                 type string;
                 description
                   "Lane polarization dependent loss";
               }
               leaf lane-osnr {
                 type string;
                 description
                   "Optical signal-to-noise ratio(dB)";
               }
             }
           }
           list optics-chromatics {
             key "optics-chromatic-diagnostics-support";
             leaf optics-chromatic-diagnostics-support {
               type string;
               description
                 "Optics chromatic not supported for interface";
             }
             leaf opticstype {
               type string;
               description
                 "Type of optical module";
             }
             list optics-chromatic {
               key "supported-cd supported-mediaid";
               leaf supported-speed {
                 type string;
                 description
                   "Supported Speed";
               }
               leaf supported-cd {
                 type string;
                 description
                   "Supported Chromatic Dispersion";
               }
               leaf supported-distance {
                 type string;
                 description
                   "Supported Distance";
               }
               leaf supported-mediaid {
                 type string;
                 description
                   "Supported Mediaid";
               }
             }
           }
         }
       }
       container macsec-statistics {
         description
           "MACSec Statistics ";
         leaf macsec-tx-sc-protected {
           type int32;
           description
             "Protected Secure Channel MACSec packets transmitted";
         }
         leaf macsec-tx-sc-encrypted {
           type int32;
           description
             "Encrypted Secure Channel MACSec packets transmitted";
         }
         leaf macsec-tx-sc-protectedbytes {
           type int32;
           description
             "Protected Secure Channel MACSec bytes transmitted";
         }
         leaf macsec-tx-sc-encryptedbytes {
           type int32;
           description
             "Encrypted Secure Channel MACSec bytes transmitted";
         }
         leaf macsec-rx-sc-ok {
           type int32;
           description
             "OK Secure Association MACSec packets received";
         }
         leaf macsec-rx-sc-validatedbytes {
           type int32;
           description
             "Validated Secure Association MACSec bytes received";
         }
         leaf macsec-rx-sc-decryptedbytes {
           type int32;
           description
             "Validated Secure Association MACSec bytes received";
         }
       }
       container peer-configuration-status {
         description
           "Nonmatching DCE end DLCIs";
         leaf peer-nonmatching-dlci {
           type int32;
           description
             "DCE end DLCIs that does not match the DTE";
         }
       }
       container lsi-traffic-statistics {
         leaf input-bytes {
           type int32;
         }
         leaf input-bps {
           type int32;
         }
         leaf input-packets {
           type uint64;
         }
         leaf input-pps {
           type int32;
         }
       }
       container stp-traffic-statistics {
         leaf stp-input-bytes-dropped {
           type int32;
           description
             "Drop statistics due to stp state at ingress in bytes";
         }
         leaf stp-output-bytes-dropped {
           type int32;
           description
             "Drop statistics due to stp state at egress in bytes";
         }
         leaf stp-input-packets-dropped {
           type int32;
           description
             "Drop statistics due to stp state at ingress in packets";
         }
         leaf stp-output-packets-dropped {
           type int32;
           description
             "Drop statistics due to stp state at egress in packets";
         }
       }
       container ethernet-rpf-counter-stats {
         leaf ethernet-rpf-ipv4-rpf-bytes {
           type int32;
           description
             "Counter for ipv4 rpf byptes";
         }
         leaf ethernet-rpf-ipv4-rpf-packets {
           type int32;
           description
             "Counter for ipv4 rpf packets";
         }
         leaf ethernet-rpf-ipv6-rpf-bytes {
           type int32;
           description
             "Counter for ipv6 rpf byptes";
         }
         leaf ethernet-rpf-ipv6-rpf-packets {
           type int32;
           description
             "Counter for ipv6 rpf packets";
         }
       }
       container af-fe-info {
       }
       container af-fe-lb-stats-info {
       }
       container af-fe-q-pkts {
       }
       container af-fe-q-bytes {
       }
       container chassis-queue-counters {
         description
           "Chassis queue counter statistics";
         container interface-chassis-cos-summary {
           description
             "Packet Forwarding Engine chassis forwarding class and queue 
             information for an interface";
           leaf intf-cos-chassis-num-queues-supported {
             type int32;
             description
               "Number of Packet Forwarding Engine chassis queues the 
               interface supports";
           }
           leaf intf-cos-chassis-num-queues-in-use {
             type int32;
             description
               "Number of Packet Forwarding Engine chassis queues in use on 
               the interface";
           }
         }
         list queue {
           key "queue-number";
           description
             "Counters for a single queue";
           leaf queue-number {
             type uint32;
             description
               "Queue number";
           }
           leaf forwarding-class-name {
             type string;
             description
               "Forwarding class name associated with queue";
           }
           leaf queue-counters-queued-packets {
             type int32;
             description
               "Queued packet count";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-queued-packets-na {
             type string;
             description
               "Queued packets not available";
           }
           leaf queue-counters-queued-bytes-na {
             type string;
             description
               "Queued bytes not available";
           }
           leaf queue-counters-trans-packets {
             type int32;
             description
               "Total number of transmitted packets";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets-na {
             type string;
             description
               "Number of packets dropped due to tail drop not available";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of packets dropped at tail drop of the queue";
           }
           leaf queue-counters-tail-drop-bytes-rate {
             type int32;
             description
               "Number of packets dropped at tail drop of the queue";
           }
           leaf queue-counters-ecn-ce-packets {
             type int32;
             description
               "Total number of ECN CE packets";
           }
           leaf queue-counters-ecn-ce-packets-rate {
             type int32;
             description
               "Rate at which ECN CE packets are transmitted";
           }
           leaf queue-counters-ecn-ce-bytes {
             type int32;
             description
               "Total number of ECN CE bytes";
           }
           leaf queue-counters-ecn-ce-bytes-rate {
             type int32;
             description
               "Rate at which ECN CE bytes are transmitted";
           }
           leaf queue-counters-rate-limit-drop-packets-na {
             type string;
             description
               "Number of packets dropped due to rate-limit drop not 
               available";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes-na {
             type string;
             description
               "Number of bytes dropped due to tail drop not available";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets-na {
             type string;
             description
               "Number of packets dropped due to RED not available";
           }
           leaf queue-counters-red-packets {
             type int32;
             description
               "Number of packets dropped due to RED";
           }
           leaf queue-counters-red-packets-rate {
             type int32;
             description
               "Rate at which packets are dropped due to RED";
           }
           leaf queue-counters-red-packets-ln {
             type int32;
             description
               "Number of RED dropped low-loss, non-TCP packets";
           }
           leaf queue-counters-red-packets-rate-ln {
             type int32;
             description
               "RED drop rate for low-loss, non-TCP packets";
           }
           leaf queue-counters-red-packets-lt {
             type int32;
             description
               "Number of RED dropped of low-loss, TCP packets";
           }
           leaf queue-counters-red-packets-rate-lt {
             type int32;
             description
               "RED drop rate for low-loss, TCP packets";
           }
           leaf queue-counters-red-packets-hn {
             type int32;
             description
               "Number of RED dropped high-loss, non-TCP packets";
           }
           leaf queue-counters-red-packets-rate-hn {
             type int32;
             description
               "RED drop rate for high-loss, non-TCP packets";
           }
           leaf queue-counters-red-packets-ht {
             type int32;
             description
               "Number of RED dropped high-loss, TCP packets";
           }
           leaf queue-counters-red-packets-rate-ht {
             type int32;
             description
               "RED drop rate for high-loss, TCP packets";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-medium {
             type int32;
             description
               "Number of RED dropped medium-loss packets";
           }
           leaf queue-counters-red-packets-rate-medium {
             type int32;
             description
               "RED drop rate for medium-loss packets";
           }
           leaf queue-counters-red-packets-high {
             type int32;
             description
               "Number of RED dropped high-loss packets";
           }
           leaf queue-counters-red-packets-rate-high {
             type int32;
             description
               "RED drop rate for high-loss packets";
           }
           leaf queue-counters-red-bytes-na {
             type string;
             description
               "Number of bytes dropped due to RED not available";
           }
           leaf queue-counters-red-bytes {
             type int32;
             description
               "Number of bytes dropped due to RED";
           }
           leaf queue-counters-red-bytes-rate {
             type int32;
             description
               "Rate at which bytes are dropped due to RED";
           }
           leaf queue-counters-red-bytes-ln {
             type int32;
             description
               "Number of RED dropped low-loss, non-TCP bytes";
           }
           leaf queue-counters-red-bytes-rate-ln {
             type int32;
             description
               "RED drop rate for low-loss, non-TCP bytes";
           }
           leaf queue-counters-red-bytes-lt {
             type int32;
             description
               "Number of RED dropped low-loss, TCP bytes";
           }
           leaf queue-counters-red-bytes-rate-lt {
             type int32;
             description
               "RED drop rate for low-loss, TCP bytes";
           }
           leaf queue-counters-red-bytes-hn {
             type int32;
             description
               "Number of RED dropped high-loss, non-TCP bytes";
           }
           leaf queue-counters-red-bytes-rate-hn {
             type int32;
             description
               "RED drop rate for high-loss, non-TCP bytes";
           }
           leaf queue-counters-red-bytes-ht {
             type int32;
             description
               "Number of RED dropped high-loss, TCP bytes";
           }
           leaf queue-counters-red-bytes-rate-ht {
             type int32;
             description
               "RED drop rate for high-loss, TCP bytes";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-medium {
             type int32;
             description
               "Number of RED dropped medium-loss bytes";
           }
           leaf queue-counters-red-bytes-rate-medium {
             type int32;
             description
               "RED drop rate for medium-loss bytes";
           }
           leaf queue-counters-red-bytes-high {
             type int32;
             description
               "Number of RED dropped high-loss bytes";
           }
           leaf queue-counters-red-bytes-rate-high {
             type int32;
             description
               "RED drop rate for high-loss bytes";
           }
           leaf queue-counters-timestamp {
             type int32;
             description
               "Last packet enqueued timestamp";
           }
           leaf queue-counters-total-drop-packets {
             type int32;
             description
               "Number of total packets dropped at the queue";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
           leaf queue-counters-reserved-buffer-packets {
             type int32;
             description
               "Queues's usage of reserved buffer pool in pkts";
           }
           leaf queue-counters-reserved-buffer-bytes {
             type int32;
             description
               "Queues's usage of reserved buffer pool in bytes";
           }
           leaf queue-counters-shared-buffer-packets {
             type int32;
             description
               "Queues's usage of shared buffer pool in pkts";
           }
           leaf queue-counters-shared-buffer-bytes {
             type int32;
             description
               "Queues's usage of shared buffer pool in bytes";
           }
           leaf queue-counters-depth-average {
             type int32;
             description
               "Time averaged queue depth";
           }
           leaf queue-counters-depth-current {
             type int32;
             description
               "Current instantaneous queue depth";
           }
           leaf queue-counters-depth-peak {
             type int32;
             description
               "Peak queue depth";
           }
           leaf queue-counters-depth-max {
             type int32;
             description
               "Maximum queue depth attained";
           }
           leaf queue-counters-srx-reserved-buffer-bytes {
             type int32;
             description
               "Queues's usage of reserved buffer pool in bytes";
           }
           leaf queue-counters-srx-depth-current {
             type int32;
             description
               "Current instantaneous queue depth";
           }
         }
       }
       container ingress-queue-counters {
         description
           "Ingress queue counter statistics";
         list queue {
           key "queue-number";
           description
             "Counters for a single queue";
           leaf queue-number {
             type uint32;
             description
               "Queue number";
           }
           leaf forwarding-class-name {
             type string;
             description
               "Forwarding class name associated with queue";
           }
           leaf queue-counters-queued-packets {
             type int32;
             description
               "Queued packet count";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-queued-packets-na {
             type string;
             description
               "Queued packets not available";
           }
           leaf queue-counters-queued-bytes-na {
             type string;
             description
               "Queued bytes not available";
           }
           leaf queue-counters-trans-packets {
             type int32;
             description
               "Total number of transmitted packets";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets-na {
             type string;
             description
               "Number of packets dropped due to tail drop not available";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of packets dropped at tail drop of the queue";
           }
           leaf queue-counters-tail-drop-bytes-rate {
             type int32;
             description
               "Number of packets dropped at tail drop of the queue";
           }
           leaf queue-counters-ecn-ce-packets {
             type int32;
             description
               "Total number of ECN CE packets";
           }
           leaf queue-counters-ecn-ce-packets-rate {
             type int32;
             description
               "Rate at which ECN CE packets are transmitted";
           }
           leaf queue-counters-ecn-ce-bytes {
             type int32;
             description
               "Total number of ECN CE bytes";
           }
           leaf queue-counters-ecn-ce-bytes-rate {
             type int32;
             description
               "Rate at which ECN CE bytes are transmitted";
           }
           leaf queue-counters-rate-limit-drop-packets-na {
             type string;
             description
               "Number of packets dropped due to rate-limit drop not 
               available";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes-na {
             type string;
             description
               "Number of bytes dropped due to tail drop not available";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets-na {
             type string;
             description
               "Number of packets dropped due to RED not available";
           }
           leaf queue-counters-red-packets {
             type int32;
             description
               "Number of packets dropped due to RED";
           }
           leaf queue-counters-red-packets-rate {
             type int32;
             description
               "Rate at which packets are dropped due to RED";
           }
           leaf queue-counters-red-packets-ln {
             type int32;
             description
               "Number of RED dropped low-loss, non-TCP packets";
           }
           leaf queue-counters-red-packets-rate-ln {
             type int32;
             description
               "RED drop rate for low-loss, non-TCP packets";
           }
           leaf queue-counters-red-packets-lt {
             type int32;
             description
               "Number of RED dropped of low-loss, TCP packets";
           }
           leaf queue-counters-red-packets-rate-lt {
             type int32;
             description
               "RED drop rate for low-loss, TCP packets";
           }
           leaf queue-counters-red-packets-hn {
             type int32;
             description
               "Number of RED dropped high-loss, non-TCP packets";
           }
           leaf queue-counters-red-packets-rate-hn {
             type int32;
             description
               "RED drop rate for high-loss, non-TCP packets";
           }
           leaf queue-counters-red-packets-ht {
             type int32;
             description
               "Number of RED dropped high-loss, TCP packets";
           }
           leaf queue-counters-red-packets-rate-ht {
             type int32;
             description
               "RED drop rate for high-loss, TCP packets";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-medium {
             type int32;
             description
               "Number of RED dropped medium-loss packets";
           }
           leaf queue-counters-red-packets-rate-medium {
             type int32;
             description
               "RED drop rate for medium-loss packets";
           }
           leaf queue-counters-red-packets-high {
             type int32;
             description
               "Number of RED dropped high-loss packets";
           }
           leaf queue-counters-red-packets-rate-high {
             type int32;
             description
               "RED drop rate for high-loss packets";
           }
           leaf queue-counters-red-bytes-na {
             type string;
             description
               "Number of bytes dropped due to RED not available";
           }
           leaf queue-counters-red-bytes {
             type int32;
             description
               "Number of bytes dropped due to RED";
           }
           leaf queue-counters-red-bytes-rate {
             type int32;
             description
               "Rate at which bytes are dropped due to RED";
           }
           leaf queue-counters-red-bytes-ln {
             type int32;
             description
               "Number of RED dropped low-loss, non-TCP bytes";
           }
           leaf queue-counters-red-bytes-rate-ln {
             type int32;
             description
               "RED drop rate for low-loss, non-TCP bytes";
           }
           leaf queue-counters-red-bytes-lt {
             type int32;
             description
               "Number of RED dropped low-loss, TCP bytes";
           }
           leaf queue-counters-red-bytes-rate-lt {
             type int32;
             description
               "RED drop rate for low-loss, TCP bytes";
           }
           leaf queue-counters-red-bytes-hn {
             type int32;
             description
               "Number of RED dropped high-loss, non-TCP bytes";
           }
           leaf queue-counters-red-bytes-rate-hn {
             type int32;
             description
               "RED drop rate for high-loss, non-TCP bytes";
           }
           leaf queue-counters-red-bytes-ht {
             type int32;
             description
               "Number of RED dropped high-loss, TCP bytes";
           }
           leaf queue-counters-red-bytes-rate-ht {
             type int32;
             description
               "RED drop rate for high-loss, TCP bytes";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-medium {
             type int32;
             description
               "Number of RED dropped medium-loss bytes";
           }
           leaf queue-counters-red-bytes-rate-medium {
             type int32;
             description
               "RED drop rate for medium-loss bytes";
           }
           leaf queue-counters-red-bytes-high {
             type int32;
             description
               "Number of RED dropped high-loss bytes";
           }
           leaf queue-counters-red-bytes-rate-high {
             type int32;
             description
               "RED drop rate for high-loss bytes";
           }
           leaf queue-counters-timestamp {
             type int32;
             description
               "Last packet enqueued timestamp";
           }
           leaf queue-counters-total-drop-packets {
             type int32;
             description
               "Number of total packets dropped at the queue";
           }
           leaf queue-counters-total-drop-packets-rate {
             type int32;
             description
               "Number of total packets dropped at the queue";
           }
           leaf queue-counters-total-drop-bytes {
             type int32;
             description
               "Number of total packets dropped at the queue";
           }
           leaf queue-counters-total-drop-bytes-rate {
             type int32;
             description
               "Number of total packets dropped at the queue";
           }
           leaf queue-counters-reserved-buffer-packets {
             type int32;
             description
               "Queues's usage of reserved buffer pool in pkts";
           }
           leaf queue-counters-reserved-buffer-bytes {
             type int32;
             description
               "Queues's usage of reserved buffer pool in bytes";
           }
           leaf queue-counters-shared-buffer-packets {
             type int32;
             description
               "Queues's usage of shared buffer pool in pkts";
           }
           leaf queue-counters-shared-buffer-bytes {
             type int32;
             description
               "Queues's usage of shared buffer pool in bytes";
           }
           leaf queue-counters-depth-average {
             type int32;
             description
               "Time averaged queue depth";
           }
           leaf queue-counters-depth-current {
             type int32;
             description
               "Current instantaneous queue depth";
           }
           leaf queue-counters-depth-peak {
             type int32;
             description
               "Peak queue depth";
           }
           leaf queue-counters-depth-max {
             type int32;
             description
               "Maximum queue depth attained";
           }
           leaf queue-counters-srx-reserved-buffer-bytes {
             type int32;
             description
               "Queues's usage of reserved buffer pool in bytes";
           }
           leaf queue-counters-srx-depth-current {
             type int32;
             description
               "Current instantaneous queue depth";
           }
         }
         container interface-cos-summary {
           description
             "Summary of forwarding class and queue information on an 
             interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
           leaf intf-cos-burst-size-for-ifl {
             type int32;
             description
               "Burst size for the logical interface";
           }
         }
         container interface-cos-short-summary {
           description
             "Summary of queue information on an interface";
           leaf intf-cos-forwarding-classes-supported {
             type int32;
             description
               "Number of forwarding classes supported on this interface";
           }
           leaf intf-cos-forwarding-classes-in-use {
             type int32;
             description
               "Number of forwarding classes currently in use on this 
               interface";
           }
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
           leaf intf-cos-queue-dedicated-or-shared {
             type string;
             description
               "Interface has dedicated or shared queues";
           }
           leaf intf-cos-sched-resource-type {
             type string;
             description
               "Interface scheduling resource type";
           }
           leaf intf-cos-sched-resource-usage-mic-limit {
             type int32;
             description
               "MIC/PIC scheduling resource usage limit";
           }
           leaf intf-cos-sched-resource-usage-mic-count {
             type int32;
             description
               "MIC/PIC scheduling resource usage count";
           }
           leaf intf-cos-sched-resource-usage-port-limit {
             type int32;
             description
               "Interface scheduling resource limit";
           }
           leaf intf-cos-sched-resource-usage-port-count {
             type int32;
             description
               "Interface scheduling resource usage";
           }
         }
         list queue-num-forwarding-class-name-map {
           key "queue-number";
           leaf queue-number {
             type uint32;
             description
               "Queue number";
           }
           leaf forwarding-class-name {
             type string;
             description
               "Forwarding class name associated with queue";
           }
         }
       }
       container otn-oc-information {
         list media-alarm {
           leaf media-alarm-name {
             type string;
           }
           leaf media-alarm-seconds {
             type int32;
           }
           leaf media-alarm-count {
             type int32;
           }
           leaf media-alarm-state {
             type string;
           }
         }
       }
       container otn-otu-information {
         list media-alarm {
           leaf media-alarm-name {
             type string;
           }
           leaf media-alarm-seconds {
             type int32;
           }
           leaf media-alarm-count {
             type int32;
           }
           leaf media-alarm-state {
             type string;
           }
         }
       }
       container otn-odu-information {
         list media-alarm {
           leaf media-alarm-name {
             type string;
           }
           leaf media-alarm-seconds {
             type int32;
           }
           leaf media-alarm-count {
             type int32;
           }
           leaf media-alarm-state {
             type string;
           }
         }
       }
       container otn-ot-module-information {
         list media-alarm {
           leaf media-alarm-name {
             type string;
           }
           leaf media-alarm-seconds {
             type int32;
           }
           leaf media-alarm-count {
             type int32;
           }
           leaf media-alarm-state {
             type string;
           }
         }
       }
       list otn-odu-tcm-information {
         list media-alarm {
           leaf media-alarm-name {
             type string;
           }
           leaf media-alarm-seconds {
             type int32;
           }
           leaf media-alarm-count {
             type int32;
           }
           leaf media-alarm-state {
             type string;
           }
         }
       }
       container ima-group-information {
         description
           "IMA group alarms";
       }
       container ima-link-information {
         description
           "IMA link alarms";
       }
       list smart-sfp-channel-statistics {
         key "iwf-channel-num";
         description
           "Smart SFP channel IWF statistics";
         leaf iwf-channel-num {
           type uint32;
           description
             "Channel number for IWF stats";
         }
         leaf channel-not-applicable {
           type string;
           description
             "Channelization are not supported";
         }
         container smart-sfp-av-titan-iwf-statistics {
           leaf rx-packets {
             type uint32;
           }
           leaf tx-packets {
             type uint32;
           }
           leaf malformed-packets {
             type uint32;
           }
           leaf reordered-packets {
             type uint32;
           }
           leaf misordered-dropped-packets {
             type uint32;
           }
           leaf missing-packets {
             type uint32;
           }
           leaf played-out-packets {
             type uint32;
           }
           leaf jb-overrun {
             type uint32;
           }
           leaf jb-underrun {
             type uint32;
           }
         }
       }
       list smart-sfp-channel-defects {
         key "defect-channel-num";
         description
           "Smart SFP channel Defects";
         leaf defect-channel-num {
           type uint32;
           description
             "Channel number ";
         }
         leaf sfp-channel-defects {
           type string;
         }
         leaf channel-not-applicable {
           type string;
           description
             "Channelization are not supported";
         }
       }
       container ethernet-mac-pfc-statistics {
         description
           "Ethernet MAC Priority Flow control Statistics";
         leaf mac-pfc-dot1p {
           type int32;
         }
         leaf input-mac-pfc-frames {
           type int32;
         }
         leaf output-mac-pfc-frames {
           type int32;
         }
       }
       container ethernet-pfcwd-statistics {
         description
           "Ethernet MAC Priority Flow control Watchdog Statistics";
         leaf queue-number {
           type uint32;
           description
             "Queue number";
         }
         leaf detected {
           type int32;
         }
         leaf recovered {
           type int32;
         }
         leaf last-count {
           type int32;
         }
         leaf total-count {
           type int32;
         }
       }
       container cos-information {
         description
           "Information about class-of-service configuration";
         list cos-stream-information {
           description
             "Information about the traffic stream";
         }
       }
       container physical-interface-cos-information {
         description
           "Physical interface class-of-service parameters";
       }
       container precl-statistics {
         description
           "Preclassifier Statistics ";
         container precl-information {
           description
             "Preclassifier Statistics";
         }
       }
       container mlfr-uni-nni-traffic-statistics {
         container bundle {
         }
       }
       container lag-traffic-statistics {
         container lag-multicast-statistics {
           leaf lag-multicast-statistics-header {
             type empty;
           }
           container lag-ipv4-multicast-statistics {
             leaf input-packets {
               type uint64;
             }
             leaf input-pps {
               type int32;
             }
             leaf input-bytes {
               type int32;
             }
             leaf input-bps {
               type int32;
             }
             leaf output-packets {
               type uint64;
             }
             leaf output-pps {
               type int32;
             }
             leaf output-bytes {
               type int32;
             }
             leaf output-bps {
               type int32;
             }
           }
           container lag-ipv6-multicast-statistics {
             leaf input-packets {
               type uint64;
             }
             leaf input-pps {
               type int32;
             }
             leaf input-bytes {
               type int32;
             }
             leaf input-bps {
               type int32;
             }
             leaf output-packets {
               type uint64;
             }
             leaf output-pps {
               type int32;
             }
             leaf output-bytes {
               type int32;
             }
             leaf output-bps {
               type int32;
             }
           }
         }
         list if-distribution-list-information {
         }
         container ifd-lag-traffic-statistics {
         }
       }
       container ifd-lag-traffic-statistics {
       }
       container interval-information {
         list interval {
           description
             "Statistics for a single interval";
         }
       }
       container transport-interval-information {
         list transport-interval {
           description
             "Statistics for a single interval";
           list transport-pm-ber {
             leaf transport-pm-ber-thr-max {
               type string;
             }
             leaf transport-pm-ber-tca-max-en {
               type string;
             }
             leaf transport-pm-ber-tca-max {
               type string;
             }
           }
           list transport-pm-ber-cur {
             leaf transport-pm-ber-cur-thr-max {
               type string;
             }
             leaf transport-pm-ber-cur-tca-max-en {
               type string;
             }
             leaf transport-pm-ber-cur-tca-max {
               type string;
             }
           }
         }
       }
     }
   }
   grouping targeting-information-block {
     list bundle-information {
       leaf bundle-name {
         type string;
         description
           "Bundle name";
       }
       leaf targeting-type {
         type string;
         description
           "Targeting type";
       }
       leaf total-n-distribution-groups {
         type int32;
         description
           "Total number of distribution groups";
       }
       leaf total-n-distribution-interfaces {
         type int32;
         description
           "Total number of distributed interfaces";
       }
       leaf redundancy-mode {
         type string;
         description
           "Redundancy mode";
       }
       list group-information {
         leaf group-name {
           type string;
           description
             "Distribution Group name";
         }
         leaf n-distribution-interfaces {
           type int32;
           description
             "Number of distributed interfaces";
         }
         list row {
           leaf physical-intf-name {
             type string;
             description
               "Physical interface";
           }
           leaf link-status {
             type string;
             description
               "Physical interface link status";
           }
           leaf n-primary-distributions {
             type int32;
             description
               "Number of primary distributions";
           }
           leaf n-backup-distributions {
             type int32;
             description
               "Number of backup distributions";
           }
           leaf primary-load {
             type int32;
             description
               "Primary Load";
           }
           leaf backup-load {
             type int32;
             description
               "Backup Load";
           }
         }
       }
     }
     container link-information {
       leaf bundle-name {
         type string;
         description
           "Bundle name";
       }
       leaf targeting-type {
         type string;
         description
           "Targeting type";
       }
       leaf link-name {
         type string;
         description
           "Physical interface name";
       }
       leaf link-status {
         type string;
         description
           "Physical interface link status";
       }
       leaf total-n-distribution-interfaces {
         type int32;
         description
           "Total number of distributed interfaces";
       }
       leaf n-primary-distributions {
         type int32;
         description
           "Number of primary distributions";
       }
       leaf n-backup-distributions {
         type int32;
         description
           "Number of backup distributions";
       }
       leaf primary-load {
         type int32;
         description
           "Primary Load";
       }
       leaf backup-load {
         type int32;
         description
           "Backup Load";
       }
     }
   }
   grouping l2-vlan-info-block {
     leaf routing-instance {
       type string;
       description
         "Routing instance associated with the route";
     }
     list core-interface {
       leaf interface-name {
         type string;
         description
           "Name of the interface associated with the route";
       }
       leaf interface-status {
         type string;
         description
           "Interface status";
       }
       list inner-vlan {
         leaf trunk-vlan-id {
           type int32;
           description
             "Trunk vlan id";
         }
         leaf inner-vlan-id-count {
           type int32;
           description
             "Total number of vlans";
         }
         leaf inner-vlan-range {
           type string;
           description
             "Inner vlan range";
         }
         leaf vlans-in-use {
           type int32;
           description
             "Count of vlan ids in use";
         }
         leaf vlans-free {
           type int32;
           description
             "Count of unassigned vlan ids in range";
         }
       }
     }
   }
   grouping distribution-list-information-block {
     list aggregate-information {
       leaf aggregate-name {
         type string;
         description
           "Aggregate name";
       }
       list distribution-list-row {
         leaf distribution-list-name {
           type string;
         }
         leaf status {
           type string;
         }
         list interface-list {
           leaf interface-name {
             type string;
             description
               "Interface name";
           }
           leaf interface-status {
             type string;
           }
         }
       }
     }
   }
   grouping dcd-lib-client-data-block {
     leaf client-info {
       type string;
       description
         " Details of client ";
     }
   }
   grouping interface-redundancy-information-block {
     list interface-redundancy {
       leaf interface-name {
         type string;
         description
           "Name of the interface";
       }
       leaf state {
         type string;
         description
           "Interface state";
       }
       leaf last-change {
         type string;
         description
           "Time since last state change ([weeks][days] 
           hours:minutes[:seconds])";
       }
       leaf primary {
         type string;
         description
           "Primary interface";
       }
       leaf secondary {
         type string;
         description
           "Secondary interface";
       }
       leaf current-status {
         type string;
         description
           "Status of primary or secondary interface, or both";
       }
     }
   }
   grouping interface-redundancy-detail-information-block {
     list interface-redundancy-detail {
       leaf interface-name {
         type string;
         description
           "Name of the interface";
       }
       leaf state {
         type string;
         description
           "Interface state";
       }
       leaf last-change {
         type string;
         description
           "Time since last state change ([weeks][days] 
           hours:minutes[:seconds])";
       }
       leaf primary {
         type string;
         description
           "Primary interface";
       }
       leaf secondary {
         type string;
         description
           "Secondary interface";
       }
       leaf mode {
         type string;
         description
           "Mode of interface hot-standby or warm-standby";
       }
       leaf current-status {
         type string;
         description
           "Status of primary or secondary interface, or both";
       }
       leaf replication-state {
         type string;
         description
           "HA transport state 
           Disconnected/Disabled/Sync-In-Progress/Sync-Completed";
       }
     }
   }
   grouping interface-load-balancing-information-block {
     list interface-load-balancing {
       leaf interface-name {
         type string;
         description
           "Name of the interface";
       }
       leaf state {
         type string;
         description
           "Interface state";
       }
       leaf last-change {
         type string;
         description
           "Time since last state change ([weeks][days] 
           hours:minutes[:seconds])";
       }
       leaf member-count {
         type int32;
         description
           "Number of member interfaces";
       }
       leaf ha-type {
         type string;
         description
           "High Availability model";
       }
     }
   }
   grouping aggregated-anchor-group-information-block {
     list aggregated-anchor-group-entry {
       leaf aggregated-anchor-group-name {
         type string;
         description
           "Aggregated anchor redundancy group name";
       }
       leaf aggregated-anchor-group-mode {
         type string;
         description
           "Mode of operation";
       }
       leaf aggregated-anchor-sub-group-id {
         type uint32;
         description
           "Sub-group id used for the group";
       }
       list aggregated-anchor-group-interface-brief-entry {
         leaf aggregated-anchor-group-member-interface {
           type string;
           description
             "PFE used for anchoring";
         }
         leaf aggregated-anchor-redundancy-cfg-state {
           type string;
           description
             "Configured redundancy state";
         }
         leaf aggregated-anchor-operational-state {
           type string;
           description
             "Operational redundancy state";
         }
         leaf aggregated-anchor-redundancy-state {
           type string;
           description
             "Actual redundancy state";
         }
         leaf aggregated-anchor-redundancy-state-reason {
           type string;
           description
             "Operational redundancy state reason";
         }
       }
       list aggregated-anchor-group-interface-detail-entry {
         leaf aggregated-anchor-group-member-interface {
           type string;
           description
             "PFE used for anchoring";
         }
         leaf aggregated-anchor-redundancy-cfg-state {
           type string;
           description
             "Configured redundancy state";
         }
         leaf aggregated-anchor-redundancy-state {
           type string;
           description
             "Actual redundancy state";
         }
         leaf aggregated-anchor-operational-state {
           type string;
           description
             "Operational redundancy state";
         }
         leaf aggregated-anchor-redundancy-state-reason {
           type string;
           description
             "Operational redundancy state reason";
         }
         leaf aggregated-anchor-switchover-information {
           type string;
           description
             "Switchover information if it happened";
         }
         leaf aggregated-anchor-last-primary-interface-name {
           type string;
           description
             "Primary interface as per the last switchover";
         }
         leaf aggregated-anchor-last-secondary-interface-name {
           type string;
           description
             "Secondary interface as per the last switchover";
         }
         leaf aggregated-anchor-state-switch-time {
           type string;
           description
             "Time when last protection switch happened";
         }
       }
       list aggregated-anchor-group-interface-extensive-entry {
         leaf aggregated-anchor-group-member-interface {
           type string;
           description
             "PFE used for anchoring";
         }
         leaf aggregated-anchor-redundancy-cfg-state {
           type string;
           description
             "Configured redundancy state";
         }
         leaf aggregated-anchor-redundancy-state {
           type string;
           description
             "Actual redundancy state";
         }
         leaf aggregated-anchor-operational-state {
           type string;
           description
             "Operational redundancy state";
         }
         leaf aggregated-anchor-redundancy-state-reason {
           type string;
           description
             "Operational redundancy state reason";
         }
         leaf aggregated-anchor-switchover-information {
           type string;
           description
             "Switchover information if it happened";
         }
         leaf aggregated-anchor-last-primary-interface-name {
           type string;
           description
             "Primary interface as per the last switchover";
         }
         leaf aggregated-anchor-last-secondary-interface-name {
           type string;
           description
             "Secondary interface as per the last switchover";
         }
         leaf aggregated-anchor-state-switch-time {
           type string;
           description
             "Time when last protection switch happened";
         }
         leaf aggregated-anchor-group-refs {
           type uint32;
           description
             "Number of references on group";
         }
         leaf aggregated-anchor-group-flags {
           type uint32;
           description
             "Flags used for debugging";
         }
         leaf aggregated-anchor-group-num-secondary {
           type uint32;
           description
             "Number of protects in the group";
         }
         leaf aggregated-anchor-interface-sub-group-id {
           type uint32;
           description
             "Sub-group id used for the group";
         }
       }
       leaf aggregated-anchor-group-id {
         type uint32;
         description
           "Group id used for the group";
       }
       leaf aggregated-anchor-switchover-information {
         type string;
         description
           "Switchover information if it happened";
       }
       leaf aggregated-anchor-last-primary-interface-name {
         type string;
         description
           "Primary interface as per the last switchover";
       }
       leaf aggregated-anchor-last-secondary-interface-name {
         type string;
         description
           "Secondary interface as per the last switchover";
       }
       leaf aggregated-anchor-state-switch-time {
         type string;
         description
           "Time when last protection switch happened";
       }
       leaf aggregated-anchor-group-member-interface {
         type string;
         description
           "PFE used for anchoring";
       }
       leaf aggregated-anchor-redundancy-cfg-state {
         type string;
         description
           "Configured redundancy state";
       }
       leaf aggregated-anchor-operational-state {
         type string;
         description
           "Operational redundancy state";
       }
       leaf aggregated-anchor-redundancy-state {
         type string;
         description
           "Actual redundancy state";
       }
       leaf aggregated-anchor-redundancy-state-reason {
         type string;
         description
           "Operational redundancy state reason";
       }
       leaf aggregated-anchor-interface-sub-group-id {
         type uint32;
         description
           "Sub-group id used for the group";
       }
       leaf aggregated-anchor-group-refs {
         type uint32;
         description
           "Number of references on group";
       }
       leaf aggregated-anchor-group-flags {
         type uint32;
         description
           "Flags used for debugging";
       }
       leaf aggregated-anchor-group-num-secondary {
         type uint32;
         description
           "Number of protects in the group";
       }
       leaf aggregated-anchor-interface-refs {
         type uint32;
         description
           "Number of references on interface";
       }
       leaf aggregated-anchor-interface-flags {
         type uint32;
         description
           "Flags used for debugging";
       }
     }
   }
 }
