/*
 * Copyright (c) 2026 Juniper Networks, Inc.
 * All rights reserved.
 */
 module junos-rpc-loop-detect {
   namespace "http://yang.juniper.net/junos/rpc/loop-detect";

   prefix loop-detect;

   import junos-common-ddl-extensions {
     prefix junos;
     revision-date 2026-01-01;
   }

   import junos-common-types {
     prefix jt;
     revision-date 2026-01-01;
   }

   organization "Juniper Networks, Inc.";

   contact "yang-support@juniper.net";

   description "Junos RPC YANG module for loop-detect command(s)";

   revision 2026-01-01 {
     description "Junos: 26.2R1.7";
   }

   rpc get-loop-detect-interface-information {
     description "Show loop detect interface information";
     junos:command "show loop-detect interface";
     input {
       leaf verbosity_level {
         junos:cli-feature "nokeyword";
         default "brief";
         type enumeration {
           enum "brief" {
             description "Display brief output (default)";
           }
           enum "detail" {
             description "Display detailed output";
           }
         }
       }
       leaf interface-name {
         description "Name of interface";
         junos:cli-feature "nokeyword";
         type union {
           type jt:interface-device;
           type string {
             pattern "<.*>|$.*";
           }
         }
       }
     }
     output {
       choice output-tags {
         case actual-tag {
           container loop-detect-interface-information {
             uses loop-detect-interface-information-block;
           }
         }
         case multichassis-tag {
           container multi-routing-engine-results {
             list multi-routing-engine-item {
               leaf re-name {
                 type string;
               }
               choice output-tags {
                 case actual-tag {
                   container loop-detect-interface-information {
                     uses loop-detect-interface-information-block;
                   }
                 }
               }
             }
           }
         }
       }
     }
   }
   rpc get-loop-detect-enhanced-interface-information {
     description "Show loop detect enhanced interface information";
     junos:command "show loop-detect enhanced interface";
     input {
       leaf interface-name {
         description "Name of interface";
         junos:cli-feature "nokeyword";
         type union {
           type jt:interface-unit;
           type string {
             pattern "<.*>|$.*";
           }
         }
       }
     }
     output {
       choice output-tags {
         case actual-tag {
           container loop-detect-enhanced-interface-information {
             uses loop-detect-enhanced-interface-information-block;
           }
         }
         case multichassis-tag {
           container multi-routing-engine-results {
             list multi-routing-engine-item {
               leaf re-name {
                 type string;
               }
               choice output-tags {
                 case actual-tag {
                   container loop-detect-enhanced-interface-information {
                     uses loop-detect-enhanced-interface-information-block;
                   }
                 }
               }
             }
           }
         }
       }
     }
   }
   rpc get-loop-detect-interface-statistics-information {
     description "Show loop detect interface statistics information";
     junos:command "show loop-detect statistics interface";
     input {
       leaf verbosity_level {
         junos:cli-feature "nokeyword";
         default "brief";
         type enumeration {
           enum "brief" {
             description "Display brief output (default)";
           }
           enum "detail" {
             description "Display detailed output";
           }
         }
       }
       leaf interface-name {
         description "Name of interface";
         junos:cli-feature "nokeyword";
         type union {
           type jt:interface-device;
           type string {
             pattern "<.*>|$.*";
           }
         }
       }
     }
     output {
       choice output-tags {
         case actual-tag {
           container loop-detect-interface-statistics-information {
             uses loop-detect-interface-statistics-information-block;
           }
         }
         case multichassis-tag {
           container multi-routing-engine-results {
             list multi-routing-engine-item {
               leaf re-name {
                 type string;
               }
               choice output-tags {
                 case actual-tag {
                   container loop-detect-interface-statistics-information {
                     uses loop-detect-interface-statistics-information-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping loop-detect-interface-information-block {
     list loop-detect-interface-entry {
       description
         "Loop detect interace information";
       leaf ld-interface-name {
         type string;
         description
           "Name of interface";
       }
       leaf ld-agg-parent-intf {
         type string;
         description
           "Aggregate Interface";
       }
       leaf ld-port-state {
         type string;
         description
           "Port state";
       }
       leaf ld-src-loop-interface {
         type string;
         description
           "Source Loop Interface";
       }
     }
   }
   grouping loop-detect-enhanced-interface-information-block {
     list loop-detect-enhanced-interface-entry {
       key "ld-interface-name";
       description
         "Loop detect interace information";
       leaf ld-interface-name {
         type string;
         description
           "Name of interface";
       }
       leaf ld-interface-vlan-id {
         type string;
         description
           "Vlan-id or 'all' in case of trunk port";
       }
       leaf ld-interface-esi {
         type string;
         description
           "ESI configured for the interface";
       }
       leaf ld-interface-state {
         type string;
         description
           "Current status of the interface";
       }
       leaf ld-remote-host {
         type string;
         description
           "Remote Host";
       }
       leaf ld-remote-chassis {
         type string;
         description
           "Remote chassis ID";
       }
       leaf ld-remote-interface {
         type string;
         description
           "Remote Interface";
       }
       leaf ld-remote-esi {
         type string;
         description
           "Remote ESI";
       }
       leaf ld-interface-vlan {
         type uint32;
         description
           "First detected loop vlan-id";
       }
       leaf ld-interface-other-vlan {
         type string;
         description
           "Other detected loop vlan-id";
       }
       leaf ld-interface-last-ld-time {
         type string;
         description
           "Last loop-detected timestamp";
       }
       leaf ld-interface-rx-stats {
         type uint32;
         description
           "Receive statistics of loop-detect PDUs";
       }
       leaf ld-interface-action {
         type string;
         description
           "Action configured for the interface";
       }
       leaf ld-interface-action-count {
         type uint32;
         description
           "Number of times action has been taken on this interface";
       }
       leaf ld-tx-interval {
         type string;
         description
           "Transmit interval configured for this interface";
       }
       leaf ld-revert-interval {
         type uint32;
         description
           "Revert interval configured for this interface";
       }
     }
   }
   grouping loop-detect-interface-statistics-information-block {
     list loop-detect-interface-statistics-entry {
       description
         "Loop detect interace statistics information";
       leaf intf-name {
         type string;
         description
           "Name of interface";
       }
       leaf total-pkts-sent {
         type int32;
         description
           "Total loop detect packets sent";
       }
       leaf total-pkts-received {
         type int32;
         description
           "Total loop detect packets received";
       }
     }
   }
 }
