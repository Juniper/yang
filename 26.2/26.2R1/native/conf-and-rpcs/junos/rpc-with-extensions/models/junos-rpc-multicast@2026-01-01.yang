/*
 * Copyright (c) 2026 Juniper Networks, Inc.
 * All rights reserved.
 */
 module junos-rpc-multicast {
   namespace "http://yang.juniper.net/junos/rpc/multicast";

   prefix multicast;

   import junos-common-ddl-extensions {
     prefix junos;
     revision-date 2026-01-01;
   }

   import junos-common-types {
     prefix jt;
     revision-date 2026-01-01;
   }

   organization "Juniper Networks, Inc.";

   contact "yang-support@juniper.net";

   description "Junos RPC YANG module for multicast command(s)";

   revision 2026-01-01 {
     description "Junos: 26.2R1.7";
   }

   rpc get-mc-fwd-cache-information {
     description "Show multicast forwarding cache statistics";
     junos:command "show multicast forwarding-cache statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf family {
         description "Address Family";
         type enumeration {
           enum "inet" {
             description "Display IPv4 information";
           }
           enum "inet6" {
             description "Display IPv6 information";
           }
         }
       }
     }
     output {
       choice output-tags {
         case actual-tag {
           container mc-fwd-cache-information {
             uses mc-fwd-cache-information-block;
           }
         }
         case multichassis-tag {
           container multi-routing-engine-results {
             list multi-routing-engine-item {
               leaf re-name {
                 type string;
               }
               choice output-tags {
                 case actual-tag {
                   container mc-fwd-cache-information {
                     uses mc-fwd-cache-information-block;
                   }
                 }
               }
             }
           }
         }
       }
     }
   }
   rpc get-multicast-router-information {
     description "Request multicast router information";
     junos:command "show multicast mrinfo";
     input {
       leaf host {
         description "Hostname or address of remote host";
         junos:cli-feature "nokeyword";
         type string;
         mandatory true;
       }
     }
     output {
       choice output-tags {
         case output-tag {
           leaf output {
             type string;
           }
         }
         case multichassis-tag {
           anyxml multi-routing-engine-results;
         }
       }
     }
   }
   rpc get-multicast-route-information {
     description "Show the multicast routing table";
     junos:command "show multicast route";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf mode {
         junos:cli-feature "nokeyword";
         default "all";
         type enumeration {
           enum "all" {
             description "Display all route entries";
           }
           enum "active" {
             description "Display active route entries";
           }
           enum "inactive" {
             description "Display inactive route entries";
           }
         }
       }
       leaf verbosity_level {
         junos:cli-feature "nokeyword";
         default "brief";
         type enumeration {
           enum "summary" {
             description "Display summary output";
           }
           enum "brief" {
             description "Display brief output (default)";
           }
           enum "detail" {
             description "Display detailed output";
           }
           enum "extensive" {
             description "Display extensive output";
           }
         }
       }
       leaf family {
         description "Address family";
         junos:cli-feature "nokeyword";
         default "inet";
         type enumeration {
           enum "inet" {
             description "Display IPv4 information";
           }
           enum "inet6" {
             description "Display IPv6 information";
           }
         }
       }
       leaf table {
         description "Entries in a particular routing table";
         status deprecated;
         type string;
       }
       leaf group {
         description "IP address and optional prefix length of group";
         type jt:ipprefix;
       }
       leaf source-prefix {
         description "IP address and optional prefix length of source for routes";
         type jt:ipprefix;
       }
       leaf regexp {
         description "Regular expression for session to match";
         junos:cli-feature "nokeyword";
         type string;
       }
       leaf display-tunnel-name {
         description "Display provider tunnel name instead of branch information";
         type empty;
       }
       leaf display-origin-protocol {
         description "Display originating protocol instead of upstream protocol";
         type empty;
       }
       leaf oif-count {
         description "Display outgoing interface count instead of list";
         type empty;
       }
     }
     output {
       choice output-tags {
         case actual-tag {
           container multicast-route-information {
             uses multicast-route-information-block;
           }
         }
         case multichassis-tag {
           container multi-routing-engine-results {
             list multi-routing-engine-item {
               leaf re-name {
                 type string;
               }
               choice output-tags {
                 case actual-tag {
                   container multicast-route-information {
                     uses multicast-route-information-block;
                   }
                 }
               }
             }
           }
         }
       }
     }
   }
   rpc get-multicast-next-hops-information {
     description "Show the multicast next-hop table";
     junos:command "show multicast next-hops";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf verbosity_level {
         junos:cli-feature "nokeyword";
         default "brief";
         type enumeration {
           enum "terse" {
             description "Display terse output";
           }
           enum "brief" {
             description "Display brief output (default)";
           }
           enum "detail" {
             description "Display detailed output";
           }
         }
       }
       leaf identifier {
         description "ID of next hop";
         junos:cli-feature "nokeyword";
         type union {
           type uint32;
           type string {
             pattern "<.*>|$.*";
           }
         }
       }
       leaf family {
         description "Address family";
         junos:cli-feature "nokeyword";
         default "inet";
         type enumeration {
           enum "inet" {
             description "Display IPv4 information";
           }
           enum "inet6" {
             description "Display IPv6 information";
           }
         }
       }
     }
     output {
       choice output-tags {
         case actual-tag {
           container multicast-next-hops-information {
             uses multicast-next-hops-information-block;
           }
         }
         case multichassis-tag {
           container multi-routing-engine-results {
             list multi-routing-engine-item {
               leaf re-name {
                 type string;
               }
               choice output-tags {
                 case actual-tag {
                   container multicast-next-hops-information {
                     uses multicast-next-hops-information-block;
                   }
                 }
               }
             }
           }
         }
       }
     }
   }
   rpc get-multicast-list-next-hops-information {
     description "Show the multicast list next-hop table";
     junos:command "show multicast next-hops list";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf identifier {
         description "ID of next hop";
         junos:cli-feature "nokeyword";
         type union {
           type uint32;
           type string {
             pattern "<.*>|$.*";
           }
         }
       }
     }
     output {
       choice output-tags {
         case actual-tag {
           container multicast-list-next-hops-information {
             uses multicast-list-next-hops-information-block;
           }
         }
         case multichassis-tag {
           container multi-routing-engine-results {
             list multi-routing-engine-item {
               leaf re-name {
                 type string;
               }
               choice output-tags {
                 case actual-tag {
                   container multicast-list-next-hops-information {
                     uses multicast-list-next-hops-information-block;
                   }
                 }
               }
             }
           }
         }
       }
     }
   }
   rpc get-multicast-nh-session-information {
     description "Show all MCNH session IDs";
     junos:command "show multicast next-hops session";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf identifier {
         description "Session ID";
         junos:cli-feature "nokeyword";
         type union {
           type uint32;
           type string {
             pattern "<.*>|$.*";
           }
         }
       }
     }
     output {
       choice output-tags {
         case actual-tag {
           container multicast-nh-session-information {
             uses multicast-nh-session-information-block;
           }
         }
         case multichassis-tag {
           container multi-routing-engine-results {
             list multi-routing-engine-item {
               leaf re-name {
                 type string;
               }
               choice output-tags {
                 case actual-tag {
                   container multicast-nh-session-information {
                     uses multicast-nh-session-information-block;
                   }
                 }
               }
             }
           }
         }
       }
     }
   }
   rpc get-satellite-control-next-hop {
     description "Show satellite multicast unicast next-hops";
     junos:command "show multicast next-hops satellite";
     input {
       leaf verbosity_level {
         junos:cli-feature "nokeyword";
         default "brief";
         type enumeration {
           enum "brief" {
             description "Display brief output (default)";
           }
           enum "detail" {
             description "Display detailed output";
           }
         }
       }
     }
     output {
       choice output-tags {
         case output-tag {
           leaf output {
             type string;
           }
         }
         case actual-tag {
           anyxml satellite-control-next-hop;
         }
         case multichassis-tag {
           anyxml multi-routing-engine-results;
         }
       }
     }
   }
   rpc get-multicast-rpf-information {
     description "Show reverse-path forwarding (RPF) source network information";
     junos:command "show multicast rpf";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf verbosity_level {
         junos:cli-feature "nokeyword";
         type enumeration {
           enum "summary" {
             description "Display summary output";
           }
         }
       }
       leaf prefix {
         description "IP address and optional prefix length of host";
         junos:cli-feature "nokeyword";
         type jt:ipprefix;
       }
       leaf family {
         description "Address family";
         junos:cli-feature "nokeyword";
         default "inet";
         type enumeration {
           enum "inet" {
             description "Display RPF information for IPv4 ";
           }
           enum "inet6" {
             description "Display RPF information for IPv6 ";
           }
         }
       }
     }
     output {
       choice output-tags {
         case actual-tag {
           container multicast-rpf-information {
             uses multicast-rpf-information-block;
           }
         }
         case multichassis-tag {
           container multi-routing-engine-results {
             list multi-routing-engine-item {
               leaf re-name {
                 type string;
               }
               choice output-tags {
                 case actual-tag {
                   container multicast-rpf-information {
                     uses multicast-rpf-information-block;
                   }
                 }
               }
             }
           }
         }
       }
     }
   }
   rpc get-multicast-scope-information {
     description "Show administratively scoped multicast information";
     junos:command "show multicast scope";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf family {
         description "Address family";
         junos:cli-feature "nokeyword";
         default "inet";
         type enumeration {
           enum "inet" {
             description "Display IPv4 information";
           }
           enum "inet6" {
             description "Display IPv6 information";
           }
         }
       }
     }
     output {
       choice output-tags {
         case actual-tag {
           container multicast-scope-information {
             uses multicast-scope-information-block;
           }
         }
         case multichassis-tag {
           container multi-routing-engine-results {
             list multi-routing-engine-item {
               leaf re-name {
                 type string;
               }
               choice output-tags {
                 case actual-tag {
                   container multicast-scope-information {
                     uses multicast-scope-information-block;
                   }
                 }
               }
             }
           }
         }
       }
     }
   }
   rpc get-multicast-sessions-information {
     description "Show announced multicast sessions";
     junos:command "show multicast sessions";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf verbosity_level {
         junos:cli-feature "nokeyword";
         default "brief";
         type enumeration {
           enum "brief" {
             description "Display brief output (default)";
           }
           enum "detail" {
             description "Display detailed output";
           }
           enum "extensive" {
             description "Display extensive output";
           }
         }
       }
       leaf regexp {
         description "Regular expression for sessions to match";
         junos:cli-feature "nokeyword";
         type string;
       }
     }
     output {
       choice output-tags {
         case actual-tag {
           container multicast-sessions-information {
             uses multicast-sessions-information-block;
           }
         }
         case multichassis-tag {
           container multi-routing-engine-results {
             list multi-routing-engine-item {
               leaf re-name {
                 type string;
               }
               choice output-tags {
                 case actual-tag {
                   container multicast-sessions-information {
                     uses multicast-sessions-information-block;
                   }
                 }
               }
             }
           }
         }
       }
     }
   }
   rpc get-multicast-statistics-information {
     description "Show multicast statistics";
     junos:command "show multicast statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf interface {
         description "Name of interface";
         type string;
       }
       leaf family {
         description "Address family";
         junos:cli-feature "nokeyword";
         default "inet";
         type enumeration {
           enum "inet" {
             description "Display statistics for IPv4 ";
           }
           enum "inet6" {
             description "Display statistics for IPv6 ";
           }
         }
       }
     }
     output {
       choice output-tags {
         case actual-tag {
           container multicast-statistics-information {
             uses multicast-statistics-information-block;
           }
         }
         case multichassis-tag {
           container multi-routing-engine-results {
             list multi-routing-engine-item {
               leaf re-name {
                 type string;
               }
               choice output-tags {
                 case actual-tag {
                   container multicast-statistics-information {
                     uses multicast-statistics-information-block;
                   }
                 }
               }
             }
           }
         }
       }
     }
   }
   rpc get-satellite-control-statistics {
     description "Show satellite multicast statistics";
     junos:command "show multicast statistics satellite";
     input {
       leaf verbosity_level {
         junos:cli-feature "nokeyword";
         default "detail";
         type enumeration {
           enum "brief" {
             description "Display brief output (default)";
           }
           enum "detail" {
             description "Display detailed output";
           }
         }
       }
     }
     output {
       choice output-tags {
         case output-tag {
           leaf output {
             type string;
           }
         }
         case actual-tag {
           anyxml satellite-control-statistics;
         }
         case multichassis-tag {
           anyxml multi-routing-engine-results;
         }
       }
     }
   }
   rpc get-multicast-tunnels-information {
     description "Show multicast tunnel information";
     status deprecated;
     junos:command "show multicast tunnels";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output-tags {
         case actual-tag {
           container multicast-tunnels-information {
             uses multicast-tunnels-information-block;
           }
         }
         case multichassis-tag {
           container multi-routing-engine-results {
             list multi-routing-engine-item {
               leaf re-name {
                 type string;
               }
               choice output-tags {
                 case actual-tag {
                   container multicast-tunnels-information {
                     uses multicast-tunnels-information-block;
                   }
                 }
               }
             }
           }
         }
       }
     }
   }
   rpc get-multicast-usage-information {
     description "Show multicast usage information";
     junos:command "show multicast usage";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf verbosity_level {
         junos:cli-feature "nokeyword";
         default "brief";
         type enumeration {
           enum "brief" {
             description "Display brief output (default)";
           }
           enum "detail" {
             description "Display detailed output";
           }
         }
       }
       leaf family {
         description "Address family";
         junos:cli-feature "nokeyword";
         default "inet";
         type enumeration {
           enum "inet" {
             description "Display IPv4 information";
           }
           enum "inet6" {
             description "Display IPv6 information";
           }
         }
       }
     }
     output {
       choice output-tags {
         case actual-tag {
           container multicast-usage-information {
             uses multicast-usage-information-block;
           }
         }
         case multichassis-tag {
           container multi-routing-engine-results {
             list multi-routing-engine-item {
               leaf re-name {
                 type string;
               }
               choice output-tags {
                 case actual-tag {
                   container multicast-usage-information {
                     uses multicast-usage-information-block;
                   }
                 }
               }
             }
           }
         }
       }
     }
   }
   rpc get-multicast-flow-maps-information {
     description "Show configured flow maps";
     junos:command "show multicast flow-map";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf verbosity_level {
         junos:cli-feature "nokeyword";
         default "brief";
         type enumeration {
           enum "brief" {
             description "Display brief output (default)";
           }
           enum "detail" {
             description "Display detailed output";
           }
         }
       }
     }
     output {
       choice output-tags {
         case actual-tag {
           container multicast-flow-maps-information {
             uses multicast-flow-maps-information-block;
           }
         }
         case multichassis-tag {
           container multi-routing-engine-results {
             list multi-routing-engine-item {
               leaf re-name {
                 type string;
               }
               choice output-tags {
                 case actual-tag {
                   container multicast-flow-maps-information {
                     uses multicast-flow-maps-information-block;
                   }
                 }
               }
             }
           }
         }
       }
     }
   }
   rpc get-multicast-interface-information {
     description "Show configured interfaces";
     junos:command "show multicast interface";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output-tags {
         case actual-tag {
           container multicast-interface-information {
             uses multicast-interface-information-block;
           }
         }
         case multichassis-tag {
           container multi-routing-engine-results {
             list multi-routing-engine-item {
               leaf re-name {
                 type string;
               }
               choice output-tags {
                 case actual-tag {
                   container multicast-interface-information {
                     uses multicast-interface-information-block;
                   }
                 }
               }
             }
           }
         }
       }
     }
   }
   rpc get-multicast-pim-to-igmp-proxy-information {
     description "Show pim-to-igmp-proxy information";
     junos:command "show multicast pim-to-igmp-proxy";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
     }
     output {
       choice output-tags {
         case actual-tag {
           container multicast-pim-to-igmp-proxy-information {
             uses multicast-pim-to-igmp-proxy-information-block;
           }
         }
         case multichassis-tag {
           container multi-routing-engine-results {
             list multi-routing-engine-item {
               leaf re-name {
                 type string;
               }
               choice output-tags {
                 case actual-tag {
                   container multicast-pim-to-igmp-proxy-information {
                     uses multicast-pim-to-igmp-proxy-information-block;
                   }
                 }
               }
             }
           }
         }
       }
     }
   }
   rpc get-multicast-pim-to-mld-proxy-information {
     description "Show pim-to-mld-proxy information";
     junos:command "show multicast pim-to-mld-proxy";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
     }
     output {
       choice output-tags {
         case actual-tag {
           container multicast-pim-to-mld-proxy-information {
             uses multicast-pim-to-mld-proxy-information-block;
           }
         }
         case multichassis-tag {
           container multi-routing-engine-results {
             list multi-routing-engine-item {
               leaf re-name {
                 type string;
               }
               choice output-tags {
                 case actual-tag {
                   container multicast-pim-to-mld-proxy-information {
                     uses multicast-pim-to-mld-proxy-information-block;
                   }
                 }
               }
             }
           }
         }
       }
     }
   }
   rpc get-multicast-backup-pe-groups-information {
     description "Show backup PE groups";
     junos:command "show multicast backup-pe-groups";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
     }
     output {
       choice output-tags {
         case actual-tag {
           container multicast-backup-pe-groups-information {
             uses multicast-backup-pe-groups-information-block;
           }
         }
         case multichassis-tag {
           container multi-routing-engine-results {
             list multi-routing-engine-item {
               leaf re-name {
                 type string;
               }
               choice output-tags {
                 case actual-tag {
                   container multicast-backup-pe-groups-information {
                     uses multicast-backup-pe-groups-information-block;
                   }
                 }
               }
             }
           }
         }
       }
     }
   }
   rpc get-multicast-backup-pe-group-information {
     description "Show information for specified group";
     junos:command "show multicast backup-pe-groups group";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf group_name {
         description "Name of the group";
         junos:cli-feature "nokeyword";
         type string;
         mandatory true;
       }
     }
     output {
       choice output-tags {
         case actual-tag {
           container multicast-backup-pe-groups-information {
             uses multicast-backup-pe-groups-information-block;
           }
         }
         case multichassis-tag {
           container multi-routing-engine-results {
             list multi-routing-engine-item {
               leaf re-name {
                 type string;
               }
               choice output-tags {
                 case actual-tag {
                   container multicast-backup-pe-groups-information {
                     uses multicast-backup-pe-groups-information-block;
                   }
                 }
               }
             }
           }
         }
       }
     }
   }
   rpc get-multicast-backup-pe-address-information {
     description "Show groups a PE address is associated with";
     junos:command "show multicast backup-pe-groups address";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf pe_address {
         description "IP address of the PE";
         junos:cli-feature "nokeyword";
         type jt:ipaddr;
         mandatory true;
       }
     }
     output {
       choice output-tags {
         case actual-tag {
           container multicast-backup-pe-address-information {
             uses multicast-backup-pe-address-information-block;
           }
         }
         case multichassis-tag {
           container multi-routing-engine-results {
             list multi-routing-engine-item {
               leaf re-name {
                 type string;
               }
               choice output-tags {
                 case actual-tag {
                   container multicast-backup-pe-address-information {
                     uses multicast-backup-pe-address-information-block;
                   }
                 }
               }
             }
           }
         }
       }
     }
   }
   rpc get-multicast-snooping-route-information {
     description "Show the multicast snooping routing table";
     junos:command "show multicast snooping route";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf mode {
         junos:cli-feature "nokeyword";
         default "data";
         type enumeration {
           enum "all" {
             description "Display all route entries";
           }
           enum "active" {
             description "Display active route entries";
           }
           enum "inactive" {
             description "Display inactive route entries";
           }
           enum "control" {
             description "Display control route entries";
           }
           enum "data" {
             description "Display data route entries";
           }
         }
       }
       leaf verbosity_level {
         junos:cli-feature "nokeyword";
         default "brief";
         type enumeration {
           enum "brief" {
             description "Display brief output (default)";
           }
           enum "detail" {
             description "Display detailed output";
           }
           enum "extensive" {
             description "Display extensive output";
           }
         }
       }
       leaf family {
         description "Address family";
         junos:cli-feature "nokeyword";
         type enumeration {
           enum "inet" {
             description "Display IPv4 information";
           }
           enum "inet6" {
             description "Display IPv6 information";
           }
         }
       }
       leaf vlan-id {
         description "VLAN ID for a learning domain";
         type union {
           type string {
             pattern "<.*>|$.*";
           }
           type uint32 {
             range "0 .. 4094";
           }
         }
       }
       leaf qualified-vlan {
         description "VLAN ID for a Qualified VLAN";
         type union {
           type string {
             pattern "<.*>|$.*";
           }
           type uint32 {
             range "0 .. 4094";
           }
         }
       }
       leaf mesh-group {
         description "Name of a mesh-group";
         type string;
       }
       leaf group {
         description "IP address and optional prefix length of group";
         type jt:ipprefix;
       }
       leaf source-prefix {
         description "IP address and optional prefix length of source";
         type jt:ipprefix;
       }
       leaf regexp {
         description "Regular expression for session to match";
         junos:cli-feature "nokeyword";
         type string;
       }
       leaf bridge-domain {
         description "Name of bridge-domain";
         type string;
       }
       leaf vlan {
         description "Name of VLAN";
         type string;
       }
       leaf instance {
         description "Name of routing-instance";
         type string;
       }
     }
     output {
       choice output-tags {
         case actual-tag {
           container multicast-route-information {
             uses multicast-route-information-block;
           }
         }
         case multichassis-tag {
           container multi-routing-engine-results {
             list multi-routing-engine-item {
               leaf re-name {
                 type string;
               }
               choice output-tags {
                 case actual-tag {
                   container multicast-route-information {
                     uses multicast-route-information-block;
                   }
                 }
               }
             }
           }
         }
       }
     }
   }
   rpc get-multicast-snp-evpn-core-nh-rt-information {
     description "Show evpn core nh routes learned form RPD";
     junos:command "show multicast snooping route evpn-core-nh-route";
     input {
       leaf family {
         description "Address family";
         type enumeration {
           enum "inet" {
             description "Display IPv4 information";
           }
           enum "inet6" {
             description "Display IPv6 information";
           }
         }
       }
     }
     output {
       choice output-tags {
         case actual-tag {
           container multicast-snp-evpn-core-nh-rt-information {
             uses multicast-snp-evpn-core-nh-rt-information-block;
           }
         }
         case multichassis-tag {
           container multi-routing-engine-results {
             list multi-routing-engine-item {
               leaf re-name {
                 type string;
               }
               choice output-tags {
                 case actual-tag {
                   container multicast-snp-evpn-core-nh-rt-information {
                     uses multicast-snp-evpn-core-nh-rt-information-block;
                   }
                 }
               }
             }
           }
         }
       }
     }
   }
   rpc get-multicast-snp-l3-irb-elab-rt-information {
     description "Show l3 irb elaboration routes learned form RPD";
     junos:command "show multicast snooping route l3-irb-elaboration-route";
     input {
       leaf family {
         description "Address family";
         type enumeration {
           enum "inet" {
             description "Display IPv4 information";
           }
           enum "inet6" {
             description "Display IPv6 information";
           }
         }
       }
     }
     output {
       choice output-tags {
         case actual-tag {
           container multicast-snp-l3-irb-elab-rt-information {
             uses multicast-snp-l3-irb-elab-rt-information-block;
           }
         }
         case multichassis-tag {
           container multi-routing-engine-results {
             list multi-routing-engine-item {
               leaf re-name {
                 type string;
               }
               choice output-tags {
                 case actual-tag {
                   container multicast-snp-l3-irb-elab-rt-information {
                     uses multicast-snp-l3-irb-elab-rt-information-block;
                   }
                 }
               }
             }
           }
         }
       }
     }
   }
   rpc get-satellite-control-multicast {
     description "Show the satellite multicast snooping information";
     junos:command "show multicast snooping route satellite";
     input {
       leaf verbosity_level {
         junos:cli-feature "nokeyword";
         default "brief";
         type enumeration {
           enum "brief" {
             description "Display brief output (default)";
           }
           enum "detail" {
             description "Display detailed output";
           }
           enum "extensive" {
             description "Display extensive output";
           }
         }
       }
       leaf vswitch-name {
         description "Virtual switch name";
         type string;
       }
       leaf bridge-domain-name {
         description "Bridge domain name";
         type string;
       }
       leaf vlan-name {
         description "Vlan name";
         type string;
       }
       leaf group {
         description "Multicast Group Address";
         type jt:ipaddr;
       }
       leaf source {
         description "Source Address";
         type jt:ipaddr;
       }
     }
     output {
       choice output-tags {
         case output-tag {
           leaf output {
             type string;
           }
         }
         case actual-tag {
           anyxml satellite-control-multicast;
         }
         case multichassis-tag {
           anyxml multi-routing-engine-results;
         }
       }
     }
   }
   rpc get-multicast-snooping-next-hops-information {
     description "Show the multicast next-hop snooping table";
     junos:command "show multicast snooping next-hops";
     input {
       leaf verbosity_level {
         junos:cli-feature "nokeyword";
         default "brief";
         type enumeration {
           enum "brief" {
             description "Display brief output (default)";
           }
           enum "detail" {
             description "Display detailed output";
           }
         }
       }
       leaf identifier {
         description "ID of next hop";
         junos:cli-feature "nokeyword";
         type union {
           type uint32;
           type string {
             pattern "<.*>|$.*";
           }
         }
       }
       leaf family {
         description "Address family";
         junos:cli-feature "nokeyword";
         type enumeration {
           enum "inet" {
             description "Display IPv4 information";
           }
           enum "inet6" {
             description "Display IPv6 information";
           }
         }
       }
     }
     output {
       choice output-tags {
         case actual-tag {
           container multicast-next-hops-information {
             uses multicast-next-hops-information-block;
           }
         }
         case multichassis-tag {
           container multi-routing-engine-results {
             list multi-routing-engine-item {
               leaf re-name {
                 type string;
               }
               choice output-tags {
                 case actual-tag {
                   container multicast-next-hops-information {
                     uses multicast-next-hops-information-block;
                   }
                 }
               }
             }
           }
         }
       }
     }
   }
   rpc get-multicast-snooping-list-next-hops {
     description "Show the multicast list next-hop from snooping table";
     junos:command "show multicast snooping next-hops list";
     input {
       leaf identifier {
         description "ID of next hop";
         junos:cli-feature "nokeyword";
         type union {
           type uint32;
           type string {
             pattern "<.*>|$.*";
           }
         }
       }
     }
     output {
       choice output-tags {
         case actual-tag {
           container multicast-list-next-hops-information {
             uses multicast-list-next-hops-information-block;
           }
         }
         case multichassis-tag {
           container multi-routing-engine-results {
             list multi-routing-engine-item {
               leaf re-name {
                 type string;
               }
               choice output-tags {
                 case actual-tag {
                   container multicast-list-next-hops-information {
                     uses multicast-list-next-hops-information-block;
                   }
                 }
               }
             }
           }
         }
       }
     }
   }
   rpc get-satellite-control-indirect-next-hop {
     description "Show satellite multicast next-hops";
     junos:command "show multicast snooping next-hops satellite";
     input {
       leaf verbosity_level {
         junos:cli-feature "nokeyword";
         default "brief";
         type enumeration {
           enum "brief" {
             description "Display brief output (default)";
           }
           enum "detail" {
             description "Display detailed output";
           }
           enum "extensive" {
             description "Display extensive output";
           }
         }
       }
       leaf nexthop-id {
         description "Next-hop ID";
         type union {
           type int32;
           type string {
             pattern "<.*>|$.*";
           }
         }
       }
     }
     output {
       choice output-tags {
         case output-tag {
           leaf output {
             type string;
           }
         }
         case actual-tag {
           anyxml satellite-control-indirect-next-hop;
         }
         case multichassis-tag {
           anyxml multi-routing-engine-results;
         }
       }
     }
   }
   rpc get-satellite-control-ecid {
     description "Show the satellite multicast ECID mapping database";
     junos:command "show multicast ecid-mapping satellite";
     input {
       leaf verbosity_level {
         junos:cli-feature "nokeyword";
         default "brief";
         type enumeration {
           enum "brief" {
             description "Display brief output (default)";
           }
           enum "detail" {
             description "Display detailed output";
           }
           enum "extensive" {
             description "Display extensive output";
           }
         }
       }
       leaf device-id {
         description "Device ID";
         type union {
           type int32;
           type string {
             pattern "<.*>|$.*";
           }
         }
       }
       leaf ecid {
         description "ECID";
         type union {
           type int32;
           type string {
             pattern "<.*>|$.*";
           }
         }
       }
       leaf reference-id {
         description "Reference ID";
         type union {
           type int32;
           type string {
             pattern "<.*>|$.*";
           }
         }
       }
     }
     output {
       choice output-tags {
         case output-tag {
           leaf output {
             type string;
           }
         }
         case actual-tag {
           anyxml satellite-control-ecid;
         }
         case multichassis-tag {
           anyxml multi-routing-engine-results;
         }
       }
     }
   }
   rpc get-satellite-control-summary {
     description "Show satellite multicast summary information";
     junos:command "show multicast summary satellite";
     input {
       leaf verbosity_level {
         junos:cli-feature "nokeyword";
         default "detail";
         type enumeration {
           enum "brief" {
             description "Display brief output (default)";
           }
           enum "detail" {
             description "Display detailed output";
           }
         }
       }
     }
     output {
       choice output-tags {
         case output-tag {
           leaf output {
             type string;
           }
         }
         case actual-tag {
           anyxml satellite-control-summary;
         }
         case multichassis-tag {
           anyxml multi-routing-engine-results;
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping mc-fwd-cache-information-block {
     container mc-fwd-cache-threshold {
       leaf mc-instance {
         type string;
         description
           "Multicast Instance";
       }
       leaf mc-fwd-cache-family {
         type string;
         description
           "Multicast address family";
       }
       list mc-cache-params {
         key "mc-cache-param-name";
         leaf mc-cache-param-name {
           type string;
           description
             "Multicast Fwd Cache Parameter";
         }
         leaf mc-cache-param-value {
           type uint32;
           description
             "Multicast Fwd Cache parameter value";
         }
       }
     }
   }
   grouping multicast-route-information-block {
     leaf multicast-route-no-group-prefix {
       type jt:ipaddr;
     }
     leaf multicast-route-no-family {
       type string;
     }
     list route-family {
       key "address-family";
       leaf multicast-instance {
         type string;
       }
       leaf address-family {
         type string;
       }
       leaf bulking-indicator {
         type string;
       }
       container multicast-route-summaries {
         list multicast-route-summary {
           key "multicast-route-type multicast-route-state-type";
           leaf multicast-route-type {
             type string;
           }
           leaf multicast-route-state-type {
             type string;
           }
           leaf multicast-route-count {
             type int32;
           }
         }
       }
       list multicast-route {
         key "multicast-group-address";
         leaf multicast-group-address {
           type jt:ipaddr;
           description
             "Group address";
         }
         leaf multicast-group-prefix-length {
           type uint32;
           description
             "Group prefix length";
         }
         leaf multicast-route-protocol {
           type string;
         }
         leaf multicast-route-packet-type {
           type string;
         }
         leaf multicast-source-address {
           type jt:ipaddr;
           description
             "Source address";
         }
         leaf multicast-source-prefix-length {
           type uint32;
           description
             "Source prefix length";
         }
         leaf multicast-route-vlan-id {
           type int32;
         }
         leaf multicast-route-bridge-domain {
           type string;
         }
         leaf multicast-route-mesh-group {
           type string;
         }
         leaf upstream-interface-name {
           type string;
           description
             "Upstream interface";
         }
         leaf upstream-pair-nh-index {
           type string;
           description
             "Upstream pair nexthop index";
         }
         leaf rpf-check-disabled {
           type empty;
           description
             "Reverse path forwarding check is disabled";
         }
         leaf upstream-neighbor {
           type jt:ipaddr;
           description
             "IP Address of Upstream Neighbor";
         }
         leaf incoming-interface-list-names {
           type string;
           description
             "Incoming interface names";
         }
         leaf evpn-dci-ndf-upstream-interface-name {
           type string;
         }
         leaf evpn-dci-ndf-upstream-pair-nh-index {
           type string;
           description
             "EVPN DCI NDF upstream pair nexthop index";
         }
         leaf outgoing-interface-count {
           type int32;
         }
         leaf evpn-dci-ndf-outgoing-interface-count {
           type int32;
         }
         leaf rejected-downstream-interface-names {
           type string;
           description
             "Downstream interfaces rejected by bandwidth admission control";
         }
         leaf for-blank-line-line {
           type empty;
         }
         leaf session-name {
           type string;
         }
         leaf forwarding-rate-kilobytes {
           type uint32;
         }
         leaf forwarding-rate-packets {
           type uint32;
         }
         leaf forwarded-packet-count {
           type uint32;
         }
         leaf multicast-statistics-timed-out {
           type empty;
         }
         leaf rpf-next-hop-id {
           type uint32;
         }
         leaf next-hop-id {
           type uint32;
         }
         leaf multicast-route-next-hop-type {
           type string;
           description
             "Next-hop type";
         }
         leaf incoming-interface-list-id {
           type uint32;
           description
             "Incoming Interface list id";
         }
         leaf upstream-nbr-nh-id {
           type uint32;
           description
             "Upstream Neighbor Next-hop ID";
         }
         leaf upstream-protocol {
           type string;
         }
         leaf multicast-route-state {
           type string;
         }
         leaf multicast-route-forwarding-state {
           type string;
         }
         leaf multicast-route-uptime {
           type string;
         }
         leaf multicast-route-timeout {
           type string;
         }
         leaf interface-mismatch-count {
           type uint32;
         }
         leaf multicast-opaque-data {
           type string;
         }
         leaf multicast-route-sensor {
           type uint32;
         }
         leaf multicast-route-vlan {
           type string;
         }
         leaf bandwidth-for-admission-control {
           type uint64;
           description
             "Bandwidth used for admission control";
         }
         leaf pair-nh-index {
           type string;
           description
             "Pair nexthop index";
         }
         leaf downstream-interface-name {
           type string;
           description
             "Name of interface";
         }
         list multicast-route-source {
           key "multicast-source-address";
           leaf multicast-source-address {
             type jt:ipaddr;
             description
               "Source address";
           }
         }
         list upstream-rpf-interface-names {
           key "interface-name";
           leaf interface-name {
             type string;
             description
               "Name of interface";
           }
           leaf-list interface-nh-index {
             type uint32;
             description
               "Logical interface nexthop index";
           }
           leaf sub-mcnh-index {
             type uint32;
             description
               "Sub multicast composite nexthop index";
           }
           leaf upstream-rpf-labels {
             type string;
             description
               "Sender-Based RPF labels";
           }
           leaf rpf-session-id {
             type uint32;
             description
               "Session id";
           }
           leaf rpf-session-status {
             type string;
             description
               "Session Status";
           }
           leaf rpf-min-rate {
             type uint32;
             description
               "Min rate";
           }
           leaf rpf-weight {
             type uint32;
             description
               "RPF Weight";
           }
         }
         list downstream-interface-names {
           key "interface-name";
           leaf interface-name {
             type string;
             description
               "Name of interface";
           }
           leaf-list interface-nh-index {
             type uint32;
             description
               "Logical interface nexthop index";
           }
           leaf pair-nh-index {
             type string;
             description
               "Pair nexthop index";
           }
           leaf sub-mcnh-index {
             type uint32;
             description
               "Sub multicast composite nexthop index";
           }
         }
         list evpn-dci-ndf-downstream-interface-names {
           key "downstream-interface-name";
           leaf downstream-interface-name {
             type string;
             description
               "Name of interface";
           }
           leaf-list interface-nh-index {
             type uint32;
             description
               "Logical interface nexthop index";
           }
           leaf pair-nh-index {
             type string;
             description
               "Pair nexthop index";
           }
           leaf sub-mcnh-index {
             type uint32;
             description
               "Sub multicast composite nexthop index";
           }
         }
         container multicast-route-summaries {
           list multicast-route-summary {
             key "multicast-route-type multicast-route-state-type";
             leaf multicast-route-type {
               type string;
             }
             leaf multicast-route-state-type {
               type string;
             }
             leaf multicast-route-count {
               type int32;
             }
           }
         }
       }
       list l2ng-multicast-route {
         leaf multicast-group-address {
           type jt:ipaddr;
           description
             "Group address";
         }
         leaf multicast-group-prefix-length {
           type uint32;
           description
             "Group prefix length";
         }
         leaf multicast-route-protocol {
           type string;
         }
         leaf multicast-route-packet-type {
           type string;
         }
         leaf multicast-source-address {
           type jt:ipaddr;
           description
             "Source address";
         }
         leaf multicast-source-prefix-length {
           type uint32;
           description
             "Source prefix length";
         }
         leaf multicast-route-vlan-id {
           type int32;
         }
         leaf multicast-route-vlan {
           type string;
         }
         leaf multicast-route-mesh-group {
           type string;
         }
         leaf upstream-interface-name {
           type string;
           description
             "Upstream interface";
         }
         leaf rpf-check-disabled {
           type empty;
           description
             "Reverse path forwarding check is disabled";
         }
         leaf incoming-interface-list-names {
           type string;
           description
             "Incoming interface names";
         }
         leaf rejected-downstream-interface-names {
           type string;
           description
             "Downstream interfaces rejected by bandwidth admission control";
         }
         leaf session-name {
           type string;
         }
         leaf forwarding-rate-kilobytes {
           type uint32;
         }
         leaf forwarding-rate-packets {
           type uint32;
         }
         leaf forwarded-packet-count {
           type uint32;
         }
         leaf multicast-statistics-timed-out {
           type empty;
         }
         leaf next-hop-id {
           type uint32;
         }
         leaf incoming-interface-list-id {
           type uint32;
           description
             "Incoming Interface list id";
         }
         leaf upstream-protocol {
           type string;
         }
         leaf multicast-route-state {
           type string;
         }
         leaf multicast-route-forwarding-state {
           type string;
         }
         leaf multicast-route-uptime {
           type string;
         }
         leaf multicast-route-timeout {
           type string;
         }
         leaf interface-mismatch-count {
           type uint32;
         }
         leaf multicast-opaque-data {
           type string;
         }
         leaf multicast-route-sensor {
           type uint32;
         }
         leaf multicast-route-bridge-domain {
           type string;
         }
         leaf bandwidth-for-admission-control {
           type uint64;
           description
             "Bandwidth used for admission control";
         }
         list l2ng-downstream-interface-names {
           leaf interface-name {
             type string;
             description
               "Name of interface";
           }
           leaf-list interface-nh-index {
             type uint32;
             description
               "Logical interface nexthop index";
           }
           leaf sub-mcnh-index {
             type uint32;
             description
               "Sub multicast composite nexthop index";
           }
         }
         container l2ng-multicast-route-summary {
           leaf multicast-route-type {
             type string;
           }
           leaf multicast-route-state-type {
             type string;
           }
           leaf multicast-route-count {
             type int32;
           }
         }
       }
     }
   }
   grouping multicast-next-hops-information-block {
     list next-hops-family {
       key "address-family";
       leaf address-family {
         type string;
       }
       list iflist-next-hop {
         key "next-hop-id";
         leaf next-hop-id {
           type uint32;
         }
         leaf next-hop-ref-count {
           type uint32;
         }
         leaf next-hop-kernel-ref-count {
           type uint32;
         }
         leaf next-hop-addr {
           type uint32;
         }
         leaf rpf-next-hop-id {
           type uint32;
         }
         list next-hop-downstream-interface {
           key "interface-name";
           leaf interface-name {
             type string;
             description
               "Name of interface";
           }
           leaf interface-index {
             type int32;
           }
           leaf-list interface-nh-index {
             type uint32;
             description
               "Logical interface nexthop index";
           }
         }
         leaf next-hop-downstream-interface-count {
           type uint32;
         }
       }
     }
   }
   grouping multicast-list-next-hops-information-block {
     list list-next-hop {
       key "list-next-hop-id";
       leaf list-next-hop-id {
         type uint32;
       }
       leaf list-next-hop-ref-count {
         type uint32;
       }
       leaf list-next-hop-kernel-table-id {
         type uint32;
       }
       list list-next-hop-member-next-hops {
         key "member-interface-name";
         leaf member-interface-name {
           type string;
           description
             "Name of interface";
         }
       }
     }
   }
   grouping multicast-nh-session-information-block {
     leaf multicast-nh-session-none {
       type empty;
       description
         "No such session IDs currently in use";
     }
     list multicast-nh-session {
       key "multicast-nh-session-index";
       description
         "Multicast Composite next hop session IDs";
       leaf multicast-nh-session-index {
         type uint32;
       }
       leaf multicast-nh-session-role {
         type string;
       }
       leaf multicast-nh-session-l3-vrf {
         type string;
       }
       leaf multicast-nh-session-state {
         type string;
       }
       leaf multicast-nh-session-refcount {
         type uint32;
       }
       leaf multicast-nh-session-flag {
         type string;
       }
     }
   }
   grouping multicast-rpf-information-block {
     list rpf-family {
       key "address-family";
       leaf rpf-table-name {
         type string;
       }
       leaf rpf-table-entry-count {
         type uint32;
       }
       leaf address-family {
         type string;
       }
       list rpf-route {
         key "prefix";
         leaf prefix {
           type jt:ipaddr;
         }
         leaf rpf-route-inactive {
           type empty;
         }
         leaf rpf-route-protocol {
           type string;
         }
         leaf interface-name {
           type string;
           description
             "Name of interface";
         }
         leaf rpf-route-neighbor {
           type jt:ipaddr;
         }
       }
     }
   }
   grouping multicast-scope-information-block {
     list multicast-scope-policy-interfaces {
       key "instance-name";
       list multicast-scope-policy-interface {
         key "interface-name";
         leaf interface-name {
           type string;
           description
             "Name of interface";
         }
         leaf scope-state {
           type string;
         }
         leaf scope-rejects {
           type uint32;
           description
             "Number of rejects in multicast scope";
         }
         leaf link-local {
           type empty;
         }
         leaf node-local {
           type empty;
         }
         leaf organization-local {
           type empty;
         }
         leaf site-local {
           type empty;
         }
         leaf global {
           type empty;
         }
       }
       leaf instance-name {
         type string;
       }
       leaf address-family {
         type string;
       }
     }
     list multicast-scope {
       key "scope-name interface-name";
       description
         "Multicast scope to match";
       leaf scope-name {
         type string;
         description
           "Name of multicast scope";
       }
       leaf address-prefix {
         type jt:ipaddr;
       }
       leaf interface-name {
         type string;
         description
           "Name of interface";
       }
       leaf scope-state {
         type string;
       }
       leaf scope-rejects {
         type uint32;
         description
           "Number of rejects in multicast scope";
       }
       leaf link-local {
         type empty;
       }
       leaf node-local {
         type empty;
       }
       leaf organization-local {
         type empty;
       }
       leaf site-local {
         type empty;
       }
       leaf global {
         type empty;
       }
     }
     leaf multicast-scope-policy {
       type string;
     }
   }
   grouping multicast-sessions-information-block {
     leaf multicast-session-count {
       type uint32;
     }
     leaf multicast-sessions-type {
       type string;
     }
     list multicast-session {
       key "session-name";
       description
         "Multicast Composite next hop session IDs";
       leaf session-announcement {
         type string;
       }
       leaf session-name {
         type string;
       }
       leaf upstream-protocol {
         type string;
       }
       leaf session-version {
         type string;
       }
       leaf session-description {
         type string;
       }
       leaf session-uri {
         type string;
       }
       leaf session-email {
         type string;
       }
       leaf session-phone {
         type string;
       }
       leaf session-bandwidth {
         type string;
       }
       leaf session-start-time {
         type string;
       }
       leaf session-stop-time {
         type string;
       }
       leaf session-encryption-key {
         type string;
       }
       leaf session-attribute {
         type string;
       }
       leaf session-media {
         type string;
       }
       container session-origin {
         leaf session-originator-username {
           type string;
         }
         leaf session-originator-address {
           type string;
         }
       }
       container session-connection-data {
         leaf session-address {
           type string;
         }
         leaf session-ttl {
           type uint32;
         }
         leaf session-layers {
           type uint32;
         }
       }
     }
   }
   grouping multicast-statistics-information-block {
     list multicast-statistics {
       key "instance-name address-family";
       leaf instance-name {
         type string;
       }
       leaf address-family {
         type string;
       }
       leaf mc-resolves-no-mc-interface {
         type uint32;
         description
           "Number of resolve requests on non-multicast interfaces";
       }
       leaf mc-global-resolves-no-route {
         type uint32;
         description
           "Number of resolve requests with no route to source";
       }
       leaf mc-notifies-no-mc-interface {
         type uint32;
         description
           "Number of routing notifications on non-multicast interfaces";
       }
       leaf mc-notifies-no-route {
         type uint32;
         description
           "Number of routing notifications with no route to source";
       }
       leaf mc-mismatches-no-mc-interface {
         type uint32;
         description
           "Number of interface mismatches on non-multicast interfaces";
       }
       leaf mc-groups-no-mc-interface {
         type uint32;
         description
           "Number of group memberships on non-multicast interfaces";
       }
       list mc-stats-interface {
         key "interface-name";
         leaf interface-name {
           type string;
           description
             "Name of interface";
         }
         leaf protocol-name {
           type string;
         }
         leaf mc-mismatch-errors {
           type uint32;
           description
             "Number of interface mismatch errors";
         }
         leaf mc-mismatches {
           type uint32;
           description
             "Number of interface mismatches";
         }
         leaf mc-mismatches-no-route {
           type uint32;
           description
             "Number of interface mismatches due to no route to source";
         }
         leaf mc-resolves {
           type uint32;
           description
             "Number of resolve requests";
         }
         leaf mc-routing-notifies {
           type uint32;
           description
             "Number of routing notifications";
         }
         leaf mc-resolves-no-route {
           type uint32;
           description
             "Number of resolve requests with no route to source";
         }
         leaf mc-resolve-errors {
           type uint32;
           description
             "Number of resolve errors";
         }
         leaf mc-resolves-filtered {
           type uint32;
           description
             "Number of resolve requests filtered by policy";
         }
         leaf mc-routing-notifies-filtered {
           type uint32;
           description
             "Number of routing notifications filtered by policy";
         }
         leaf mc-input-kbytes {
           type uint64;
           description
             "Number of input kilobytes";
         }
         leaf mc-input-packets {
           type uint64;
           description
             "Number of input packets";
         }
         leaf mc-output-kbytes {
           type uint64;
           description
             "Number of output kilobytes";
         }
         leaf mc-output-packets {
           type uint64;
           description
             "Number of output packets";
         }
         list mc-stats-interface-p2mp-nbr {
           key "mc-p2mp-nbr-address";
           leaf mc-p2mp-nbr-address {
             type jt:ipaddr;
             description
               "P2MP Neighbor address";
           }
           leaf mc-p2mp-mismatch-errors {
             type uint32;
             description
               "Number of interface mismatch errors";
           }
           leaf mc-p2mp-mismatches {
             type uint32;
             description
               "Number of interface mismatches";
           }
           leaf mc-p2mp-mismatches-no-route {
             type uint32;
             description
               "Number of interface mismatches due to no route to source";
           }
           leaf mc-p2mp-resolves {
             type uint32;
             description
               "Number of resolve requests";
           }
           leaf mc-p2mp-routing-notifies {
             type uint32;
             description
               "Number of routing notifications";
           }
           leaf mc-p2mp-resolves-no-route {
             type uint32;
             description
               "Number of resolve requests with no route to source";
           }
           leaf mc-p2mp-resolve-errors {
             type uint32;
             description
               "Number of resolve errors";
           }
           leaf mc-p2mp-resolves-filtered {
             type uint32;
             description
               "Number of resolve requests filtered by policy";
           }
           leaf mc-p2mp-routing-notifies-filtered {
             type uint32;
             description
               "Number of routing notifications filtered by policy";
           }
           leaf mc-p2mp-input-kbytes {
             type uint64;
             description
               "Number of input kilobytes";
           }
           leaf mc-p2mp-input-packets {
             type uint64;
             description
               "Number of input packets";
           }
           leaf mc-p2mp-output-kbytes {
             type uint64;
             description
               "Number of output kilobytes";
           }
           leaf mc-p2mp-output-packets {
             type uint64;
             description
               "Number of output packets";
           }
           leaf protocol-name {
             type string;
           }
         }
       }
     }
   }
   grouping multicast-tunnels-information-block {
     list multicast-tunnel {
       leaf interface-name {
         type string;
         description
           "Name of interface";
       }
       leaf tunnel-local-address {
         type jt:ipaddr;
       }
       leaf tunnel-remote-address {
         type jt:ipaddr;
       }
       leaf tunnel-ttl {
         type uint32;
       }
     }
   }
   grouping multicast-usage-information-block {
     leaf multicast-usage-no-group-prefix {
       type jt:ipaddr;
     }
     leaf multicast-usage-strange-family {
       type uint32;
     }
     leaf multicast-usage-timed-out {
       type empty;
     }
     list multicast-group {
       key "multicast-group-address";
       leaf multicast-group-address {
         type jt:ipaddr;
         description
           "Group address";
       }
       leaf multicast-source-count {
         type uint32;
       }
       leaf multicast-packet-count {
         type uint32;
       }
       leaf multicast-packet-count-not-available {
         type empty;
       }
       leaf multicast-byte-count {
         type uint32;
       }
       leaf multicast-byte-count-not-available {
         type empty;
       }
       list multicast-group-source {
         key "multicast-source-address";
         leaf multicast-source-address {
           type jt:ipaddr;
           description
             "Source address";
         }
         leaf multicast-source-prefix-length {
           type uint32;
           description
             "Source prefix length";
         }
         leaf multicast-packet-count {
           type uint32;
         }
         leaf multicast-byte-count {
           type uint32;
         }
         leaf multicast-packet-count-not-available {
           type empty;
         }
         leaf multicast-byte-count-not-available {
           type empty;
         }
       }
     }
     list multicast-source {
       key "multicast-source-address";
       leaf multicast-source-address {
         type jt:ipaddr;
         description
           "Source address";
       }
       leaf multicast-source-prefix-length {
         type uint32;
         description
           "Source prefix length";
       }
       leaf multicast-group-count {
         type uint32;
       }
       leaf multicast-packet-count {
         type uint32;
       }
       leaf multicast-packet-count-not-available {
         type empty;
       }
       leaf multicast-byte-count {
         type uint32;
       }
       leaf multicast-byte-count-not-available {
         type empty;
       }
       list multicast-source-group {
         key "multicast-group-address";
         leaf multicast-group-address {
           type jt:ipaddr;
           description
             "Group address";
         }
         leaf multicast-packet-count {
           type uint32;
         }
         leaf multicast-byte-count {
           type uint32;
         }
         leaf multicast-packet-count-not-available {
           type empty;
         }
         leaf multicast-byte-count-not-available {
           type empty;
         }
       }
     }
   }
   grouping multicast-flow-maps-information-block {
     container multicast-flow-maps {
       description
         "Information about multicast flow maps for one routing instance";
       leaf instance-name {
         type string;
       }
       list multicast-flow-map {
         key "flow-map-name";
         description
           "Information about a multicast flow map";
         leaf flow-map-name {
           type string;
           description
             "Name of the flow map";
         }
         leaf policy-name {
           type string;
           description
             "Name of the policy";
         }
         leaf cache-timeout {
           type string;
           description
             "Delay before discarding a matched cache entry";
         }
         leaf flow-bandwidth {
           type uint64;
           description
             "Bandwidth for matched flows";
         }
         leaf bandwidth-type {
           type string;
           description
             "Bandwidth type for matched flows";
         }
         list redundant-sources {
           key "multicast-source-address";
           description
             "Redundant source addresses";
           leaf multicast-source-address {
             type jt:ipaddr;
             description
               "Source address";
           }
         }
       }
     }
   }
   grouping multicast-interface-information-block {
     list multicast-interface {
       key "interface-name";
       description
         "Information about a multicast interface";
       leaf interface-name {
         type string;
         description
           "Name of interface";
       }
       leaf interface-max-bandwidth {
         type uint64;
         description
           "Maximum bandwidth for multicast flows";
       }
       leaf interface-local-bandwidth-deduction {
         type int64;
         description
           "Bandwidth deduction for local multicast flows";
       }
       leaf interface-mapped-bandwidth-deduction {
         type int64;
         description
           "Bandwidth deduction for mapped multicast flows";
       }
       leaf interface-remaining-bandwidth {
         type int64;
         description
           "Remaining bandwidth for multicast flows";
       }
       leaf interface-reverse-oif-mapping {
         type string;
         description
           "Reverse OIF mapping is enabled";
       }
       leaf interface-reverse-oif-mapping-no-qos-adjust {
         type string;
         description
           "Reverse OIF mapping no QoS adjust is enabled";
       }
       leaf interface-subscriber-leave-timer {
         type uint32;
         description
           "Bw restore waiting time after subscriber leaves group";
       }
       leaf interface-no-qos-adjust {
         type string;
         description
           "Interface no QoS adjustment is enabled";
       }
     }
   }
   grouping multicast-pim-to-igmp-proxy-information-block {
     container multicast-pim-to-igmp-proxy {
       description
         "Pim-to-igmp-proxy state";
       leaf instance-name {
         type string;
       }
       leaf proxy-state {
         type string;
       }
       list proxy-upstream-interface {
         key "interface-name";
         leaf interface-name {
           type string;
           description
             "Name of interface";
         }
       }
     }
   }
   grouping multicast-pim-to-mld-proxy-information-block {
     container multicast-pim-to-mld-proxy {
       description
         "Pim-to-mld-proxy state";
       leaf instance-name {
         type string;
       }
       leaf proxy-state {
         type string;
       }
     }
     list proxy-upstream-interface {
       key "interface-name";
       leaf interface-name {
         type string;
         description
           "Name of interface";
       }
     }
   }
   grouping multicast-backup-pe-groups-information-block {
     container multicast-backup-pe-groups {
       description
         "Information about multicast backup PE groups for one routing 
         instance";
       leaf instance-name {
         type string;
       }
       list multicast-backup-pe-group {
         key "multicast-backup-pe-group-name";
         description
           "Information about a multicast backup PE group";
         leaf multicast-backup-pe-group-name {
           type string;
           description
             "Name of the backup PE group";
         }
         leaf designated-pe {
           type jt:ipaddr;
           description
             "Address of the designated PE";
         }
         leaf transitions {
           type uint32;
           description
             "Number of times desginated PE has changed";
         }
         leaf last-transition {
           type string;
           description
             "Time since last designated PE transition 
             (hours:minutes:seconds)";
         }
         leaf local-pe-address {
           type jt:ipaddr;
           description
             "Local address used in designated router election";
         }
         list backup-pes {
           key "multicast-backup-pe-address";
           description
             "Backup PE addresses";
           leaf multicast-backup-pe-address {
             type jt:ipaddr;
             description
               "Backup PE address";
           }
         }
       }
     }
   }
   grouping multicast-backup-pe-address-information-block {
     leaf multicast-backup-pe-address {
       type jt:ipaddr;
       description
         "Backup PE address";
     }
     leaf pe-address-local {
       type string;
       description
         "Indicates if this address belongs to this local PE";
     }
     leaf lsp-to-pe-up {
       type string;
       description
         "Indicates if the LSP to this PE is up";
     }
     container multicast-backup-pe-group-list {
       description
         "Information about multicast backup PE groups associatd with PE";
       list multicast-backup-pe-group-member {
         description
           "Information about a multicast backup PE group";
         leaf multicast-backup-pe-group-name {
           type string;
           description
             "Name of the backup PE group";
         }
       }
     }
   }
   grouping multicast-snp-evpn-core-nh-rt-information-block {
     list multicast-snp-evpn-core-nh-rt {
       description
         "Show multicast snooping evpn-core-nh-route info";
       leaf multicast-group-address {
         type jt:ipaddr;
         description
           "Group address";
       }
       leaf multicast-group-prefix-length {
         type uint32;
         description
           "Group prefix length";
       }
       leaf multicast-source-address {
         type jt:ipaddr;
         description
           "Source address";
       }
       leaf multicast-source-prefix-length {
         type uint32;
         description
           "Source prefix length";
       }
       leaf multicast-route-vlan {
         type string;
       }
       leaf multicast-route-mesh-group {
         type string;
       }
       leaf rt-table-id {
         type uint32;
         description
           "Route table ID";
       }
       leaf next-hop-id {
         type uint32;
       }
     }
   }
   grouping multicast-snp-l3-irb-elab-rt-information-block {
     list multicast-snp-l3-irb-elab-rt {
       description
         "Show multicast snooping l3-irb-elaboration-route info";
       leaf multicast-group-address {
         type jt:ipaddr;
         description
           "Group address";
       }
       leaf multicast-group-prefix-length {
         type uint32;
         description
           "Group prefix length";
       }
       leaf multicast-source-address {
         type jt:ipaddr;
         description
           "Source address";
       }
       leaf multicast-source-prefix-length {
         type uint32;
         description
           "Source prefix length";
       }
       leaf upstream-interface-name {
         type string;
         description
           "Upstream interface";
       }
       leaf-list l3-irb-rt-downstream-interface-name {
         type string;
       }
       leaf-list interface-nh-index {
         type uint32;
         description
           "Logical interface nexthop index";
       }
       leaf rt-table-id {
         type uint32;
         description
           "Route table ID";
       }
       leaf next-hop-id {
         type uint32;
       }
     }
   }
 }
