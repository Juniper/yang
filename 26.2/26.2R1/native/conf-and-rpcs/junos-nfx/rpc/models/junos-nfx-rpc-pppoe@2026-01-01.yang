/*
 * Copyright (c) 2026 Juniper Networks, Inc.
 * All rights reserved.
 */
 module junos-nfx-rpc-pppoe {
   namespace "http://yang.juniper.net/junos-nfx/rpc/pppoe";

   prefix pppoe;

   import junos-common-types {
     prefix jt;
     revision-date 2026-01-01;
   }

   organization "Juniper Networks, Inc.";

   contact "yang-support@juniper.net";

   description "Junos RPC YANG module for pppoe command(s)";

   revision 2026-01-01 {
     description "Junos: 26.2R1.7";
   }

   rpc get-pppoe-interface-information {
     description "Show interface information";
     input {
       leaf control-plane-instance {
         description "Control plane instance name";
         type string;
         mandatory true;
       }
       leaf level {
         type enumeration {
           enum "brief" {
             description "Show brief output";
           }
           enum "detail" {
             description "Show detailed output";
           }
           enum "extensive" {
             description "Show extensive output";
           }
         }
       }
       leaf interface-name {
         description "Name of PPPoE logical interface";
         type string;
       }
     }
     output {
       choice output-tags {
         case actual-tag {
           container pppoe-interface-information {
             uses pppoe-interface-information-block;
           }
         }
         case multichassis-tag {
           container multi-routing-engine-results {
             list multi-routing-engine-item {
               leaf re-name {
                 type string;
               }
               choice output-tags {
                 case actual-tag {
                   container pppoe-interface-information {
                     uses pppoe-interface-information-block;
                   }
                 }
               }
             }
           }
         }
       }
     }
   }
   rpc get-pppoe-lockout-information {
     description "Show interface lockout information";
     input {
       leaf control-plane-instance {
         description "Control plane instance name";
         type string;
         mandatory true;
       }
       leaf underlying-interface-name {
         description "Name of PPPoE underlying logical interface";
         type string;
       }
     }
     output {
       choice output-tags {
         case output-tag {
           leaf output {
             type string;
           }
         }
         case actual-tag {
           anyxml pppoe-lockout-information;
         }
         case multichassis-tag {
           anyxml multi-routing-engine-results;
         }
       }
     }
   }
   rpc get-pppoe-lockout-vlan-information {
     description "VLAN Identifier of PPPoE underlying logical interface";
     input {
       leaf device-name {
         description "Name of physical port or AE bundle";
         type union {
           type jt:interface-device;
           type string {
             pattern "<.*>|$.*";
           }
         }
         mandatory true;
       }
       leaf svlan-id {
         description "SVLAN tag";
         type union {
           type string {
             pattern "<.*>|$.*";
           }
           type uint16 {
             range "1 .. 4094";
           }
         }
       }
       leaf vlan-id {
         description "VLAN tag";
         type union {
           type string {
             pattern "<.*>|$.*";
           }
           type uint16 {
             range "1 .. 4094";
           }
         }
       }
     }
     output {
       choice output-tags {
         case output-tag {
           leaf output {
             type string;
           }
         }
         case actual-tag {
           anyxml pppoe-lockout-information;
         }
         case multichassis-tag {
           anyxml multi-routing-engine-results;
         }
       }
     }
   }
   rpc get-pppoe-service-name-table-information {
     description "Show service name table information";
     input {
       leaf control-plane-instance {
         description "Control plane instance name";
         type string;
         mandatory true;
       }
       leaf table-name {
         description "Name of PPPoE service name table";
         type string;
       }
     }
     output {
       choice output-tags {
         case actual-tag {
           container pppoe-service-name-table-information {
             uses pppoe-service-name-table-information-block;
           }
         }
         case multichassis-tag {
           container multi-routing-engine-results {
             list multi-routing-engine-item {
               leaf re-name {
                 type string;
               }
               choice output-tags {
                 case actual-tag {
                   container pppoe-service-name-table-information {
                     uses pppoe-service-name-table-information-block;
                   }
                 }
               }
             }
           }
         }
       }
     }
   }
   rpc get-pppoe-session-information {
     description "Show active PPPoE session information";
     input {
       leaf control-plane-instance {
         description "Control plane instance name";
         type string;
         mandatory true;
       }
       leaf service {
         description "Name of PPPoE service";
         type string;
       }
       leaf aci {
         description "Agent Circuit ID";
         type string;
       }
       leaf ari {
         description "Agent Remote ID";
         type string;
       }
     }
     output {
       choice output-tags {
         case output-tag {
           leaf output {
             type string;
           }
         }
         case actual-tag {
           anyxml pppoe-session-information;
         }
         case multichassis-tag {
           anyxml multi-routing-engine-results;
         }
       }
     }
   }
   rpc get-pppoe-statistics-information {
     description "Show PPPoE-related interface statistics";
     input {
       leaf control-plane-instance {
         description "Control plane instance name";
         type string;
         mandatory true;
       }
       leaf underlying-interface-name {
         description "Name of PPPoE underlying logical interface";
         type string;
       }
     }
     output {
       choice output-tags {
         case actual-tag {
           container pppoe-statistics-information {
             uses pppoe-statistics-information-block;
           }
         }
         case multichassis-tag {
           container multi-routing-engine-results {
             list multi-routing-engine-item {
               leaf re-name {
                 type string;
               }
               choice output-tags {
                 case actual-tag {
                   container pppoe-statistics-information {
                     uses pppoe-statistics-information-block;
                   }
                 }
               }
             }
           }
         }
       }
     }
   }
   rpc get-pppoe-interface-set-information {
     description "Show interface set information";
     input {
       leaf control-plane-instance {
         description "Control plane instance name";
         type string;
         mandatory true;
       }
       leaf interface-set-name {
         description "Name of PPPoE interface set";
         type string;
       }
     }
     output {
       choice output-tags {
         case actual-tag {
           container pppoe-interface-set-information {
             uses pppoe-interface-set-information-block;
           }
         }
         case multichassis-tag {
           container multi-routing-engine-results {
             list multi-routing-engine-item {
               leaf re-name {
                 type string;
               }
               choice output-tags {
                 case actual-tag {
                   container pppoe-interface-set-information {
                     uses pppoe-interface-set-information-block;
                   }
                 }
               }
             }
           }
         }
       }
     }
   }
   rpc get-pppoe-underlying-interface-information {
     description "Show underlying interface information";
     input {
       leaf control-plane-instance {
         description "Control plane instance name";
         type string;
         mandatory true;
       }
       leaf level {
         type enumeration {
           enum "brief" {
             description "Show brief output";
           }
           enum "detail" {
             description "Show detailed output";
           }
           enum "extensive" {
             description "Show extensive output";
           }
           enum "lockout" {
             description "Show lockout output";
           }
         }
       }
       leaf underlying-interface-name {
         description "Name of PPPoE underlying logical interface";
         type string;
       }
     }
     output {
       choice output-tags {
         case actual-tag {
           container pppoe-underlying-interface-information {
             uses pppoe-underlying-interface-information-block;
           }
         }
         case multichassis-tag {
           container multi-routing-engine-results {
             list multi-routing-engine-item {
               leaf re-name {
                 type string;
               }
               choice output-tags {
                 case actual-tag {
                   container pppoe-underlying-interface-information {
                     uses pppoe-underlying-interface-information-block;
                   }
                 }
               }
             }
           }
         }
       }
     }
   }
   rpc get-pppoe-version {
     description "Show version";
     input {
       leaf control-plane-instance {
         description "Control plane instance name";
         type string;
         mandatory true;
       }
     }
     output {
       choice output-tags {
         case actual-tag {
           container pppoe-version {
             uses pppoe-version-block;
           }
         }
         case multichassis-tag {
           container multi-routing-engine-results {
             list multi-routing-engine-item {
               leaf re-name {
                 type string;
               }
               choice output-tags {
                 case actual-tag {
                   container pppoe-version {
                     uses pppoe-version-block;
                   }
                 }
               }
             }
           }
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping pppoe-interface-information-block {
     list pppoe-interface {
       leaf interface-name {
         type string;
         description
           "Interface name";
       }
       leaf underlying-interface-name {
         type string;
         description
           "Underlying interface name";
       }
       leaf state {
         type string;
         description
           "State";
       }
       leaf session-id {
         type string;
         description
           "Session ID";
       }
       leaf remote-mac {
         type string;
         description
           "Remote MAC address";
       }
       leaf padg-credits {
         type int32;
         description
           "PADG transmit credits";
       }
       leaf interface-index {
         type string;
         description
           "Index";
       }
       leaf ifl-type {
         type string;
         description
           "Type";
       }
       leaf service-name {
         type string;
         description
           "Service name";
       }
       leaf ac-name-session {
         type string;
         description
           "Session AC name";
       }
       leaf ac-name-config {
         type string;
         description
           "Configured AC name";
       }
       leaf session-uptime {
         type string;
         description
           "Duration for which the session has been up";
       }
       leaf dynamic-profile {
         type string;
         description
           "Dynamic Profile name";
       }
       leaf auto-reconnect {
         type string;
         description
           "Autoreconnect timeout";
       }
       leaf idle-timeout {
         type string;
         description
           "Idle timeout";
       }
       leaf underlying-interface-index {
         type string;
         description
           "Underlying interface index";
       }
       leaf ignore-eol-tag {
         type string;
         description
           "Ignore End-of-List TAG";
       }
       leaf agent-circuit-id {
         type string;
         description
           "Agent Circuit ID";
       }
       leaf agent-remote-id {
         type string;
         description
           "Agent Remote ID";
       }
       leaf aci-iflset-name {
         type string;
         description
           "ACI Interface Set name";
       }
       leaf aci-iflset-index {
         type string;
         description
           "ACI Interface Set index";
       }
       leaf padm-motm {
         type string;
         description
           "PADM Message of the Moment tag";
       }
       leaf padm-hurl {
         type string;
         description
           "PADM HTTP URL tag";
       }
       leaf pppoe-credits {
         type string;
         description
           "Forwarding credit balances";
       }
       leaf pppoe-credit-scale-factor {
         type string;
         description
           "Scaling factor";
       }
       leaf dynamic-interface-bandwidth {
         type string;
         description
           "Dynamic interface bandwidth";
       }
       leaf ppp-max-payload-tag {
         type int32;
         description
           "PPP-Max-Payload TAG";
       }
       leaf pppoe-relay-session-id {
         type string;
         description
           "PPPoE Relay Session ID";
       }
     }
   }
   grouping pppoe-service-name-table-information-block {
     leaf service-name-table {
       type string;
       description
         "Name of Service Name Table";
     }
     container pppoe-service-name {
       leaf service-name {
         type string;
         description
           "Service name";
       }
       leaf service-action {
         type string;
         description
           "Service action";
       }
       leaf dynamic-profile {
         type string;
         description
           "Dynamic Profile name";
       }
       leaf routing-instance {
         type string;
         description
           "Routing Instance name";
       }
       leaf max-sessions {
         type int32;
         description
           "Maximum number of PPPoE sessions";
       }
       leaf active-sessions {
         type int32;
         description
           "Number of active PPPoE sessions";
       }
       leaf max-sessions-exceeded-delay {
         type string;
         description
           "Max-sessions exceeded delay";
       }
       container pppoe-aci-ari-entry {
         leaf agent-circuit-id {
           type string;
           description
             "Agent Circuit ID";
         }
         leaf agent-remote-id {
           type string;
           description
             "Agent Remote ID";
         }
         leaf service-action {
           type string;
           description
             "Service action";
         }
         leaf dynamic-profile {
           type string;
           description
             "Dynamic Profile name";
         }
         leaf routing-instance {
           type string;
           description
             "Routing Instance name";
         }
         leaf static-interface {
           type string;
           description
             "Static PPPoE Interface name";
         }
       }
     }
   }
   grouping pppoe-statistics-information-block {
     container pppoe-statistics {
       leaf active-sessions {
         type int32;
         description
           "Number of active PPPoE sessions";
       }
       container pppoe-counters {
         leaf padi-sent {
           type int32;
           description
             "PADI sent counter";
         }
         leaf padi-received {
           type int32;
           description
             "PADI received counter";
         }
         leaf pado-sent {
           type int32;
           description
             "PADO sent counter";
         }
         leaf pado-received {
           type int32;
           description
             "PADO received counter";
         }
         leaf padr-sent {
           type int32;
           description
             "PADR sent counter";
         }
         leaf padr-received {
           type int32;
           description
             "PADR received counter";
         }
         leaf pads-sent {
           type int32;
           description
             "PADS sent counter";
         }
         leaf pads-received {
           type int32;
           description
             "PADS received counter";
         }
         leaf padt-sent {
           type int32;
           description
             "PADT sent counter";
         }
         leaf padt-received {
           type int32;
           description
             "PADT received counter";
         }
         leaf padm-sent {
           type int32;
           description
             "PADM sent counter";
         }
         leaf padm-received {
           type int32;
           description
             "PADM received counter";
         }
         leaf padn-sent {
           type int32;
           description
             "PADN sent counter";
         }
         leaf padn-received {
           type int32;
           description
             "PADN received counter";
         }
         leaf padg-sent {
           type int32;
           description
             "PADG sent counter";
         }
         leaf padg-received {
           type int32;
           description
             "PADG received counter";
         }
         leaf padc-sent {
           type int32;
           description
             "PADC sent counter";
         }
         leaf padc-received {
           type int32;
           description
             "PADC received counter";
         }
         leaf padq-sent {
           type int32;
           description
             "PADQ sent counter";
         }
         leaf padq-received {
           type int32;
           description
             "PADQ received counter";
         }
         leaf servname-err-sent {
           type int32;
           description
             "Service name error sent counter";
         }
         leaf servname-err-received {
           type int32;
           description
             "Service name error received counter";
         }
         leaf acsystem-err-sent {
           type int32;
           description
             "AC system error sent counter";
         }
         leaf acsystem-err-received {
           type int32;
           description
             "AC system error received counter";
         }
         leaf generic-err-sent {
           type int32;
           description
             "Generic error sent counter";
         }
         leaf generic-err-received {
           type int32;
           description
             "Generic error received counter";
         }
         leaf malformed-pkt-received {
           type int32;
           description
             "Malformed error received counter";
         }
         leaf unknown-pkt-received {
           type int32;
           description
             "Unknown packet received counter";
         }
         leaf padi-tmo {
           type int32;
           description
             "PADI timeout counter";
         }
         leaf pado-tmo {
           type int32;
           description
             "PADO timeout counter";
         }
         leaf padr-tmo {
           type int32;
           description
             "PADR timeout counter";
         }
         leaf padi-recv-err {
           type int32;
           description
             "PADI receive error counter";
         }
         leaf pado-recv-err {
           type int32;
           description
             "PADO receive error counter";
         }
         leaf padr-recv-err {
           type int32;
           description
             "PADR receive error counter";
         }
         leaf pads-recv-err {
           type int32;
           description
             "PADS receive error counter";
         }
       }
     }
   }
   grouping pppoe-interface-set-information-block {
     container pppoe-interface-set {
       leaf interface-set-name {
         type string;
         description
           "Interface set name";
       }
       leaf interface-set-index {
         type string;
         description
           "Interface set index";
       }
       leaf state {
         type string;
         description
           "State";
       }
       leaf dynamic-profile {
         type string;
         description
           "Dynamic Profile name";
       }
       leaf max-sessions {
         type int32;
         description
           "Maximum number of PPPoE sessions";
       }
       leaf max-sessions-vsa-ignore {
         type string;
         description
           "Ignore max-sessions VSA";
       }
       leaf active-sessions {
         type int32;
         description
           "Number of active PPPoE sessions";
       }
       leaf agent-circuit-id {
         type string;
         description
           "Agent Circuit ID";
       }
       leaf agent-remote-id {
         type string;
         description
           "Agent Remote ID";
       }
     }
     container pppoe-interface-set-members {
       description
         "PPPoE interface-set member information";
       list pppoe-interface {
         leaf interface-name {
           type string;
           description
             "Interface name";
         }
         leaf interface-index {
           type string;
           description
             "Index";
         }
         leaf padg-credits {
           type int32;
           description
             "PADG transmit credits";
         }
       }
     }
   }
   grouping pppoe-underlying-interface-information-block {
     list pppoe-underlying-interface {
       leaf underlying-interface-name {
         type string;
         description
           "Underlying interface name";
       }
       leaf service-name-table {
         type string;
         description
           "Name of Service Name Table";
       }
       leaf dynamic-profile {
         type string;
         description
           "Dynamic Profile name";
       }
       leaf underlying-interface-index {
         type string;
         description
           "Underlying interface index";
       }
       leaf state {
         type string;
         description
           "State";
       }
       leaf max-sessions {
         type int32;
         description
           "Maximum number of PPPoE sessions";
       }
       leaf max-sessions-vsa-ignore {
         type string;
         description
           "Ignore max-sessions VSA";
       }
       leaf active-sessions {
         type int32;
         description
           "Number of active PPPoE sessions";
       }
       leaf ac-name {
         type string;
         description
           "Access Concentrator name";
       }
       leaf duplicate-protection {
         type string;
         description
           "Duplicate protection mode";
       }
       leaf short-cycle-protection {
         type string;
         description
           "Short cycle protection mode";
       }
       leaf aci-autosensing {
         type string;
         description
           "ACI VLAN Autosensing mode";
       }
       leaf line-identity-autosensing {
         type string;
         description
           "Line Identity Autosensing mode";
       }
       leaf direct-connect {
         type string;
         description
           "Direct connect mode";
       }
       leaf encapsulation-type-identifier {
         type string;
         description
           "Encapsulation type identifier";
       }
     }
   }
   grouping pppoe-version-block {
     leaf max-sessions {
       type int32;
       description
         "Maximum number of PPPoE sessions";
     }
     leaf padi-resend-tmo {
       type int32;
       description
         "PADI resend timeout";
     }
     leaf padr-resend-tmo {
       type int32;
       description
         "PADR resend timeout";
     }
     leaf max-resend-tmo {
       type int32;
       description
         "Maximum resend timeout";
     }
     leaf max-ac-tmo {
       type int32;
       description
         "Maximum configured AC timeout";
     }
   }
 }
