/*
 * Copyright (c) 2026 Juniper Networks, Inc.
 * All rights reserved.
 */
 module junos-nfx-rpc-network-access {
   namespace "http://yang.juniper.net/junos-nfx/rpc/network-access";

   prefix network-access;

   import junos-common-types {
     prefix jt;
     revision-date 2026-01-01;
   }

   organization "Juniper Networks, Inc.";

   contact "yang-support@juniper.net";

   description "Junos RPC YANG module for network-access command(s)";

   revision 2026-01-01 {
     description "Junos: 26.2R1.7";
   }

   rpc get-authentication-pending-table {
     description "Show pending authentication requests";
     input {
       uses command-forwarding;
       leaf control-plane-instance {
         description "Control plane instance name";
         type string;
         mandatory true;
       }
       choice filter {
         case detail {
           leaf get-authentication-pending-table-detailed {
             description "Show the detailed information";
             type empty;
           }
         }
         case index {
           leaf get-authentication-pending-table-specific {
             description "Show detail information for a specific request";
             type union {
               type string {
                 pattern "<.*>|$.*";
               }
               type uint64 {
                 range "1 .. 18446744073709551615";
               }
             }
           }
         }
       }
     }
     output {
       choice output-tags {
         case output-tag {
           leaf output {
             type string;
           }
         }
         case actual-tag {
           anyxml auth-pending-table;
         }
         case multichassis-tag {
           anyxml multi-routing-engine-results;
         }
       }
     }
   }
   rpc get-authentication-statistics {
     description "Show authentication statistics";
     input {
       uses command-forwarding;
       leaf control-plane-instance {
         description "Control plane instance name";
         type string;
         mandatory true;
       }
     }
     output {
       choice output-tags {
         case actual-tag {
           container auth-statistics {
             uses auth-statistics-block;
           }
         }
         case multichassis-tag {
           container multi-routing-engine-results {
             list multi-routing-engine-item {
               leaf re-name {
                 type string;
               }
               choice output-tags {
                 case actual-tag {
                   container auth-statistics {
                     uses auth-statistics-block;
                   }
                 }
               }
             }
           }
         }
       }
     }
   }
   rpc get-domain-map-statistics {
     description "Domain-map module statistics";
     input {
       uses command-forwarding;
       leaf control-plane-instance {
         description "Control plane instance name";
         type string;
         mandatory true;
       }
     }
     output {
       choice output-tags {
         case actual-tag {
           container domain-map-statistics {
             uses domain-map-statistics-block;
           }
         }
         case multichassis-tag {
           container multi-routing-engine-results {
             list multi-routing-engine-item {
               leaf re-name {
                 type string;
               }
               choice output-tags {
                 case actual-tag {
                   container domain-map-statistics {
                     uses domain-map-statistics-block;
                   }
                 }
               }
             }
           }
         }
       }
     }
   }
   rpc get-inline-napt-pool-table {
     description "Show NAPT pool information";
     input {
       leaf control-plane-instance {
         description "Control plane instance name";
         type string;
         mandatory true;
       }
       leaf pool-name {
         description "Show information for a specific pool";
         type string;
         mandatory true;
       }
     }
     output {
       choice output-tags {
         case actual-tag {
           container inline-napt-pool-table {
             uses inline-napt-pool-table-block;
           }
         }
         case multichassis-tag {
           container multi-routing-engine-results {
             list multi-routing-engine-item {
               leaf re-name {
                 type string;
               }
               choice output-tags {
                 case actual-tag {
                   container inline-napt-pool-table {
                     uses inline-napt-pool-table-block;
                   }
                 }
               }
             }
           }
         }
       }
     }
   }
   rpc get-aaa-subscriber-table {
     description "List subscriber specific command options";
     input {
       uses command-forwarding;
       leaf control-plane-instance {
         description "Control plane instance name";
         type string;
         mandatory true;
       }
       leaf username {
         description "Show details for this subscriber's session entry";
         type string;
       }
       leaf routing-instance {
         description "Name of routing instance";
         type string;
       }
       choice lsys-tenant {
       }
       choice daemon-select {
         case logical-system {
         }
       }
     }
     output {
       choice output-tags {
         case output-tag {
           leaf output {
             type string;
           }
         }
         case actual-tag {
           anyxml aaa-subscriber-table;
         }
         case multichassis-tag {
           anyxml multi-routing-engine-results;
         }
       }
     }
   }
   rpc get-aaa-subscriber-by-session-id {
     description "Session id";
     input {
       leaf control-plane-instance {
         description "Control plane instance name";
         type string;
         mandatory true;
       }
       leaf id {
         description "Session id";
         type union {
           type string {
             pattern "<.*>|$.*";
           }
           type uint64 {
             range "1 .. 18446744073709551615";
           }
         }
         mandatory true;
       }
       leaf level {
         default "brief";
         type enumeration {
           enum "brief" {
             description "Show brief output";
           }
           enum "detail" {
             description "Show detailed output";
           }
         }
       }
       choice lsys-tenant {
       }
       choice daemon-select {
         case logical-system {
           leaf logical-system {
             description "Name of logical system";
             type string {
             }
           }
         }
       }
       leaf tenant {
         description "Name of tenant";
         type string {
         }
       }
     }
     output {
       choice output-tags {
         case actual-tag {
           container authd-subsciber-by-session-id-information {
             uses authd-subsciber-by-session-id-information-block;
           }
         }
         case multichassis-tag {
           container multi-routing-engine-results {
             list multi-routing-engine-item {
               leaf re-name {
                 type string;
               }
               choice output-tags {
                 case actual-tag {
                   container authd-subsciber-by-session-id-information {
                     uses authd-subsciber-by-session-id-information-block;
                   }
                 }
               }
             }
           }
         }
       }
     }
   }
   rpc get-aaa-subscriber-statistics {
     description "Statistics on subscriber events";
     input {
       uses command-forwarding;
       leaf control-plane-instance {
         description "Control plane instance name";
         type string;
         mandatory true;
       }
       leaf username {
         description "Show statistics for this subscriber's session entry";
         type string;
         mandatory true;
       }
       choice lsys-tenant {
       }
       choice daemon-select {
         case logical-system {
         }
       }
     }
     output {
       choice output-tags {
         case output-tag {
           leaf output {
             type string;
           }
         }
         case actual-tag {
           anyxml aaa-subscriber-statistics;
         }
         case multichassis-tag {
           anyxml multi-routing-engine-results;
         }
       }
     }
   }
   rpc get-aaa-module-statistics {
     description "(Re)authentication, authorization and accounting (AAA) module statistics";
     input {
       uses command-forwarding;
       leaf control-plane-instance {
         description "Control plane instance name";
         type string;
         mandatory true;
       }
       leaf statistics-type {
         type enumeration {
           enum "authentication" {
             description "Authentication statistics";
           }
           enum "accounting" {
             description "Accounting statistics";
           }
           enum "dynamic-requests" {
             description "Dynamic requests statistics";
           }
           enum "re-authentication" {
             description "Re-authentication statistics";
           }
           enum "preauthentication" {
             description "Preauthentication statistics";
           }
           enum "subscribers" {
             description "Subscriber statistics";
           }
           enum "radius" {
             description "RADIUS statistics";
           }
           enum "pending-accounting-stops" {
             description "Pending Accounting stop statistics";
           }
           enum "saml" {
             description "SAML statistics";
           }
         }
         mandatory true;
       }
       leaf detail {
         description "Display detailed output";
         type empty;
       }
     }
     output {
       choice output-tags {
         case actual-tag {
           container aaa-module-statistics {
             uses aaa-module-statistics-block;
           }
         }
         case multichassis-tag {
           container multi-routing-engine-results {
             list multi-routing-engine-item {
               leaf re-name {
                 type string;
               }
               choice output-tags {
                 case actual-tag {
                   container aaa-module-statistics {
                     uses aaa-module-statistics-block;
                   }
                 }
               }
             }
           }
         }
       }
     }
   }
   rpc get-session-limit-per-username {
     description "Show session limit per username related information";
     input {
       leaf control-plane-instance {
         description "Control plane instance name";
         type string;
         mandatory true;
       }
       leaf level {
         default "summary";
         type enumeration {
           enum "summary" {
             description "Show summary output";
           }
           enum "brief" {
             description "Show brief output";
           }
           enum "detail" {
             description "Show detailed output";
           }
         }
       }
     }
     output {
       choice output-tags {
         case output-tag {
           leaf output {
             type string;
           }
         }
         case actual-tag {
           anyxml aaa-session-limit-per-username-info;
         }
         case multichassis-tag {
           anyxml multi-routing-engine-results;
         }
       }
     }
   }
   rpc get-address-assignment-pool-statistics {
     description "Show pool information based on pool name";
     input {
       leaf control-plane-instance {
         description "Control plane instance name";
         type string;
         mandatory true;
       }
       leaf get-address-assignment-pool-table-specific {
         description "Show information for a specific pool";
         type string;
         mandatory true;
       }
       leaf routing-instance {
         description "Name of routing instance";
         type string;
       }
       choice lsys-tenant {
       }
       choice daemon-select {
         case logical-system {
           leaf logical-system {
             description "Name of logical system";
             type string {
             }
           }
         }
       }
       leaf tenant {
         description "Name of tenant";
         type string {
         }
       }
     }
     output {
       choice output-tags {
         case actual-tag {
           container aaa-module-statistics {
             uses aaa-module-statistics-block;
           }
         }
         case multichassis-tag {
           container multi-routing-engine-results {
             list multi-routing-engine-item {
               leaf re-name {
                 type string;
               }
               choice output-tags {
                 case actual-tag {
                   container aaa-module-statistics {
                     uses aaa-module-statistics-block;
                   }
                 }
               }
             }
           }
         }
       }
     }
   }
   rpc get-address-assignment-client-statistics {
     description "Show pool information based on client";
     input {
       leaf control-plane-instance {
         description "Control plane instance name";
         type string;
         mandatory true;
       }
       leaf routing-instance {
         description "Name of routing instance";
         type string;
       }
       choice daemon-select {
         case logical-system {
           leaf logical-system {
             description "Name of logical system";
             type string {
             }
           }
         }
       }
     }
     output {
       choice output-tags {
         case actual-tag {
           container aaa-module-statistics {
             uses aaa-module-statistics-block;
           }
         }
         case multichassis-tag {
           container multi-routing-engine-results {
             list multi-routing-engine-item {
               leaf re-name {
                 type string;
               }
               choice output-tags {
                 case actual-tag {
                   container aaa-module-statistics {
                     uses aaa-module-statistics-block;
                   }
                 }
               }
             }
           }
         }
       }
     }
   }
   rpc get-inline-napt-pool-statistics {
     description "Show NAPT pool information";
     input {
       leaf control-plane-instance {
         description "Control plane instance name";
         type string;
         mandatory true;
       }
       leaf pool-name {
         description "Show information for a specific pool";
         type string;
         mandatory true;
       }
     }
     output {
       choice output-tags {
         case actual-tag {
           container aaa-module-statistics {
             uses aaa-module-statistics-block;
           }
         }
         case multichassis-tag {
           container multi-routing-engine-results {
             list multi-routing-engine-item {
               leaf re-name {
                 type string;
               }
               choice output-tags {
                 case actual-tag {
                   container aaa-module-statistics {
                     uses aaa-module-statistics-block;
                   }
                 }
               }
             }
           }
         }
       }
     }
   }
   rpc get-reconciliation-statistics {
     description "Reconciliation statistics";
     input {
       leaf control-plane-instance {
         description "Control plane instance name";
         type string;
         mandatory true;
       }
     }
     output {
       choice output-tags {
         case output-tag {
           leaf output {
             type string;
           }
         }
         case actual-tag {
           anyxml aaa-module-reconciliation;
         }
         case multichassis-tag {
           anyxml multi-routing-engine-results;
         }
       }
     }
   }
   rpc get-aaa-terminate-code {
     description "Show terminate-code information";
     input {
       uses command-forwarding;
       leaf verbosity_level {
         default "summary";
         type enumeration {
           enum "summary" {
             description "Display summary output(default)";
           }
           enum "brief" {
             description "Display brief output";
           }
           enum "detail" {
             description "Display detailed output";
           }
         }
       }
       leaf control-plane-instance {
         description "Control plane instance name";
         type string;
         mandatory true;
       }
     }
     output {
       choice output-tags {
         case output-tag {
           leaf output {
             type string;
           }
         }
         case actual-tag {
           anyxml aaa-terminate-code;
         }
         case multichassis-tag {
           anyxml multi-routing-engine-results;
         }
       }
     }
   }
   rpc get-aaa-terminate-code-aaa {
     description "Limit display to AAA terminate codes";
     input {
       uses command-forwarding;
       leaf verbosity_level {
         default "summary";
         type enumeration {
           enum "summary" {
             description "Display summary output(default)";
           }
           enum "brief" {
             description "Display brief output";
           }
           enum "detail" {
             description "Display detailed output";
           }
         }
       }
       leaf control-plane-instance {
         description "Control plane instance name";
         type string;
         mandatory true;
       }
     }
     output {
       choice output-tags {
         case output-tag {
           leaf output {
             type string;
           }
         }
         case actual-tag {
           anyxml aaa-terminate-code-aaa;
         }
         case multichassis-tag {
           anyxml multi-routing-engine-results;
         }
       }
     }
   }
   rpc get-aaa-terminate-code-dhcp {
     description "Limit display to DHCP terminate codes";
     input {
       uses command-forwarding;
       leaf verbosity_level {
         default "summary";
         type enumeration {
           enum "summary" {
             description "Display summary output(default)";
           }
           enum "brief" {
             description "Display brief output";
           }
           enum "detail" {
             description "Display detailed output";
           }
         }
       }
       leaf control-plane-instance {
         description "Control plane instance name";
         type string;
         mandatory true;
       }
     }
     output {
       choice output-tags {
         case output-tag {
           leaf output {
             type string;
           }
         }
         case actual-tag {
           anyxml aaa-terminate-code-dhcp;
         }
         case multichassis-tag {
           anyxml multi-routing-engine-results;
         }
       }
     }
   }
   rpc get-aaa-terminate-code-l2tp {
     description "Limit display to L2TP terminate codes";
     input {
       uses command-forwarding;
       leaf verbosity_level {
         default "summary";
         type enumeration {
           enum "summary" {
             description "Display summary output(default)";
           }
           enum "brief" {
             description "Display brief output";
           }
           enum "detail" {
             description "Display detailed output";
           }
         }
       }
       leaf control-plane-instance {
         description "Control plane instance name";
         type string;
         mandatory true;
       }
     }
     output {
       choice output-tags {
         case output-tag {
           leaf output {
             type string;
           }
         }
         case actual-tag {
           anyxml aaa-terminate-code-l2tp;
         }
         case multichassis-tag {
           anyxml multi-routing-engine-results;
         }
       }
     }
   }
   rpc get-aaa-terminate-code-ppp {
     description "Limit display to PPP terminate codes";
     input {
       uses command-forwarding;
       leaf verbosity_level {
         default "summary";
         type enumeration {
           enum "summary" {
             description "Display summary output(default)";
           }
           enum "brief" {
             description "Display brief output";
           }
           enum "detail" {
             description "Display detailed output";
           }
         }
       }
       leaf control-plane-instance {
         description "Control plane instance name";
         type string;
         mandatory true;
       }
     }
     output {
       choice output-tags {
         case output-tag {
           leaf output {
             type string;
           }
         }
         case actual-tag {
           anyxml aaa-terminate-code-ppp;
         }
         case multichassis-tag {
           anyxml multi-routing-engine-results;
         }
       }
     }
   }
   rpc get-aaa-terminate-code-reverse {
     description "Show reverse terminate-code information";
     input {
       uses command-forwarding;
       leaf verbosity_level {
         default "summary";
         type enumeration {
           enum "summary" {
             description "Display summary output(default)";
           }
           enum "brief" {
             description "Display brief output";
           }
           enum "detail" {
             description "Display detailed output";
           }
         }
       }
       leaf control-plane-instance {
         description "Control plane instance name";
         type string;
         mandatory true;
       }
     }
     output {
       choice output-tags {
         case output-tag {
           leaf output {
             type string;
           }
         }
         case actual-tag {
           anyxml aaa-terminate-code-reverss;
         }
         case multichassis-tag {
           anyxml multi-routing-engine-results;
         }
       }
     }
   }
   rpc get-aaa-terminate-code-reverse-aaa {
     description "Limit display to AAA terminate codes";
     input {
       uses command-forwarding;
       leaf verbosity_level {
         default "summary";
         type enumeration {
           enum "summary" {
             description "Display summary output(default)";
           }
           enum "brief" {
             description "Display brief output";
           }
           enum "detail" {
             description "Display detailed output";
           }
         }
       }
       leaf control-plane-instance {
         description "Control plane instance name";
         type string;
         mandatory true;
       }
     }
     output {
       choice output-tags {
         case output-tag {
           leaf output {
             type string;
           }
         }
         case actual-tag {
           anyxml aaa-terminate-code-reverse-aaa;
         }
         case multichassis-tag {
           anyxml multi-routing-engine-results;
         }
       }
     }
   }
   rpc get-aaa-terminate-code-reverse-dhcp {
     description "Limit display to DHCP terminate codes";
     input {
       uses command-forwarding;
       leaf verbosity_level {
         default "summary";
         type enumeration {
           enum "summary" {
             description "Display summary output(default)";
           }
           enum "brief" {
             description "Display brief output";
           }
           enum "detail" {
             description "Display detailed output";
           }
         }
       }
       leaf control-plane-instance {
         description "Control plane instance name";
         type string;
         mandatory true;
       }
     }
     output {
       choice output-tags {
         case output-tag {
           leaf output {
             type string;
           }
         }
         case actual-tag {
           anyxml aaa-terminate-code-reverse-dhcp;
         }
         case multichassis-tag {
           anyxml multi-routing-engine-results;
         }
       }
     }
   }
   rpc get-aaa-terminate-code-reverse-l2tp {
     description "Limit display to L2TP terminate codes";
     input {
       uses command-forwarding;
       leaf verbosity_level {
         default "summary";
         type enumeration {
           enum "summary" {
             description "Display summary output(default)";
           }
           enum "brief" {
             description "Display brief output";
           }
           enum "detail" {
             description "Display detailed output";
           }
         }
       }
       leaf control-plane-instance {
         description "Control plane instance name";
         type string;
         mandatory true;
       }
     }
     output {
       choice output-tags {
         case output-tag {
           leaf output {
             type string;
           }
         }
         case actual-tag {
           anyxml aaa-terminate-code-reverse-l2tp;
         }
         case multichassis-tag {
           anyxml multi-routing-engine-results;
         }
       }
     }
   }
   rpc get-aaa-terminate-code-reverse-ppp {
     description "Limit display to PPP terminate codes";
     input {
       uses command-forwarding;
       leaf verbosity_level {
         default "summary";
         type enumeration {
           enum "summary" {
             description "Display summary output(default)";
           }
           enum "brief" {
             description "Display brief output";
           }
           enum "detail" {
             description "Display detailed output";
           }
         }
       }
       leaf control-plane-instance {
         description "Control plane instance name";
         type string;
         mandatory true;
       }
     }
     output {
       choice output-tags {
         case output-tag {
           leaf output {
             type string;
           }
         }
         case actual-tag {
           anyxml aaa-terminate-code-reverse-ppp;
         }
         case multichassis-tag {
           anyxml multi-routing-engine-results;
         }
       }
     }
   }
   rpc get-aaa-accounting-status {
     description "Statistics of RADIUS servers";
     input {
       uses command-forwarding;
       leaf control-plane-instance {
         description "Control plane instance name";
         type string;
         mandatory true;
       }
     }
     output {
       choice output-tags {
         case actual-tag {
           container aaa-accounting-status {
             uses aaa-accounting-status-block;
           }
         }
         case multichassis-tag {
           container multi-routing-engine-results {
             list multi-routing-engine-item {
               leaf re-name {
                 type string;
               }
               choice output-tags {
                 case actual-tag {
                   container aaa-accounting-status {
                     uses aaa-accounting-status-block;
                   }
                 }
               }
             }
           }
         }
       }
     }
   }
   rpc get-radius-servers-table {
     description "Show RADIUS servers information";
     input {
       uses command-forwarding;
       leaf control-plane-instance {
         description "Control plane instance name";
         type string;
         mandatory true;
       }
       leaf verbosity_level {
         default "brief";
         type enumeration {
           enum "brief" {
             description "Display brief output";
           }
           enum "detail" {
             description "Display detailed output";
           }
         }
       }
     }
     output {
       choice output-tags {
         case actual-tag {
           container aaa-module-radius-servers-information {
             uses aaa-module-radius-servers-information-block;
           }
         }
         case multichassis-tag {
           container multi-routing-engine-results {
             list multi-routing-engine-item {
               leaf re-name {
                 type string;
               }
               choice output-tags {
                 case actual-tag {
                   container aaa-module-radius-servers-information {
                     uses aaa-module-radius-servers-information-block;
                   }
                 }
               }
             }
           }
         }
       }
     }
   }
   rpc get-saml-assertion-cache-information {
     description "Show assertion cache information";
     input {
       uses command-forwarding;
       leaf control-plane-instance {
         description "Control plane instance name";
         type string;
         mandatory true;
       }
       leaf level {
         default "brief";
         type enumeration {
           enum "brief" {
             description "Show brief output (default)";
           }
           enum "detail" {
             description "Show detailed output";
           }
         }
       }
       choice display-choice {
         case username {
           leaf username {
             description "SAML authenticated user, same as user login id";
             type string;
           }
         }
         case domain {
           leaf domain {
             description "Domain like example.net or any, same as configured domain in profile";
             type string;
           }
         }
       }
     }
     output {
       choice output-tags {
         case actual-tag {
           container saml-assertion-cache-information {
             uses saml-assertion-cache-information-block;
           }
         }
         case multichassis-tag {
           container multi-routing-engine-results {
             list multi-routing-engine-item {
               leaf re-name {
                 type string;
               }
               choice output-tags {
                 case actual-tag {
                   container saml-assertion-cache-information {
                     uses saml-assertion-cache-information-block;
                   }
                 }
               }
             }
           }
         }
       }
     }
   }
   rpc get-address-assignment-pool-table {
     description "Show pool information";
     input {
       uses command-forwarding;
       leaf control-plane-instance {
         description "Control plane instance name";
         type string;
         mandatory true;
       }
       leaf get-address-assignment-pool-table-specific {
         description "Show information for a specific pool";
         type string;
         mandatory true;
       }
       leaf routing-instance {
         description "Name of routing instance";
         type string;
       }
       choice lsys-tenant {
       }
       choice daemon-select {
         case logical-system {
         }
       }
     }
     output {
       choice output-tags {
         case output-tag {
           leaf output {
             type string;
           }
         }
         case actual-tag {
           anyxml address-assignment-pool-table;
         }
         case multichassis-tag {
           anyxml multi-routing-engine-results;
         }
       }
     }
   }
   rpc get-address-assignment-preserved-table {
     description "Show preserved addresses";
     input {
       uses command-forwarding;
       leaf control-plane-instance {
         description "Control plane instance name";
         type string;
         mandatory true;
       }
       leaf routing-instance {
         description "Name of routing instance";
         type string;
       }
       choice lsys-tenant {
       }
       choice daemon-select {
         case logical-system {
         }
       }
       leaf address-type {
         description "Address preservation address types";
         type enumeration {
           enum "delegated-prefix" {
             description "Address preservation IPv6 delegated prefix";
           }
           enum "ipv4-address" {
             description "Address preservation IPv4 address";
           }
           enum "ipv6-address" {
             description "Address preservation IPv6 WAN address (/128 or Router-Advertisement prefix)";
           }
         }
       }
     }
     output {
       choice output-tags {
         case actual-tag {
           container aaa-module-address-assignment-reserved-addresses {
             uses aaa-module-address-assignment-reserved-addresses-block;
           }
         }
         case multichassis-tag {
           container multi-routing-engine-results {
             list multi-routing-engine-item {
               leaf re-name {
                 type string;
               }
               choice output-tags {
                 case actual-tag {
                   container aaa-module-address-assignment-reserved-addresses {
                     uses aaa-module-address-assignment-reserved-addresses-block;
                   }
                 }
               }
             }
           }
         }
       }
     }
   }
   rpc get-authd-apm-status {
     description "Show APM connection/alarm status information";
     input {
       leaf control-plane-instance {
         description "Control plane instance name";
         type string;
         mandatory true;
       }
     }
     output {
       choice output-tags {
         case actual-tag {
           container authd-apm-status {
             uses authd-apm-status-block;
           }
         }
         case multichassis-tag {
           container multi-routing-engine-results {
             list multi-routing-engine-item {
               leaf re-name {
                 type string;
               }
               choice output-tags {
                 case actual-tag {
                   container authd-apm-status {
                     uses authd-apm-status-block;
                   }
                 }
               }
             }
           }
         }
       }
     }
   }
   rpc get-authd-apm-domain-information {
     description "Show address-pool-manager domain status";
     input {
       leaf control-plane-instance {
         description "Control plane instance name";
         type string;
         mandatory true;
       }
       leaf get-authd-apm-domain-name {
         description "Show detailed APM domain statistics";
         type string;
       }
       leaf get-authd-apm-domain-routing-instance {
         description "Name of routing instance";
         type string;
       }
     }
     output {
       choice output-tags {
         case actual-tag {
           container authd-apm-domain-information {
             uses authd-apm-domain-information-block;
           }
         }
         case multichassis-tag {
           container multi-routing-engine-results {
             list multi-routing-engine-item {
               leaf re-name {
                 type string;
               }
               choice output-tags {
                 case actual-tag {
                   container authd-apm-domain-information {
                     uses authd-apm-domain-information-block;
                   }
                 }
               }
             }
           }
         }
       }
     }
   }
   rpc get-authd-apm-domain-state {
     description "Show address-pool-manager domain state";
     input {
       leaf control-plane-instance {
         description "Control plane instance name";
         type string;
         mandatory true;
       }
       leaf get-apm-domain-state-routing-instance {
         description "Name of routing instance";
         type string;
       }
     }
     output {
       choice output-tags {
         case actual-tag {
           container authd-apm-domain-state {
             uses authd-apm-domain-state-block;
           }
         }
         case multichassis-tag {
           container multi-routing-engine-results {
             list multi-routing-engine-item {
               leaf re-name {
                 type string;
               }
               choice output-tags {
                 case actual-tag {
                   container authd-apm-domain-state {
                     uses authd-apm-domain-state-block;
                   }
                 }
               }
             }
           }
         }
       }
     }
   }
   rpc node-secret-file-table {
     description "Show SecurID server's node secret file path";
     input {
       uses command-forwarding;
       leaf control-plane-instance {
         description "Control plane instance name";
         type string;
         mandatory true;
       }
     }
     output {
       choice output-tags {
         case actual-tag {
           container node-secret-file-table {
             uses node-secret-file-table-block;
           }
         }
         case multichassis-tag {
           container multi-routing-engine-results {
             list multi-routing-engine-item {
               leaf re-name {
                 type string;
               }
               choice output-tags {
                 case actual-tag {
                   container node-secret-file-table {
                     uses node-secret-file-table-block;
                   }
                 }
               }
             }
           }
         }
       }
     }
   }
   rpc get-jsrc-counters {
     description "Jsrc module statistics";
     input {
       uses command-forwarding;
       leaf control-plane-instance {
         description "Control plane instance name";
         type string;
         mandatory true;
       }
     }
     output {
       choice output-tags {
         case output-tag {
           leaf output {
             type string;
           }
         }
         case actual-tag {
           anyxml jsrc-counters;
         }
         case multichassis-tag {
           anyxml multi-routing-engine-results;
         }
       }
     }
   }
   rpc get-gx-plus-state-information {
     description "Show gx-plus state information";
     input {
       uses command-forwarding;
       leaf control-plane-instance {
         description "Control plane instance name";
         type string;
         mandatory true;
       }
     }
     output {
       choice output-tags {
         case actual-tag {
           container gx-plus-state-information {
             uses gx-plus-state-information-block;
           }
         }
         case multichassis-tag {
           container multi-routing-engine-results {
             list multi-routing-engine-item {
               leaf re-name {
                 type string;
               }
               choice output-tags {
                 case actual-tag {
                   container gx-plus-state-information {
                     uses gx-plus-state-information-block;
                   }
                 }
               }
             }
           }
         }
       }
     }
   }
   rpc get-gx-plus-sync-state-information {
     description "Show gx-plus sync-state information";
     input {
       uses command-forwarding;
       leaf control-plane-instance {
         description "Control plane instance name";
         type string;
         mandatory true;
       }
     }
     output {
       choice output-tags {
         case actual-tag {
           container gx-plus-sync-state-information {
             uses gx-plus-sync-state-information-block;
           }
         }
         case multichassis-tag {
           container multi-routing-engine-results {
             list multi-routing-engine-item {
               leaf re-name {
                 type string;
               }
               choice output-tags {
                 case actual-tag {
                   container gx-plus-sync-state-information {
                     uses gx-plus-sync-state-information-block;
                   }
                 }
               }
             }
           }
         }
       }
     }
   }
   rpc get-gx-plus-statistics-information {
     description "Show gx-plus statistics information";
     input {
       uses command-forwarding;
       leaf verbosity_level {
         default "brief";
         type enumeration {
           enum "brief" {
             description "Show brief output (deafault)";
           }
           enum "detail" {
             description "Show detailed output";
           }
           enum "extensive" {
             description "Show extensive output";
           }
         }
       }
       leaf control-plane-instance {
         description "Control plane instance name";
         type string;
         mandatory true;
       }
     }
     output {
       choice output-tags {
         case actual-tag {
           container gx-plus-statistics-information {
             uses gx-plus-statistics-information-block;
           }
         }
         case multichassis-tag {
           container multi-routing-engine-results {
             list multi-routing-engine-item {
               leaf re-name {
                 type string;
               }
               choice output-tags {
                 case actual-tag {
                   container gx-plus-statistics-information {
                     uses gx-plus-statistics-information-block;
                   }
                 }
               }
             }
           }
         }
       }
     }
   }
   rpc get-nasreq-counters {
     description "Nasreq module statistics";
     input {
       uses command-forwarding;
       leaf control-plane-instance {
         description "Control plane instance name";
         type string;
         mandatory true;
       }
     }
     output {
       choice output-tags {
         case output-tag {
           leaf output {
             type string;
           }
         }
         case actual-tag {
           anyxml nasreq-counters;
         }
         case multichassis-tag {
           anyxml multi-routing-engine-results;
         }
       }
     }
   }
   rpc get-pcrf-state-information {
     description "Show pcrf state information";
     input {
       uses command-forwarding;
       leaf control-plane-instance {
         description "Control plane instance name";
         type string;
         mandatory true;
       }
     }
     output {
       choice output-tags {
         case actual-tag {
           container pcrf-state-information {
             uses pcrf-state-information-block;
           }
         }
         case multichassis-tag {
           container multi-routing-engine-results {
             list multi-routing-engine-item {
               leaf re-name {
                 type string;
               }
               choice output-tags {
                 case actual-tag {
                   container pcrf-state-information {
                     uses pcrf-state-information-block;
                   }
                 }
               }
             }
           }
         }
       }
     }
   }
   rpc get-pcrf-statistics-information {
     description "Show pcrf statistics information";
     input {
       uses command-forwarding;
       leaf verbosity_level {
         default "brief";
         type enumeration {
           enum "brief" {
             description "Show brief output (deafault)";
           }
           enum "detail" {
             description "Show detailed output";
           }
           enum "extensive" {
             description "Show extensive output";
           }
         }
       }
       leaf control-plane-instance {
         description "Control plane instance name";
         type string;
         mandatory true;
       }
     }
     output {
       choice output-tags {
         case actual-tag {
           container pcrf-statistics-information {
             uses pcrf-statistics-information-block;
           }
         }
         case multichassis-tag {
           container multi-routing-engine-results {
             list multi-routing-engine-item {
               leaf re-name {
                 type string;
               }
               choice output-tags {
                 case actual-tag {
                   container pcrf-statistics-information {
                     uses pcrf-statistics-information-block;
                   }
                 }
               }
             }
           }
         }
       }
     }
   }
   rpc get-ocs-state-information {
     description "Show ocs state information";
     input {
       uses command-forwarding;
       leaf control-plane-instance {
         description "Control plane instance name";
         type string;
         mandatory true;
       }
     }
     output {
       choice output-tags {
         case actual-tag {
           container ocs-state-information {
             uses ocs-state-information-block;
           }
         }
         case multichassis-tag {
           container multi-routing-engine-results {
             list multi-routing-engine-item {
               leaf re-name {
                 type string;
               }
               choice output-tags {
                 case actual-tag {
                   container ocs-state-information {
                     uses ocs-state-information-block;
                   }
                 }
               }
             }
           }
         }
       }
     }
   }
   rpc get-ocs-statistics-information {
     description "Show ocs statistics information";
     input {
       uses command-forwarding;
       leaf verbosity_level {
         default "brief";
         type enumeration {
           enum "brief" {
             description "Show brief output (deafault)";
           }
           enum "detail" {
             description "Show detailed output";
           }
           enum "extensive" {
             description "Show extensive output";
           }
         }
       }
       leaf control-plane-instance {
         description "Control plane instance name";
         type string;
         mandatory true;
       }
     }
     output {
       choice output-tags {
         case actual-tag {
           container ocs-statistics-information {
             uses ocs-statistics-information-block;
           }
         }
         case multichassis-tag {
           container multi-routing-engine-results {
             list multi-routing-engine-item {
               leaf re-name {
                 type string;
               }
               choice output-tags {
                 case actual-tag {
                   container ocs-statistics-information {
                     uses ocs-statistics-information-block;
                   }
                 }
               }
             }
           }
         }
       }
     }
   }
   rpc get-radsec-state-information {
     description "Show radsec state information";
     input {
       uses command-forwarding;
       leaf control-plane-instance {
         description "Control plane instance name";
         type string;
         mandatory true;
       }
       leaf radsec-state-destination {
         description "Destination to show";
         type union {
           type uint32;
           type string {
             pattern "<.*>|$.*";
           }
         }
       }
     }
     output {
       choice output-tags {
         case actual-tag {
           container radsec-state-information {
             uses radsec-state-information-block;
           }
         }
         case multichassis-tag {
           container multi-routing-engine-results {
             list multi-routing-engine-item {
               leaf re-name {
                 type string;
               }
               choice output-tags {
                 case actual-tag {
                   container radsec-state-information {
                     uses radsec-state-information-block;
                   }
                 }
               }
             }
           }
         }
       }
     }
   }
   rpc get-radsec-statistics-information {
     description "Show radsec statistics information";
     input {
       uses command-forwarding;
       leaf verbosity_level {
         default "brief";
         type enumeration {
           enum "brief" {
             description "Show brief output (deafault)";
           }
           enum "detail" {
             description "Show detailed output";
           }
           enum "extensive" {
             description "Show extensive output";
           }
         }
       }
       leaf control-plane-instance {
         description "Control plane instance name";
         type string;
         mandatory true;
       }
       leaf radsec-statistics-destination {
         description "Destination to show";
         type union {
           type uint32;
           type string {
             pattern "<.*>|$.*";
           }
         }
       }
     }
     output {
       choice output-tags {
         case output-tag {
           leaf output {
             type string;
           }
         }
         case actual-tag {
           anyxml rasec-statistics-information;
         }
         case multichassis-tag {
           anyxml multi-routing-engine-results;
         }
       }
     }
   }
   rpc get-local-cert-state-information {
     description "Show local certificate state information";
     input {
       uses command-forwarding;
       leaf control-plane-instance {
         description "Control plane instance name";
         type string;
         mandatory true;
       }
     }
     output {
       choice output-tags {
         case actual-tag {
           container local-cert-state-information {
             uses local-cert-state-information-block;
           }
         }
         case multichassis-tag {
           container multi-routing-engine-results {
             list multi-routing-engine-item {
               leaf re-name {
                 type string;
               }
               choice output-tags {
                 case actual-tag {
                   container local-cert-state-information {
                     uses local-cert-state-information-block;
                   }
                 }
               }
             }
           }
         }
       }
     }
   }
   rpc get-local-cert-statistics-information {
     description "Show local certificate statistics information";
     input {
       uses command-forwarding;
       leaf verbosity_level {
         default "brief";
         type enumeration {
           enum "brief" {
             description "Show brief output (deafault)";
           }
           enum "detail" {
             description "Show detailed output";
           }
           enum "extensive" {
             description "Show extensive output";
           }
         }
       }
       leaf control-plane-instance {
         description "Control plane instance name";
         type string;
         mandatory true;
       }
     }
     output {
       choice output-tags {
         case actual-tag {
           container local-cert-statistics-information {
             uses local-cert-statistics-information-block;
           }
         }
         case multichassis-tag {
           container multi-routing-engine-results {
             list multi-routing-engine-item {
               leaf re-name {
                 type string;
               }
               choice output-tags {
                 case actual-tag {
                   container local-cert-statistics-information {
                     uses local-cert-statistics-information-block;
                   }
                 }
               }
             }
           }
         }
       }
     }
   }
   rpc get-s6a-state-information {
     description "Show s6a state information";
     input {
       uses command-forwarding;
       leaf control-plane-instance {
         description "Control plane instance name";
         type string;
         mandatory true;
       }
     }
     output {
       choice output-tags {
         case actual-tag {
           container s6a-state-information {
             uses s6a-state-information-block;
           }
         }
         case multichassis-tag {
           container multi-routing-engine-results {
             list multi-routing-engine-item {
               leaf re-name {
                 type string;
               }
               choice output-tags {
                 case actual-tag {
                   container s6a-state-information {
                     uses s6a-state-information-block;
                   }
                 }
               }
             }
           }
         }
       }
     }
   }
   rpc get-s6a-statistics-information {
     description "Show s6a statistics information";
     input {
       uses command-forwarding;
       leaf verbosity_level {
         default "brief";
         type enumeration {
           enum "brief" {
             description "Show brief output (deafault)";
           }
           enum "detail" {
             description "Show detailed output";
           }
           enum "extensive" {
             description "Show extensive output";
           }
         }
       }
       leaf control-plane-instance {
         description "Control plane instance name";
         type string;
         mandatory true;
       }
     }
     output {
       choice output-tags {
         case actual-tag {
           container s6a-statistics-information {
             uses s6a-statistics-information-block;
           }
         }
         case multichassis-tag {
           container multi-routing-engine-results {
             list multi-routing-engine-item {
               leaf re-name {
                 type string;
               }
               choice output-tags {
                 case actual-tag {
                   container s6a-statistics-information {
                     uses s6a-statistics-information-block;
                   }
                 }
               }
             }
           }
         }
       }
     }
   }
   rpc get-nas-5g-state-information {
     description "Show nas-5g state information";
     input {
       uses command-forwarding;
       leaf control-plane-instance {
         description "Control plane instance name";
         type string;
         mandatory true;
       }
     }
     output {
       choice output-tags {
         case actual-tag {
           container nas-5g-state-information {
             uses nas-5g-state-information-block;
           }
         }
         case multichassis-tag {
           container multi-routing-engine-results {
             list multi-routing-engine-item {
               leaf re-name {
                 type string;
               }
               choice output-tags {
                 case actual-tag {
                   container nas-5g-state-information {
                     uses nas-5g-state-information-block;
                   }
                 }
               }
             }
           }
         }
       }
     }
   }
   rpc get-nas-5g-counters {
     description "Show nas-5g statistics information";
     input {
       uses command-forwarding;
       leaf verbosity_level {
         default "brief";
         type enumeration {
           enum "brief" {
             description "Show brief output (deafault)";
           }
           enum "detail" {
             description "Show detailed output";
           }
           enum "extensive" {
             description "Show extensive output";
           }
         }
       }
       leaf control-plane-instance {
         description "Control plane instance name";
         type string;
         mandatory true;
       }
     }
     output {
       choice output-tags {
         case output-tag {
           leaf output {
             type string;
           }
         }
         case actual-tag {
           anyxml nas-5g-counters;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping auth-statistics-block {
     container total-statistics {
       leaf total-requests {
         type uint32;
         description
           "Number of authentication requests received";
       }
       leaf total-responses {
         type uint32;
         description
           "Number of authentication requests replied to";
       }
     }
     container radius-auth-statistics {
       leaf total-requests {
         type uint32;
         description
           "Number of authentication requests received";
       }
       leaf success-responses {
         type uint32;
         description
           "Number of succeeded authentication requests";
       }
       leaf failure-responses {
         type uint32;
         description
           "Number of failed authentication requests";
       }
     }
     container radius-reauth-statistics {
       leaf total-requests {
         type uint32;
         description
           "Number of authentication requests received";
       }
       leaf success-responses {
         type uint32;
         description
           "Number of succeeded authentication requests";
       }
       leaf failure-responses {
         type uint32;
         description
           "Number of failed authentication requests";
       }
     }
     container ldap-auth-statistics {
       leaf total-requests {
         type uint32;
         description
           "Number of authentication requests received";
       }
       leaf success-responses {
         type uint32;
         description
           "Number of succeeded authentication requests";
       }
       leaf failure-responses {
         type uint32;
         description
           "Number of failed authentication requests";
       }
     }
     container securid-auth-statistics {
       leaf total-requests {
         type uint32;
         description
           "Number of authentication requests received";
       }
       leaf success-responses {
         type uint32;
         description
           "Number of succeeded authentication requests";
       }
       leaf failure-responses {
         type uint32;
         description
           "Number of failed authentication requests";
       }
     }
     container local-auth-statistics {
       leaf total-requests {
         type uint32;
         description
           "Number of authentication requests received";
       }
       leaf success-responses {
         type uint32;
         description
           "Number of succeeded authentication requests";
       }
       leaf failure-responses {
         type uint32;
         description
           "Number of failed authentication requests";
       }
     }
     container local-reauth-statistics {
       leaf total-requests {
         type uint32;
         description
           "Number of authentication requests received";
       }
       leaf success-responses {
         type uint32;
         description
           "Number of succeeded authentication requests";
       }
       leaf failure-responses {
         type uint32;
         description
           "Number of failed authentication requests";
       }
     }
   }
   grouping domain-map-statistics-block {
     leaf matched-domains {
       type uint32;
       description
         "The parsed domain name matched a configured domain";
     }
     leaf unmatched-domains {
       type uint32;
       description
         "The parsed domain name did not match any configured domains";
     }
     leaf missing-domains {
       type uint32;
       description
         "The username is missing the domain portion";
     }
     leaf stripped-username {
       type uint32;
       description
         "The domain portion was stripped from the username string";
     }
     leaf stripped-domain {
       type uint32;
       description
         "The user portion was stripped for authentication only";
     }
     leaf default-used {
       type uint32;
       description
         "Domain name of default was used for the mapping";
     }
   }
   grouping inline-napt-pool-table-block {
     container inline-napt-pool-entry {
       leaf ip-address {
         type jt:ipaddr;
         description
           "IPv4/v6 address/prefix assigned to the client";
       }
     }
   }
   grouping authd-subsciber-by-session-id-information-block {
     list authd-service-pcrf-ubm-usage {
       description
         "Show PCRF last report data by session-id";
       leaf ubm-session-id {
         type uint64;
         description
           "Service session id";
       }
       leaf ubm-service-name {
         type string;
         description
           "Service session name";
       }
       leaf ubm-service-state {
         type string;
         description
           "Service session state";
       }
       leaf ubm-last-duration {
         type uint32;
         description
           "Duration usage at the last CCR-U report";
       }
       leaf ubm-last-input-bytes {
         type uint64;
         description
           "Input-byte usage at the last CCR-U report";
       }
       leaf ubm-last-output-bytes {
         type uint64;
         description
           "Output-byte usage at the last CCR-U report";
       }
       leaf ubm-last-total-bytes {
         type uint64;
         description
           "Total-byte usage at the last CCR-U report";
       }
     }
   }
   grouping aaa-module-statistics-block {
     leaf requests {
       type uint32;
       description
         "Number of requests received";
     }
     leaf multistack-requests {
       type uint32;
       description
         "Number of multistack requests received";
     }
     leaf accepts {
       type uint32;
       description
         "Number of authentication accepts";
     }
     leaf rejects {
       type uint32;
       description
         "Number of authentication rejects";
     }
     leaf radius-failures {
       type uint32;
       description
         "Number of RADIUS authentication failures";
     }
     leaf rejects-queue-request-deleted {
       type uint32;
       description
         "Number of authentication rejects due to queue request deleted";
     }
     leaf rejects-malformed-reply {
       type uint32;
       description
         "Number of authentication rejects due to malformed reply";
     }
     leaf rejects-no-server-configured {
       type uint32;
       description
         "Number of authentication rejects due to no servers configured";
     }
     leaf rejects-access-profile-config-unavailable {
       type uint32;
       description
         "Number of authentication rejects due to unavailable access profile
         configuration";
     }
     leaf rejects-no-client-record {
       type uint32;
       description
         "Number of authentication rejects due to failure to create client 
         record";
     }
     leaf rejects-no-client-request {
       type uint32;
       description
         "Number of authentication rejects due to failure to create client 
         request";
     }
     leaf rejects-no-build-auth-request {
       type uint32;
       description
         "Number of authentication rejects due to failure to build 
         authentication request";
     }
     leaf rejects-no-server {
       type uint32;
       description
         "Number of authentication rejects due to failure to find server";
     }
     leaf rejects-no-create-handle {
       type uint32;
       description
         "Number of authentication rejects due to failure to create handle";
     }
     leaf rejects-no-queue-request {
       type uint32;
       description
         "Number of authentication rejects due to failure to queue request";
     }
     leaf rejects-invalid-credentials {
       type uint32;
       description
         "Number of authentication rejects due to invalid credentials";
     }
     leaf rejects-internal-failure {
       type uint32;
       description
         "Number of authentication rejects due to internal failure";
     }
     leaf rejects-malformed-request {
       type uint32;
       description
         "Number of authentication rejects due to malformed request";
     }
     leaf rejects-license-unavailable {
       type uint32;
       description
         "Number of authentication rejects due to license unavailable";
     }
     leaf rejects-redirect-requested {
       type uint32;
       description
         "Number of authentication rejects due to redirect requested";
     }
     leaf local-failures {
       type uint32;
       description
         "Number of local authentication failures";
     }
     leaf ldap-failures {
       type uint32;
       description
         "Number of LDAP lookup failures";
     }
     leaf accounting-request-failures {
       type uint32;
       description
         "Number of accounting requests failed to be sent out";
     }
     leaf accounting-request-success {
       type uint32;
       description
         "Number of accounting requests sent out sucessfully";
     }
     leaf timeouts {
       type uint32;
       description
         "Number of requests timed out";
     }
     leaf accounting-response-failures {
       type uint32;
       description
         "Number of accounting response failures";
     }
     leaf accounting-response-success {
       type uint32;
       description
         "Number of successful accounting responses";
     }
     leaf acct-unknown-responses {
       type uint32;
       description
         "Number of unknown accounting responses received";
     }
     leaf acct-requests-pending {
       type uint32;
       description
         "Number of pending account requests sent";
     }
     leaf acct-malformed-responses {
       type uint32;
       description
         "Number of malformed accounting responses received";
     }
     leaf acct-retransmissions {
       type uint32;
       description
         "Number of accounting retransmissions";
     }
     leaf acct-bad-authenticators {
       type uint32;
       description
         "Number of bad accounting authenticators";
     }
     leaf acct-packets-dropped {
       type uint32;
       description
         "Number of accounting packets dropped because not supported for 
         config";
     }
     leaf acct-acct-on-requests {
       type uint32;
       description
         "Number of account on requests sent";
     }
     leaf acct-start-requests {
       type uint32;
       description
         "Number of accounting start requests sent";
     }
     leaf acct-interim-requests {
       type uint32;
       description
         "Number of accounting interim requests sent";
     }
     leaf acct-stop-requests {
       type uint32;
       description
         "Number of accounting stop requests sent";
     }
     leaf acct-rollover-requests {
       type uint32;
       description
         "Number of accounting requests that rollover to another server due 
         to timeout/maxout";
     }
     leaf acct-acct-on-responses {
       type uint32;
       description
         "Number of accounting on responses received";
     }
     leaf acct-start-responses {
       type uint32;
       description
         "Number of accounting start responses received";
     }
     leaf acct-interim-responses {
       type uint32;
       description
         "Number of accounting interim responses received";
     }
     leaf acct-stop-responses {
       type uint32;
       description
         "Number of accounting stop responses received";
     }
     leaf multistack-suppressions {
       type uint32;
       description
         "Number of multistack requests suppressed";
     }
     leaf challenges {
       type uint32;
       description
         "Number of authentication challenges";
     }
     leaf processed-ok {
       type uint32;
       description
         "Number of requests successfully processed";
     }
     leaf processed-initial {
       type uint32;
       description
         "Number of requests initially processed successfully";
     }
     leaf processing-error {
       type uint32;
       description
         "Number of requests unsuccessfully processed";
     }
     leaf silent-drops {
       type uint32;
       description
         "Number of requests silently dropped";
     }
     leaf internal-errors {
       type uint32;
       description
         "Number of internal errors";
     }
     leaf aborts {
       type uint32;
       description
         "Number of abort requests";
     }
     leaf interim-updates-rcvd {
       type uint32;
       description
         "Number of interim updates received from libstats";
     }
     leaf interim-updates-sent {
       type uint32;
       description
         "Number of interim updates sent to radius";
     }
     leaf interim-updates-error-rcvd {
       type uint32;
       description
         "Number of interim error callbacks received";
     }
     leaf requested-final-stats {
       type uint32;
       description
         "Number of final stats requested from libstats";
     }
     leaf final-stats-retry-count {
       type uint32;
       description
         "Number of final stats retried";
     }
     leaf final-stats-rcvd {
       type uint32;
       description
         "Number of final stats updates received";
     }
     leaf final-stats-error-rcvd {
       type uint32;
       description
         "Number of final stats errors received";
     }
     leaf final-stats-sent {
       type uint32;
       description
         "Number of final stats sent to radius";
     }
     leaf time-only-info-sent {
       type uint32;
       description
         "Number of time info only stops sent";
     }
     leaf stats-timer-fired {
       type uint32;
       description
         "Number of times the accounting stats timer fired";
     }
     leaf libstats-interim-egress-subs {
       type uint32;
       description
         "Interim egress subs";
     }
     leaf libstats-interim-ingress-subs {
       type uint32;
       description
         "Interim ingress subs";
     }
     leaf libstats-interim-egress-general-error {
       type uint32;
       description
         "Interim egress general error";
     }
     leaf libstats-interim-ingress-general-error {
       type uint32;
       description
         "Interim ingress general error";
     }
     leaf libstats-interim-egress-kernel-error {
       type uint32;
       description
         "Interim egress kernel error";
     }
     leaf libstats-interim-ingress-kernel-error {
       type uint32;
       description
         "Interim ingress kernel error";
     }
     leaf libstats-interim-egress-memory-error {
       type uint32;
       description
         "Interim egress memory error";
     }
     leaf libstats-interim-ingress-memory-error {
       type uint32;
       description
         "Interim ingress memory error";
     }
     leaf libstats-interim-egress-ipc-error {
       type uint32;
       description
         "Interim egress IPC error";
     }
     leaf libstats-interim-ingress-ipc-error {
       type uint32;
       description
         "Interim ingress IPC error";
     }
     leaf libstats-interim-egress-validation-error {
       type uint32;
       description
         "Interim egress validation error";
     }
     leaf libstats-interim-ingress-validation-error {
       type uint32;
       description
         "Interim ingress validation error";
     }
     leaf libstats-interim-egress-db-lookup-error {
       type uint32;
       description
         "Interim egress db lookup error";
     }
     leaf libstats-interim-ingress-db-lookup-error {
       type uint32;
       description
         "Interim ingress db lookup error";
     }
     leaf libstats-final-egress-subs {
       type uint32;
       description
         "Final egress subs";
     }
     leaf libstats-final-ingress-subs {
       type uint32;
       description
         "Final ingress subs";
     }
     leaf libstats-final-egress-general-error {
       type uint32;
       description
         "Final egress general error";
     }
     leaf libstats-final-ingress-general-error {
       type uint32;
       description
         "Final ingress general error";
     }
     leaf libstats-final-egress-kernel-error {
       type uint32;
       description
         "Final egress kernel error";
     }
     leaf libstats-final-ingress-kernel-error {
       type uint32;
       description
         "Final ingress kernel error";
     }
     leaf libstats-final-egress-memory-error {
       type uint32;
       description
         "Final egress memory error";
     }
     leaf libstats-final-ingress-memory-error {
       type uint32;
       description
         "Final ingress memory error";
     }
     leaf libstats-final-egress-ipc-error {
       type uint32;
       description
         "Final egress IPC error";
     }
     leaf libstats-final-ingress-ipc-error {
       type uint32;
       description
         "Final ingress IPC error";
     }
     leaf libstats-final-egress-validation-error {
       type uint32;
       description
         "Final egress validation error";
     }
     leaf libstats-final-ingress-validation-error {
       type uint32;
       description
         "Final ingress validation error";
     }
     leaf libstats-final-egress-db-lookup-error {
       type uint32;
       description
         "Final egress DB lookup error";
     }
     leaf libstats-final-ingress-db-lookup-error {
       type uint32;
       description
         "Final ingress DB lookup error";
     }
     leaf libstats-all-egress-msg-types {
       type uint32;
       description
         "All egress message types";
     }
     leaf libstats-all-ingress-msg-types {
       type uint32;
       description
         "All ingress message types";
     }
     leaf libstats-all-egress-general-error {
       type uint32;
       description
         "All egress general error";
     }
     leaf libstats-all-ingress-general-error {
       type uint32;
       description
         "All ingress general error";
     }
     leaf libstats-all-egress-kernel-error {
       type uint32;
       description
         "All egress kernel error";
     }
     leaf libstats-all-ingress-kernel-error {
       type uint32;
       description
         "All ingress kernel error";
     }
     leaf libstats-all-egress-memory-error {
       type uint32;
       description
         "All egress memory error";
     }
     leaf libstats-all-ingress-memory-error {
       type uint32;
       description
         "All ingress memory error";
     }
     leaf libstats-all-egress-ipc-error {
       type uint32;
       description
         "All egress IPC error";
     }
     leaf libstats-all-ingress-ipc-error {
       type uint32;
       description
         "All ingress IPC error";
     }
     leaf libstats-all-egress-validation-error {
       type uint32;
       description
         "All egress validation error";
     }
     leaf libstats-all-ingress-validation-error {
       type uint32;
       description
         "All ingress validation error";
     }
     leaf libstats-all-egress-db-lookup-error {
       type uint32;
       description
         "All egress DB lookup error";
     }
     leaf libstats-all-ingress-db-lookup-error {
       type uint32;
       description
         "All ingress DB lookup error";
     }
     leaf pending-acct-stops {
       type uint32;
       description
         "Number of requests received";
     }
     leaf pending-sub-acct-stops {
       type uint32;
       description
         "Number of subscriber requests in backup queue";
     }
     leaf pending-serv-acct-stops {
       type uint32;
       description
         "Number of service requests in backup queue";
     }
     leaf pending-total-acct-stops {
       type uint32;
       description
         "Number of total requests in backup queue";
     }
     leaf acct-backup-record-creation-requests {
       type uint32;
       description
         "Number of backup records creation requests sent to backup 
         accounting module";
     }
     leaf acct-backup-radius-retransmissions {
       type uint32;
       description
         "Number of radius retries sent in backup context";
     }
     leaf acct-backup-request-timeouts {
       type uint32;
       description
         "Number of backup requests that timed out";
     }
     leaf acct-backup-request-failures {
       type uint32;
       description
         "Number of backup requests that encountered an error";
     }
     leaf acct-backup-request-success {
       type uint32;
       description
         "Number of backup requests that were success";
     }
     leaf acct-backup-request-replay-success {
       type uint32;
       description
         "Number of backup requests that were reconstructed successfully 
         during replay";
     }
     leaf acct-backup-radius-pending-request {
       type uint32;
       description
         "Number of Backup requests sent to radius server but yet to receive
         response or error";
     }
     leaf acct-backup-in-flight-requests {
       type uint32;
       description
         "Number of Backup requests sent but yet to receive response or 
         error";
     }
     leaf acct-backup-response-success {
       type uint32;
       description
         "Number of backup responses received and processed by backup module";
     }
     leaf acct-backup-malformed-responses {
       type uint32;
       description
         "Number of requests sent to backup accounting module";
     }
     leaf acct-backup-bad-authenticators {
       type uint32;
       description
         "Number of bad accounting authenticators in backup context";
     }
     leaf acct-backup-packets-dropped {
       type uint32;
       description
         "Number of backup responses dropped due to an issue not covered 
         above";
     }
     leaf acct-backup-rollover-requests {
       type uint32;
       description
         "Number of backup requests that rollover to another server due to 
         timeout/maxout";
     }
     leaf acct-backup-unknown-responses {
       type uint32;
       description
         "Number of backup requests that rollover to another server due to 
         timeout/maxout";
     }
     leaf acct-backup-radius-requests {
       type uint32;
       description
         "Number of backup requests that rollover to another server due to 
         timeout/maxout";
     }
     leaf acct-backup-radius-responses {
       type uint32;
       description
         "Number of backup requests that rollover to another server due to 
         timeout/maxout";
     }
     leaf acct-backup-radius-timeouts {
       type uint32;
       description
         "Number of backup requests that rollover to another server due to 
         timeout/maxout";
     }
     container aaa-module-authentication-statistics {
       leaf requests {
         type uint32;
         description
           "Number of requests received";
       }
       leaf multistack-requests {
         type uint32;
         description
           "Number of multistack requests received";
       }
       leaf accepts {
         type uint32;
         description
           "Number of authentication accepts";
       }
       leaf rejects {
         type uint32;
         description
           "Number of authentication rejects";
       }
       leaf challenges {
         type uint32;
         description
           "Number of authentication challenges";
       }
       leaf timeouts {
         type uint32;
         description
           "Number of requests timed out";
       }
       leaf radius-failures {
         type uint32;
         description
           "Number of RADIUS authentication failures";
       }
       leaf local-failures {
         type uint32;
         description
           "Number of local authentication failures";
       }
       leaf ldap-failures {
         type uint32;
         description
           "Number of LDAP lookup failures";
       }
       leaf rejects-queue-request-deleted {
         type uint32;
         description
           "Number of authentication rejects due to queue request deleted";
       }
       leaf rejects-malformed-reply {
         type uint32;
         description
           "Number of authentication rejects due to malformed reply";
       }
       leaf rejects-no-server-configured {
         type uint32;
         description
           "Number of authentication rejects due to no servers configured";
       }
       leaf rejects-access-profile-config-unavailable {
         type uint32;
         description
           "Number of authentication rejects due to unavailable access 
           profile configuration";
       }
       leaf rejects-no-client-record {
         type uint32;
         description
           "Number of authentication rejects due to failure to create client
           record";
       }
       leaf rejects-no-client-request {
         type uint32;
         description
           "Number of authentication rejects due to failure to create client
           request";
       }
       leaf rejects-no-build-auth-request {
         type uint32;
         description
           "Number of authentication rejects due to failure to build 
           authentication request";
       }
       leaf rejects-no-server {
         type uint32;
         description
           "Number of authentication rejects due to failure to find server";
       }
       leaf rejects-no-create-handle {
         type uint32;
         description
           "Number of authentication rejects due to failure to create handle";
       }
       leaf rejects-no-queue-request {
         type uint32;
         description
           "Number of authentication rejects due to failure to queue request";
       }
       leaf rejects-invalid-credentials {
         type uint32;
         description
           "Number of authentication rejects due to invalid credentials";
       }
       leaf rejects-internal-failure {
         type uint32;
         description
           "Number of authentication rejects due to internal failure";
       }
       leaf rejects-malformed-request {
         type uint32;
         description
           "Number of authentication rejects due to malformed request";
       }
       leaf rejects-license-unavailable {
         type uint32;
         description
           "Number of authentication rejects due to license unavailable";
       }
       leaf rejects-redirect-requested {
         type uint32;
         description
           "Number of authentication rejects due to redirect requested";
       }
     }
     container aaa-module-pending-accounting-stop-statistics {
       leaf pending-acct-stops {
         type uint32;
         description
           "Number of requests received";
       }
     }
     container aaa-module-preauthentication-statistics {
       leaf requests {
         type uint32;
         description
           "Number of requests received";
       }
       leaf multistack-requests {
         type uint32;
         description
           "Number of multistack requests received";
       }
       leaf accepts {
         type uint32;
         description
           "Number of authentication accepts";
       }
       leaf rejects {
         type uint32;
         description
           "Number of authentication rejects";
       }
       leaf challenges {
         type uint32;
         description
           "Number of authentication challenges";
       }
       leaf timeouts {
         type uint32;
         description
           "Number of requests timed out";
       }
     }
     list aaa-module-accounting-statistics {
       leaf requests {
         type uint32;
         description
           "Number of requests received";
       }
       leaf accounting-request-failures {
         type uint32;
         description
           "Number of accounting requests failed to be sent out";
       }
       leaf accounting-request-success {
         type uint32;
         description
           "Number of accounting requests sent out sucessfully";
       }
       leaf timeouts {
         type uint32;
         description
           "Number of requests timed out";
       }
       leaf accounting-response-failures {
         type uint32;
         description
           "Number of accounting response failures";
       }
       leaf accounting-response-success {
         type uint32;
         description
           "Number of successful accounting responses";
       }
       leaf acct-rollover-requests {
         type uint32;
         description
           "Number of accounting requests that rollover to another server 
           due to timeout/maxout";
       }
       leaf acct-unknown-responses {
         type uint32;
         description
           "Number of unknown accounting responses received";
       }
       leaf acct-requests-pending {
         type uint32;
         description
           "Number of pending account requests sent";
       }
       leaf acct-malformed-responses {
         type uint32;
         description
           "Number of malformed accounting responses received";
       }
       leaf acct-retransmissions {
         type uint32;
         description
           "Number of accounting retransmissions";
       }
       leaf acct-bad-authenticators {
         type uint32;
         description
           "Number of bad accounting authenticators";
       }
       leaf acct-packets-dropped {
         type uint32;
         description
           "Number of accounting packets dropped because not supported for 
           config";
       }
       leaf acct-acct-on-requests {
         type uint32;
         description
           "Number of account on requests sent";
       }
       leaf acct-start-requests {
         type uint32;
         description
           "Number of accounting start requests sent";
       }
       leaf acct-interim-requests {
         type uint32;
         description
           "Number of accounting interim requests sent";
       }
       leaf acct-stop-requests {
         type uint32;
         description
           "Number of accounting stop requests sent";
       }
       leaf acct-acct-on-responses {
         type uint32;
         description
           "Number of accounting on responses received";
       }
       leaf acct-start-responses {
         type uint32;
         description
           "Number of accounting start responses received";
       }
       leaf acct-interim-responses {
         type uint32;
         description
           "Number of accounting interim responses received";
       }
       leaf acct-stop-responses {
         type uint32;
         description
           "Number of accounting stop responses received";
       }
       leaf acct-backup-record-creation-requests {
         type uint32;
         description
           "Number of backup records creation requests sent to backup 
           accounting module";
       }
       leaf acct-backup-radius-retransmissions {
         type uint32;
         description
           "Number of radius retries sent in backup context";
       }
       leaf acct-backup-request-timeouts {
         type uint32;
         description
           "Number of backup requests that timed out";
       }
       leaf acct-backup-request-failures {
         type uint32;
         description
           "Number of backup requests that encountered an error";
       }
       leaf acct-backup-request-success {
         type uint32;
         description
           "Number of backup requests that were success";
       }
       leaf acct-backup-request-replay-success {
         type uint32;
         description
           "Number of backup requests that were reconstructed successfully 
           during replay";
       }
       leaf acct-backup-radius-pending-request {
         type uint32;
         description
           "Number of Backup requests sent to radius server but yet to 
           receive response or error";
       }
       leaf acct-backup-in-flight-requests {
         type uint32;
         description
           "Number of Backup requests sent but yet to receive response or 
           error";
       }
       leaf acct-backup-response-success {
         type uint32;
         description
           "Number of backup responses received and processed by backup 
           module";
       }
       leaf acct-backup-malformed-responses {
         type uint32;
         description
           "Number of requests sent to backup accounting module";
       }
       leaf acct-backup-bad-authenticators {
         type uint32;
         description
           "Number of bad accounting authenticators in backup context";
       }
       leaf acct-backup-packets-dropped {
         type uint32;
         description
           "Number of backup responses dropped due to an issue not covered 
           above";
       }
       leaf acct-backup-rollover-requests {
         type uint32;
         description
           "Number of backup requests that rollover to another server due to
           timeout/maxout";
       }
       leaf acct-backup-unknown-responses {
         type uint32;
         description
           "Number of backup requests that rollover to another server due to
           timeout/maxout";
       }
       leaf acct-backup-radius-requests {
         type uint32;
         description
           "Number of backup requests that rollover to another server due to
           timeout/maxout";
       }
       leaf acct-backup-radius-responses {
         type uint32;
         description
           "Number of backup requests that rollover to another server due to
           timeout/maxout";
       }
       leaf acct-backup-radius-timeouts {
         type uint32;
         description
           "Number of backup requests that rollover to another server due to
           timeout/maxout";
       }
     }
     container aaa-module-dynamic-requests-statistics {
       leaf requests {
         type uint32;
         description
           "Number of requests received";
       }
       leaf processed-ok {
         type uint32;
         description
           "Number of requests successfully processed";
       }
       leaf processed-initial {
         type uint32;
         description
           "Number of requests initially processed successfully";
       }
       leaf processing-error {
         type uint32;
         description
           "Number of requests unsuccessfully processed";
       }
       leaf silent-drops {
         type uint32;
         description
           "Number of requests silently dropped";
       }
       container aaa-module-dynamic-requests-bulkcoa-statistics {
         leaf bulkcoa-received {
           type uint32;
           description
             "Number of bulk-CoA different transactions received";
         }
         leaf bulkcoa-success {
           type uint32;
           description
             "Number of bulk-CoA transactions successfully committed";
         }
         leaf bulkcoa-timeout {
           type uint32;
           description
             "Number of bulk-CoA transactions timedout";
         }
         leaf bulkcoa-transaction-mismatch {
           type uint32;
           description
             "Number of bulk-CoA transaction-id mismatch";
         }
         leaf bulkcoa-in-progress {
           type uint32;
           description
             "Number of bulk-CoA transactions with processing already in 
             progress";
         }
         leaf bulkcoa-no-services {
           type uint32;
           description
             "Number of bulk-CoA transactions with no services in Bulk-CoA";
         }
         leaf bulkcoa-service-not-found {
           type uint32;
           description
             "Number of bulk-CoA transactions with service not found to 
             deactivate";
         }
         leaf bulkcoa-service-active {
           type uint32;
           description
             "Number of bulk-CoA transactions with service already active";
         }
         leaf bulkcoa-execution-failure {
           type uint32;
           description
             "Number of bulk-CoA transactions with execution failure";
         }
         leaf bulkcoa-logout-in-progress {
           type uint32;
           description
             "Number of bulk-CoA transactions with logout in progress";
         }
         leaf bulkcoa-max-services {
           type uint32;
           description
             "Number of bulk-CoA transactions with max services exceeded";
         }
         leaf bulkcoa-max-requests {
           type uint32;
           description
             "Number of bulk-CoA transactions with max requests exceeded";
         }
         leaf bulkcoa-max-concurrent-coas {
           type uint32;
           description
             "Max Number of bulk-CoA transactions concurrently being 
             processed";
         }
         leaf bulkcoa-extensible-services-errors {
           type uint32;
           description
             "Number of bulk-CoA transactions with extensible services 
             errors";
         }
       }
     }
     container aaa-module-volume-accounting-statistics {
       leaf interim-updates-rcvd {
         type uint32;
         description
           "Number of interim updates received from libstats";
       }
       leaf interim-updates-sent {
         type uint32;
         description
           "Number of interim updates sent to radius";
       }
       leaf interim-updates-error-rcvd {
         type uint32;
         description
           "Number of interim error callbacks received";
       }
       leaf requested-final-stats {
         type uint32;
         description
           "Number of final stats requested from libstats";
       }
       leaf final-stats-retry-count {
         type uint32;
         description
           "Number of final stats retried";
       }
       leaf final-stats-rcvd {
         type uint32;
         description
           "Number of final stats updates received";
       }
       leaf final-stats-error-rcvd {
         type uint32;
         description
           "Number of final stats errors received";
       }
       leaf final-stats-sent {
         type uint32;
         description
           "Number of final stats sent to radius";
       }
       leaf time-only-info-sent {
         type uint32;
         description
           "Number of time info only stops sent";
       }
       leaf stats-timer-fired {
         type uint32;
         description
           "Number of times the accounting stats timer fired";
       }
       leaf libstats-interim-egress-subs {
         type uint32;
         description
           "Interim egress subs";
       }
       leaf libstats-interim-ingress-subs {
         type uint32;
         description
           "Interim ingress subs";
       }
       leaf libstats-interim-egress-general-error {
         type uint32;
         description
           "Interim egress general error";
       }
       leaf libstats-interim-ingress-general-error {
         type uint32;
         description
           "Interim ingress general error";
       }
       leaf libstats-interim-egress-kernel-error {
         type uint32;
         description
           "Interim egress kernel error";
       }
       leaf libstats-interim-ingress-kernel-error {
         type uint32;
         description
           "Interim ingress kernel error";
       }
       leaf libstats-interim-egress-memory-error {
         type uint32;
         description
           "Interim egress memory error";
       }
       leaf libstats-interim-ingress-memory-error {
         type uint32;
         description
           "Interim ingress memory error";
       }
       leaf libstats-interim-egress-ipc-error {
         type uint32;
         description
           "Interim egress IPC error";
       }
       leaf libstats-interim-ingress-ipc-error {
         type uint32;
         description
           "Interim ingress IPC error";
       }
       leaf libstats-interim-egress-validation-error {
         type uint32;
         description
           "Interim egress validation error";
       }
       leaf libstats-interim-ingress-validation-error {
         type uint32;
         description
           "Interim ingress validation error";
       }
       leaf libstats-interim-egress-db-lookup-error {
         type uint32;
         description
           "Interim egress db lookup error";
       }
       leaf libstats-interim-ingress-db-lookup-error {
         type uint32;
         description
           "Interim ingress db lookup error";
       }
       leaf libstats-final-egress-subs {
         type uint32;
         description
           "Final egress subs";
       }
       leaf libstats-final-ingress-subs {
         type uint32;
         description
           "Final ingress subs";
       }
       leaf libstats-final-egress-general-error {
         type uint32;
         description
           "Final egress general error";
       }
       leaf libstats-final-ingress-general-error {
         type uint32;
         description
           "Final ingress general error";
       }
       leaf libstats-final-egress-kernel-error {
         type uint32;
         description
           "Final egress kernel error";
       }
       leaf libstats-final-ingress-kernel-error {
         type uint32;
         description
           "Final ingress kernel error";
       }
       leaf libstats-final-egress-memory-error {
         type uint32;
         description
           "Final egress memory error";
       }
       leaf libstats-final-ingress-memory-error {
         type uint32;
         description
           "Final ingress memory error";
       }
       leaf libstats-final-egress-ipc-error {
         type uint32;
         description
           "Final egress IPC error";
       }
       leaf libstats-final-ingress-ipc-error {
         type uint32;
         description
           "Final ingress IPC error";
       }
       leaf libstats-final-egress-validation-error {
         type uint32;
         description
           "Final egress validation error";
       }
       leaf libstats-final-ingress-validation-error {
         type uint32;
         description
           "Final ingress validation error";
       }
       leaf libstats-final-egress-db-lookup-error {
         type uint32;
         description
           "Final egress DB lookup error";
       }
       leaf libstats-final-ingress-db-lookup-error {
         type uint32;
         description
           "Final ingress DB lookup error";
       }
       leaf libstats-all-egress-msg-types {
         type uint32;
         description
           "All egress message types";
       }
       leaf libstats-all-ingress-msg-types {
         type uint32;
         description
           "All ingress message types";
       }
       leaf libstats-all-egress-general-error {
         type uint32;
         description
           "All egress general error";
       }
       leaf libstats-all-ingress-general-error {
         type uint32;
         description
           "All ingress general error";
       }
       leaf libstats-all-egress-kernel-error {
         type uint32;
         description
           "All egress kernel error";
       }
       leaf libstats-all-ingress-kernel-error {
         type uint32;
         description
           "All ingress kernel error";
       }
       leaf libstats-all-egress-memory-error {
         type uint32;
         description
           "All egress memory error";
       }
       leaf libstats-all-ingress-memory-error {
         type uint32;
         description
           "All ingress memory error";
       }
       leaf libstats-all-egress-ipc-error {
         type uint32;
         description
           "All egress IPC error";
       }
       leaf libstats-all-ingress-ipc-error {
         type uint32;
         description
           "All ingress IPC error";
       }
       leaf libstats-all-egress-validation-error {
         type uint32;
         description
           "All egress validation error";
       }
       leaf libstats-all-ingress-validation-error {
         type uint32;
         description
           "All ingress validation error";
       }
       leaf libstats-all-egress-db-lookup-error {
         type uint32;
         description
           "All egress DB lookup error";
       }
       leaf libstats-all-ingress-db-lookup-error {
         type uint32;
         description
           "All ingress DB lookup error";
       }
     }
     container aaa-module-re-authentication-statistics {
       leaf requests {
         type uint32;
         description
           "Number of requests received";
       }
       leaf accepts {
         type uint32;
         description
           "Number of authentication accepts";
       }
       leaf rejects {
         type uint32;
         description
           "Number of authentication rejects";
       }
       leaf challenges {
         type uint32;
         description
           "Number of authentication challenges";
       }
       leaf timeouts {
         type uint32;
         description
           "Number of requests timed out";
       }
     }
     container aaa-module-address-assignment-pool-statistics {
       leaf pool-name {
         type string;
         description
           "Pool name";
       }
       leaf link-name {
         type string;
         description
           "Link name";
       }
       leaf out-of-memory {
         type uint64;
         description
           "Number of times we have hit an out of memory condition";
       }
       leaf out-of-addresses {
         type uint64;
         description
           "Number of times we have hit an out of address condition";
       }
       leaf total-addresses {
         type uint64;
         description
           "Number of addresses in pool";
       }
       leaf used-addresses {
         type uint64;
         description
           "Number of addresses in use";
       }
       leaf excluded-addresses {
         type uint64;
         description
           "Number of addresses excluded";
       }
       leaf pool-usage {
         type int32;
         description
           "Percentage of addesses in use";
       }
       leaf pool-drain-configured {
         type string;
         description
           "Pool drain configured";
       }
     }
     container aaa-module-napt-pool-statistics {
       leaf pool-name {
         type string;
         description
           "Pool name";
       }
       leaf out-of-memory {
         type uint64;
         description
           "Number of times we have hit an out of memory condition";
       }
       leaf out-of-addresses {
         type uint64;
         description
           "Number of times we have hit an out of address condition";
       }
       leaf total-addresses {
         type uint64;
         description
           "Number of addresses in pool";
       }
       leaf used-addresses {
         type uint64;
         description
           "Number of addresses in use";
       }
       leaf pool-usage {
         type int32;
         description
           "Percentage of addesses in use";
       }
     }
     container aaa-module-address-assignment-client-statistics {
       leaf client-name {
         type string;
         description
           "Client name";
       }
       leaf out-of-memory {
         type uint64;
         description
           "Number of times we have hit an out of memory condition";
       }
       leaf no-matches {
         type int32;
         description
           "Number of times we have not had an address match";
       }
     }
     container aaa-module-subscriber-statistics {
       leaf total-number-of-subscribers {
         type int32;
         description
           "Total number of subscribers";
       }
     }
     container aaa-module-radius-statistics {
       leaf radius-statistics-error {
         type string;
         description
           "Error message to display related to RADIUS server statistics";
       }
       list radius-server {
         description
           "RADIUS servers";
         leaf server-address {
           type jt:ipaddr;
           description
             "RADIUS server address";
         }
         leaf profile {
           type string;
           description
             "Profile that includes this RADIUS server";
         }
         leaf max-outstanding {
           type int32;
           description
             "Maximum number of outstanding RADIUS requests for this server";
         }
         leaf current-outstanding {
           type int32;
           description
             "Current number of outstanding RADIUS requests for this server";
         }
         leaf peak-outstanding {
           type int32;
           description
             "Highest number of outstanding RADIUS requests for this server";
         }
         leaf fail-outstanding {
           type int32;
           description
             "Number of max-outstanding-exceeded failures for this server";
         }
       }
     }
     container aaa-module-radius-queue-statistics {
       leaf profile {
         type string;
         description
           "Profile that includes this RADIUS server";
       }
       leaf current-size {
         type int32;
         description
           "Current number of entries on this RADIUS queue";
       }
       leaf peak {
         type int32;
         description
           "Peak entries on this RADIUS queue";
       }
       leaf max-size {
         type int32;
         description
           "Maximum number of entries on this RADIUS queue";
       }
     }
     container aaa-module-reconciliation-statistics {
       leaf client-id {
         type string;
         description
           "Client id";
       }
       leaf reconciliation-state {
         type string;
         description
           "Reconciliation state";
       }
       leaf reconciliation-request-count {
         type uint32;
         description
           "Reconciliation request received";
       }
       leaf reconciliation-response-success-count {
         type uint32;
         description
           "Reconciliation response success";
       }
       leaf reconciliation-response-failure-count {
         type uint32;
         description
           "Reconciliation response failure";
       }
       leaf reconciliation-cleanup-count {
         type uint32;
         description
           "Reconciliation cleanup";
       }
       leaf reconciliation-pending-cleanup {
         type string;
         description
           "Reconciliation pending cleanup";
       }
       leaf reconciliation-request-dropped-count {
         type uint32;
         description
           "Reconciliation requests dropped";
       }
       leaf logins-during-reconciliation {
         type uint32;
         description
           "Subscriber logins during reconciliation";
       }
       leaf reconciliation-ready-sent-time {
         type string;
         description
           "Reconciliation Ready sent timestamp";
       }
       leaf reconciliation-end-received-time {
         type string;
         description
           "Reconciliation End received timestamp";
       }
       leaf last-reconciliation-duration {
         type string;
         description
           "Last reconciliation duration";
       }
       leaf logouts-during-reconciliation {
         type uint32;
         description
           "Subscriber logouts during reconciliation";
       }
       container reconciliation-state-table {
         container reconciliation-state-table-entry {
           leaf reconciliation-state {
             type string;
             description
               "Reconciliation state";
           }
           leaf logins-during-reconciliation {
             type uint32;
             description
               "Subscriber logins during reconciliation";
           }
           leaf logouts-during-reconciliation {
             type uint32;
             description
               "Subscriber logouts during reconciliation";
           }
         }
       }
     }
   }
   grouping aaa-accounting-status-block {
     container aaa-accounting-status-list {
       leaf profile {
         type string;
         description
           "Profile that includes this RADIUS server";
       }
       leaf logical-system {
         type string;
         description
           "Logical system this RADIUS server is part of";
       }
       leaf routing-instance {
         type string;
         description
           "Routing instance this RADIUS server is part of";
       }
       leaf acct-on-response {
         type string;
         description
           "ACCT-ON Response from the RADIUS server";
       }
     }
   }
   grouping aaa-module-radius-servers-information-block {
     list aaa-module-profile-radius-servers {
       leaf profile-name {
         type string;
         description
           "Profile-name using which the user is being authenticated";
       }
       leaf server-address {
         type jt:ipaddr;
         description
           "RADIUS server address";
       }
       leaf authentication-port {
         type uint32;
         description
           "RADIUS authentication port";
       }
       leaf preauthentication-port {
         type uint32;
         description
           "RADIUS preauthentication port";
       }
       leaf accounting-port {
         type uint32;
         description
           "RADIUS accounting port";
       }
       leaf accounting-retry {
         type uint32;
         description
           "RADIUS accounting retry";
       }
       leaf accounting-timeout {
         type uint32;
         description
           "RADIUS accounting accounting timeout";
       }
       leaf available-status {
         type string;
         description
           "RADIUS server status";
       }
       leaf last-rtt {
         type uint32;
         description
           "Last Round Trip Time";
       }
       leaf authentication-requests {
         type uint32;
         description
           "Authentication requests";
       }
       leaf authentication-rollover-requests {
         type uint32;
         description
           "Authentication rollover requests";
       }
       leaf authentication-retransmissions {
         type uint32;
         description
           "Authentication retransmissions";
       }
       leaf accepts {
         type uint32;
         description
           "Number of authentication accepts";
       }
       leaf rejects {
         type uint32;
         description
           "Number of authentication rejects";
       }
       leaf challenges {
         type uint32;
         description
           "Number of authentication challenges";
       }
       leaf authentication-malformed-responses {
         type uint32;
         description
           "Authentication malformed responses";
       }
       leaf authentication-bad-authenticators {
         type uint32;
         description
           "Authentication malformed responses";
       }
       leaf authentication-requests-pending {
         type uint32;
         description
           "Authentication requests pending";
       }
       leaf authentication-timeouts {
         type uint32;
         description
           "Authentication request timeouts";
       }
       leaf authentication-unknown-responses {
         type uint32;
         description
           "Authentication unknown responses";
       }
       leaf authentication-packets-dropped {
         type uint32;
         description
           "Authentication packets dropped";
       }
       leaf preauthentication-requests {
         type uint32;
         description
           "Preauthentication requests";
       }
       leaf preauthentication-rollover-requests {
         type uint32;
         description
           "Preauthentication rollover requests";
       }
       leaf preauthentication-retransmissions {
         type uint32;
         description
           "Preauthentication retransmissions";
       }
       leaf preauthentication-accepts {
         type uint32;
         description
           "Preauthentication accepts";
       }
       leaf preauthentication-rejects {
         type uint32;
         description
           "Preauthentication rejects";
       }
       leaf preauthentication-challenges {
         type uint32;
         description
           "Preauthentication challenges";
       }
       leaf preauthentication-malformed-responses {
         type uint32;
         description
           "Preauthentication malformed responses";
       }
       leaf preauthentication-bad-authenticators {
         type uint32;
         description
           "Preauthentication bad authenticators";
       }
       leaf preauthentication-requests-pending {
         type uint32;
         description
           "Preauthentication requests pending";
       }
       leaf preauthentication-timeouts {
         type uint32;
         description
           "Preauthentication request timeouts";
       }
       leaf preauthentication-unknown-responses {
         type uint32;
         description
           "Preauthentication unknown responses";
       }
       leaf preauthentication-packets-dropped {
         type uint32;
         description
           "Preauthentication packets dropped";
       }
       leaf accounting-start-requests {
         type uint32;
         description
           "Accounting start requests";
       }
       leaf accounting-interim-requests {
         type uint32;
         description
           "Accounting interim requests";
       }
       leaf accounting-stop-requests {
         type uint32;
         description
           "Accounting stop requests";
       }
       leaf accounting-reject-requests {
         type uint32;
         description
           "Accounting reject requests";
       }
       leaf accounting-rollover-requests {
         type uint32;
         description
           "Accounting rollover requests";
       }
       leaf accounting-retransmissions {
         type uint32;
         description
           "Accounting request retransmissions";
       }
       leaf accounting-start-response {
         type uint32;
         description
           "Accounting start responses";
       }
       leaf accounting-interim-response {
         type uint32;
         description
           "Accounting interim responses";
       }
       leaf accounting-stop-response {
         type uint32;
         description
           "Accounting stop responses";
       }
       leaf accounting-reject-response {
         type uint32;
         description
           "Accounting reject response";
       }
       leaf accounting-malformed-response {
         type uint32;
         description
           "Accounting malformed responses";
       }
       leaf accounting-bad-authenticators {
         type uint32;
         description
           "Accounting bad authenticators";
       }
       leaf accounting-requests-pending {
         type uint32;
         description
           "Accounting requests pending";
       }
       leaf accounting-timeouts {
         type uint32;
         description
           "Accounting request timeouts";
       }
       leaf accounting-unknown-responses {
         type uint32;
         description
           "Accounting unknown responses";
       }
       leaf accounting-packets-dropped {
         type uint32;
         description
           "Accounting packets dropped";
       }
       leaf dynamic-request-coa {
         type uint32;
         description
           "Dynamic request change of authorization";
       }
       leaf dynamic-request-disconnect {
         type uint32;
         description
           "Dynamic request disconnect";
       }
       leaf dynamic-request-unknown {
         type uint32;
         description
           "Dynamic request unknown";
       }
       leaf dynamic-request-malformed {
         type uint32;
         description
           "Dynamic request malformed";
       }
       leaf dynamic-request-bad-authenticators {
         type uint32;
         description
           "Dynamic request bad authenticators";
       }
       leaf dynamic-request-invalid-length {
         type uint32;
         description
           "Dynamic request invalid length";
       }
     }
     list aaa-module-radius-servers-statistics {
       leaf radius-statistics-error {
         type string;
         description
           "Error message to display related to RADIUS server statistics";
       }
       leaf server-address {
         type jt:ipaddr;
         description
           "RADIUS server address";
       }
       leaf last-rtt {
         type uint32;
         description
           "Last Round Trip Time";
       }
       leaf authentication-requests {
         type uint32;
         description
           "Authentication requests";
       }
       leaf authentication-rollover-requests {
         type uint32;
         description
           "Authentication rollover requests";
       }
       leaf authentication-retransmissions {
         type uint32;
         description
           "Authentication retransmissions";
       }
       leaf accepts {
         type uint32;
         description
           "Number of authentication accepts";
       }
       leaf rejects {
         type uint32;
         description
           "Number of authentication rejects";
       }
       leaf challenges {
         type uint32;
         description
           "Number of authentication challenges";
       }
       leaf authentication-malformed-responses {
         type uint32;
         description
           "Authentication malformed responses";
       }
       leaf authentication-bad-authenticators {
         type uint32;
         description
           "Authentication malformed responses";
       }
       leaf authentication-requests-pending {
         type uint32;
         description
           "Authentication requests pending";
       }
       leaf authentication-timeouts {
         type uint32;
         description
           "Authentication request timeouts";
       }
       leaf authentication-unknown-responses {
         type uint32;
         description
           "Authentication unknown responses";
       }
       leaf authentication-packets-dropped {
         type uint32;
         description
           "Authentication packets dropped";
       }
       leaf preauthentication-requests {
         type uint32;
         description
           "Preauthentication requests";
       }
       leaf preauthentication-rollover-requests {
         type uint32;
         description
           "Preauthentication rollover requests";
       }
       leaf preauthentication-retransmissions {
         type uint32;
         description
           "Preauthentication retransmissions";
       }
       leaf preauthentication-accepts {
         type uint32;
         description
           "Preauthentication accepts";
       }
       leaf preauthentication-rejects {
         type uint32;
         description
           "Preauthentication rejects";
       }
       leaf preauthentication-challenges {
         type uint32;
         description
           "Preauthentication challenges";
       }
       leaf preauthentication-malformed-responses {
         type uint32;
         description
           "Preauthentication malformed responses";
       }
       leaf preauthentication-bad-authenticators {
         type uint32;
         description
           "Preauthentication bad authenticators";
       }
       leaf preauthentication-requests-pending {
         type uint32;
         description
           "Preauthentication requests pending";
       }
       leaf preauthentication-timeouts {
         type uint32;
         description
           "Preauthentication request timeouts";
       }
       leaf preauthentication-unknown-responses {
         type uint32;
         description
           "Preauthentication unknown responses";
       }
       leaf preauthentication-packets-dropped {
         type uint32;
         description
           "Preauthentication packets dropped";
       }
       leaf accounting-start-requests {
         type uint32;
         description
           "Accounting start requests";
       }
       leaf accounting-interim-requests {
         type uint32;
         description
           "Accounting interim requests";
       }
       leaf accounting-stop-requests {
         type uint32;
         description
           "Accounting stop requests";
       }
       leaf accounting-reject-requests {
         type uint32;
         description
           "Accounting reject requests";
       }
       leaf accounting-rollover-requests {
         type uint32;
         description
           "Accounting rollover requests";
       }
       leaf accounting-retransmissions {
         type uint32;
         description
           "Accounting request retransmissions";
       }
       leaf accounting-start-response {
         type uint32;
         description
           "Accounting start responses";
       }
       leaf accounting-interim-response {
         type uint32;
         description
           "Accounting interim responses";
       }
       leaf accounting-stop-response {
         type uint32;
         description
           "Accounting stop responses";
       }
       leaf accounting-reject-response {
         type uint32;
         description
           "Accounting reject response";
       }
       leaf accounting-malformed-response {
         type uint32;
         description
           "Accounting malformed responses";
       }
       leaf accounting-bad-authenticators {
         type uint32;
         description
           "Accounting bad authenticators";
       }
       leaf accounting-requests-pending {
         type uint32;
         description
           "Accounting requests pending";
       }
       leaf accounting-timeouts {
         type uint32;
         description
           "Accounting request timeouts";
       }
       leaf accounting-unknown-responses {
         type uint32;
         description
           "Accounting unknown responses";
       }
       leaf accounting-packets-dropped {
         type uint32;
         description
           "Accounting packets dropped";
       }
       leaf dynamic-request-coa {
         type uint32;
         description
           "Dynamic request change of authorization";
       }
       leaf dynamic-request-disconnect {
         type uint32;
         description
           "Dynamic request disconnect";
       }
       leaf dynamic-request-unknown {
         type uint32;
         description
           "Dynamic request unknown";
       }
       leaf dynamic-request-malformed {
         type uint32;
         description
           "Dynamic request malformed";
       }
       leaf dynamic-request-bad-authenticators {
         type uint32;
         description
           "Dynamic request bad authenticators";
       }
       leaf dynamic-request-invalid-length {
         type uint32;
         description
           "Dynamic request invalid length";
       }
     }
   }
   grouping saml-assertion-cache-information-block {
     list assertion-cache-brief {
       leaf-list user-id {
         type string;
         description
           "Authenticated username";
       }
       leaf-list cache-validity {
         type string;
         description
           "Cache validity";
       }
     }
     list assertion-cache-detail {
       leaf-list user-id {
         type string;
         description
           "Authenticated username";
       }
       leaf-list cache-validity {
         type string;
         description
           "Cache validity";
       }
       container user-attribute {
         leaf-list attribute-name {
           type string;
           description
             "Attribute name";
         }
         leaf-list attribute-value {
           type string;
           description
             "Attribute value";
         }
       }
     }
   }
   grouping aaa-module-address-assignment-reserved-addresses-block {
     container address-assignment-reserved-address-table {
       container address-assignment-reserved-address-entry {
         leaf reservation-key {
           type string;
           description
             "The Key";
         }
         leaf delegated-prefix {
           type jt:ipaddr;
           description
             "Delegated Prefix";
         }
         leaf age-out-end {
           type string;
           description
             "Reservation End";
         }
       }
     }
     container address-assignment-reserved-ipv4-address-table {
       container address-assignment-reserved-ipv4-address-entry {
         leaf reservation-key {
           type string;
           description
             "The Key";
         }
         leaf ipv4-addr {
           type jt:ipaddr;
           description
             "IPv4 Address";
         }
         leaf age-out-end {
           type string;
           description
             "Reservation End";
         }
       }
     }
     container address-assignment-reserved-ipv6-address-table {
       container address-assignment-reserved-ipv6-address-entry {
         leaf reservation-key {
           type string;
           description
             "The Key";
         }
         leaf ipv6-addr {
           type jt:ipaddr;
           description
             "IPv6 Address";
         }
         leaf age-out-end {
           type string;
           description
             "Reservation End";
         }
       }
     }
     container address-assignment-reserved-ndra-address-table {
       container address-assignment-reserved-ndra-address-entry {
         leaf reservation-key {
           type string;
           description
             "The Key";
         }
         leaf ndra-prefix {
           type jt:ipaddr;
           description
             "NDRA Prefix";
         }
         leaf age-out-end {
           type string;
           description
             "Reservation End";
         }
       }
     }
   }
   grouping authd-apm-status-block {
     leaf authd-apm-state {
       type string;
       description
         "APM connection state";
     }
     leaf authd-apm-system-id {
       type string;
       description
         "APM connection system id";
     }
     leaf authd-apm-security {
       type string;
       description
         "APM connection security";
     }
     leaf authd-apm-apportionment {
       type string;
       description
         "APM apportionment";
     }
   }
   grouping authd-apm-domain-information-block {
     list authd-apm-domain {
       leaf pool-domain-name {
         type string;
       }
       leaf pool-domain-active-tag {
         type string;
       }
       leaf pool-domain-backup-tag {
         type string;
       }
       leaf pool-domain-pool-count {
         type uint32;
       }
       leaf pool-domain-total-addresses {
         type uint32;
       }
       leaf pool-domain-free-addresses {
         type uint32;
       }
       leaf pool-domain-apportionments-count {
         type uint32;
       }
       leaf pool-domain-reclaim-count {
         type uint32;
       }
       leaf pool-domain-abatement-count {
         type uint32;
       }
       leaf pool-domain-pooldrain-count {
         type uint32;
       }
     }
   }
   grouping authd-apm-domain-state-block {
     list authd-apm-domain-state-entry {
       leaf pool-domain-state-name {
         type string;
       }
       leaf pool-domain-state-alarm-type {
         type string;
       }
       leaf pool-domain-state-alarm-age {
         type string;
       }
     }
   }
   grouping node-secret-file-table-block {
     container node-secret-file-table-entry {
       leaf server-name {
         type string;
         description
           "Name of the SecurID server associated with this node secret file";
       }
       leaf node-secret-file {
         type string;
         description
           "Path of the node secret file";
       }
     }
   }
   grouping gx-plus-state-information-block {
     leaf gx-plus-engine-state {
       type string;
       description
         "Gx-plus engine state";
     }
     leaf gx-plus-config-state {
       type string;
       description
         "Gx-plus configuration state";
     }
     leaf gx-plus-active-config-state {
       type string;
       description
         "Gx-plus active configuration state";
     }
     leaf gx-plus-diameter-config-state {
       type string;
       description
         "Gx-plus diameter configuration state";
     }
     leaf gx-plus-total-prov-count {
       type uint32;
       description
         "Gx-plus number of entries, including pending, not including 
         logouts";
     }
     leaf gx-plus-pending-prov-count {
       type uint32;
       description
         "Gx-plus number of pending entries";
     }
     leaf gx-plus-pending-logout-count {
       type uint32;
       description
         "Gx-plus number of pending logouts";
     }
   }
   grouping gx-plus-sync-state-information-block {
     leaf gx-plus-sync-state-no-events {
       type string;
       description
         "No pending events";
     }
     list gx-plus-sync-state-data {
       description
         "Gx-plus sync state data";
       leaf gx-plus-sync-event-name {
         type string;
         description
           "Gx-plus sync-event name";
       }
       leaf gx-plus-sync-event-timeout {
         type uint32;
         description
           "Gx-plus sync-event time until next try timout (milliseconds)";
       }
     }
   }
   grouping gx-plus-statistics-information-block {
     leaf gx-plus-statistics-no-counters {
       type string;
       description
         "No counters to display";
     }
     container gx-plus-statistics-table {
       description
         "Gx-plus statistics table";
       list gx-plus-statistics-data {
         description
           "Gx-plus statistics data";
         leaf gx-plus-counter-name {
           type string;
           description
             "Gx-plus statistics counter name";
         }
         leaf gx-plus-counter-value {
           type uint64;
           description
             "Gx-plus statistics counter value";
         }
       }
     }
     container gx-plus-sync-event-stats-table {
       description
         "Gx-plus sync-event stats table";
       list gx-plus-sync-event-stats-data {
         description
           "Gx-plus sync-event stats data";
         leaf gx-plus-sync-event {
           type string;
           description
             "Gx-plus sync-event";
         }
         leaf gx-plus-sync-event-counter-name {
           type string;
           description
             "Gx-plus per sync-event statistics counter name";
         }
         leaf gx-plus-sync-event-counter-value {
           type uint64;
           description
             "Gx-plus per sync-event statistics counter value";
         }
       }
     }
     container gx-plus-sync-event-de-stats-table {
       description
         "Gx-plus syn-even diameter events stats table";
       list gx-plus-sync-event-de-stats-data {
         description
           "Gx-plus sync-event diameter event stats data";
         leaf gx-plus-sync-event-de {
           type string;
           description
             "Gx-plus sync-event";
         }
         leaf gx-plus-sync-event-de-counter-name {
           type string;
           description
             "Gx-plus per sync-event diameter event statistics counter name";
         }
         leaf gx-plus-sync-event-de-counter-value {
           type uint64;
           description
             "Gx-plus per sync-event diameter event statistics counter value";
         }
       }
     }
     container gx-plus-upstream-stats-table {
       description
         "Gx-plus upstream stats table";
       list gx-plus-upstream-stats-data {
         description
           "Gx-plus upsteam stats data";
         leaf gx-plus-upstream-category {
           type string;
           description
             "Gx-plus upstream category";
         }
         leaf gx-plus-upstream-counter-name {
           type string;
           description
             "Gx-plus upstream statistics counter name";
         }
         leaf gx-plus-upstream-counter-value {
           type uint64;
           description
             "Gx-plus upstream statistics counter value";
         }
       }
     }
     container gx-plus-upstream-de-stats-table {
       description
         "Gx-plus upstream diameter events stats table";
       list gx-plus-upstream-de-stats-data {
         description
           "Gx-plus upsteam diameter event stats data";
         leaf gx-plus-upstream-de-category {
           type string;
           description
             "Gx-plus per upstream category diameter events ";
         }
         leaf gx-plus-upstream-de-counter-name {
           type string;
           description
             "Gx-plus per upstream category diameter event statistics 
             counter name";
         }
         leaf gx-plus-upstream-de-counter-value {
           type uint64;
           description
             "Gx-plus per upstream category statistics counter value";
         }
       }
     }
     container gx-plus-downstream-stats-table {
       description
         "Gx-plus downstream stats-table";
       list gx-plus-downstream-stats-data {
         description
           "Gx-plus downsteam stats data";
         leaf gx-plus-downstream-category {
           type string;
           description
             "Gx-plus downstream category";
         }
         leaf gx-plus-downstream-counter-name {
           type string;
           description
             "Gx-plus downstream statistics counter name";
         }
         leaf gx-plus-downstream-counter-value {
           type uint64;
           description
             "Gx-plus downstream statistics counter value";
         }
       }
     }
   }
   grouping pcrf-state-information-block {
     container pcrf-state-table {
       description
         "Pcrf state table";
       list pcrf-state-data {
         description
           "Pcrf state data";
         leaf pcrf-state-component-name {
           type string;
           description
             "Pcrf state component name";
         }
         leaf pcrf-state-component-value {
           type uint64;
           description
             "Pcrf state component value";
         }
       }
     }
   }
   grouping pcrf-statistics-information-block {
     leaf pcrf-statistics-no-counters {
       type string;
       description
         "No counters to display";
     }
     container pcrf-statistics-table {
       description
         "Pcrf statistics table";
       list pcrf-statistics-data {
         description
           "Pcrf statistics data";
         leaf pcrf-counter-name {
           type string;
           description
             "Pcrf statistics counter name";
         }
         leaf pcrf-counter-value {
           type uint64;
           description
             "Pcrf statistics counter value";
         }
       }
     }
     container pcrf-diameter-event-table {
       description
         "Pcrf diameter event table";
       list pcrf-diameter-event-data {
         description
           "Pcrf diameter-event data";
         leaf pcrf-diameter-event-name {
           type string;
           description
             "Pcrf diameter event name";
         }
         leaf pcrf-diameter-event-counter-value {
           type uint64;
           description
             "Pcrf diameter event counter value";
         }
       }
     }
     container pcrf-rule-install-table {
       description
         "Pcrf install table";
       list pcrf-rule-install-data {
         description
           "Pcrf rule install data";
         leaf pcrf-rule-install-counter-name {
           type string;
           description
             "Pcrf rule install counter name";
         }
         leaf pcrf-rule-install-counter-value {
           type uint64;
           description
             "Pcrf rule install counter value";
         }
       }
     }
     container pcrf-rule-remove-table {
       description
         "Pcrf remove table";
       list pcrf-rule-remove-data {
         description
           "Pcrf rule remove data";
         leaf pcrf-rule-remove-counter-name {
           type string;
           description
             "Pcrf rule remove counter name";
         }
         leaf pcrf-rule-remove-counter-value {
           type uint64;
           description
             "Pcrf rule remove counter value";
         }
       }
     }
   }
   grouping ocs-state-information-block {
     container ocs-state-table {
       description
         "Ocs state table";
       list ocs-state-data {
         description
           "Ocs state data";
         leaf ocs-state-component-name {
           type string;
           description
             "Ocs state component name";
         }
         leaf ocs-state-component-value {
           type uint64;
           description
             "Ocs state component value";
         }
       }
     }
   }
   grouping ocs-statistics-information-block {
     leaf ocs-statistics-no-counters {
       type string;
       description
         "No counters to display";
     }
     container ocs-statistics-table {
       description
         "Ocs statistics table";
       list ocs-statistics-data {
         description
           "Ocs statistics data";
         leaf ocs-counter-name {
           type string;
           description
             "Ocs statistics counter name";
         }
         leaf ocs-counter-value {
           type uint64;
           description
             "Ocs statistics counter value";
         }
       }
     }
     container ocs-diameter-event-table {
       description
         "Ocs diameter event table";
       list ocs-diameter-event-data {
         description
           "Ocs diameter-event data";
         leaf ocs-diameter-event-name {
           type string;
           description
             "Ocs diameter event name";
         }
         leaf ocs-diameter-event-counter-value {
           type uint64;
           description
             "Ocs diameter event counter value";
         }
       }
     }
   }
   grouping radsec-state-information-block {
     leaf radsec-state-no-destination {
       type string;
       description
         "Destination does not exist";
     }
     container radsec-state-table {
       description
         "Radsec state table";
       list radsec-state-data {
         description
           "Radsec state data";
         leaf radsec-destination {
           type uint32;
           description
             "Radsec destination";
         }
         leaf radsec-state-string-component-name {
           type string;
           description
             "Radsec state string component name";
         }
         leaf radsec-state-string-component-value {
           type string;
           description
             "Radsec state string component value";
         }
         leaf radsec-state-integer-component-name {
           type string;
           description
             "Radsec state integer component name";
         }
         leaf radsec-state-integer-component-value {
           type uint32;
           description
             "Radsec state integer component value";
         }
       }
     }
   }
   grouping local-cert-state-information-block {
     leaf local-cert-state-not-found {
       type string;
       description
         "No local certificates";
     }
     container local-cert-state-table {
       description
         "Local certificate state table";
       list local-cert-state-data {
         description
           "Local certificate state data";
         leaf local-cert-name {
           type string;
           description
             "Local certificate name";
         }
         leaf local-cert-state {
           type string;
           description
             "Local certificate state ";
         }
       }
     }
   }
   grouping local-cert-statistics-information-block {
     leaf local-cert-statistics-no-counters {
       type string;
       description
         "No counters to display";
     }
     container local-cert-statistics-table {
       description
         "Local certificate statistics table";
       list local-cert-statistics-data {
         description
           "Local certificate statistics data";
         leaf local-cert-counter-name {
           type string;
           description
             "Local certificate statistics counter name";
         }
         leaf local-cert-counter-value {
           type uint64;
           description
             "Local certificate statistics counter value";
         }
       }
     }
   }
   grouping s6a-state-information-block {
     container s6a-state-table {
       description
         "S6a state table";
       list s6a-state-data {
         description
           "S6a state data";
         leaf s6a-state-component-name {
           type string;
           description
             "S6a state component name";
         }
         leaf s6a-state-component-value {
           type uint64;
           description
             "S6a state component value";
         }
       }
     }
   }
   grouping s6a-statistics-information-block {
     leaf s6a-statistics-no-counters {
       type string;
       description
         "No counters to display";
     }
     container s6a-statistics-table {
       description
         "S6a statistics table";
       list s6a-statistics-data {
         description
           "S6a statistics data";
         leaf s6a-counter-name {
           type string;
           description
             "S6a statistics counter name";
         }
         leaf s6a-counter-value {
           type uint64;
           description
             "S6a statistics counter value";
         }
       }
     }
     container s6a-diameter-event-table {
       description
         "S6a diameter event table";
       list s6a-diameter-event-data {
         description
           "S6a diameter-event data";
         leaf s6a-diameter-event-name {
           type string;
           description
             "S6a diameter event name";
         }
         leaf s6a-diameter-event-counter-value {
           type uint64;
           description
             "S6a diameter event counter value";
         }
       }
     }
   }
   grouping nas-5g-state-information-block {
     leaf connection-state {
       type string;
       description
         "Connection state";
     }
     leaf total-number-of-subscribers {
       type int32;
       description
         "Total number of subscribers";
     }
   }
 }
