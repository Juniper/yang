/*
 * Copyright (c) 2026 Juniper Networks, Inc.
 * All rights reserved.
 */
 module junos-nfx-conf-chassis {
   namespace "http://yang.juniper.net/junos-nfx/conf/chassis";

   prefix jc-chassis;

   import junos-common-types {
     prefix jt;
     revision-date 2026-01-01;
   }

   import junos-nfx-conf-root {
     prefix jc;
     revision-date 2026-01-01;
   }

   organization "Juniper Networks, Inc.";

   contact "yang-support@juniper.net";

   description "Junos chassis configuration module";

   revision 2026-01-01 {
     description "Junos: 26.2R1.7";
   }

   augment /jc:configuration {
     uses chassis-group;
   }
   augment /jc:configuration/jc:groups {
     uses chassis-group;
   }
   grouping chassis-group {
     container chassis {
       description "Chassis configuration";
       uses chassis_type;
     }
   }
   grouping chassis_type {
     uses apply-advanced;
     container copy-tos-to-outer {
       description "Copy TOS from inner to outer header";
       uses apply-advanced;
       container service-type {
         description "Service type for which the TOS copy is needed";
         uses apply-advanced;
         leaf gre {
           description "Copy TOS for GRE Tunnel service";
           type empty;
         }
         leaf mt {
           description "Copy TOS for MT Tunnel service";
           type empty;
         }
       }
     }
     container nssu {
       presence "enable nssu";
       description "Nonstop Software Upgrade settings";
       uses apply-advanced;
       list upgrade-group {
         key name;
         ordered-by user;
         description "Nonstop Software Upgrade group";
         leaf name {
           type string {
             length "1 .. 254";
           }
         }
         uses apply-advanced;
         leaf-list fpcs {
           description "FPCs associated with update-group";
           type union {
             type string {
               pattern "<.*>|$.*";
             }
             type uint32;
           }
           max-elements 16;
         }
         list member {
           key name;
           description "Member of virtual chassis configuration";
           uses upgrade-group-fpcs;
         }
       }
       leaf rcp-count {
         description "Parallel rcp count";
         type union {
           type string {
             pattern "<.*>|$.*";
           }
           type int32 {
             range "1 .. 8";
           }
         }
       }
       leaf lc-reboot-delay {
         description "Delay between linecard reboot during NSSU";
         type union {
           type string {
             pattern "<.*>|$.*";
           }
           type int32 {
             range "0 .. 600";
           }
         }
       }
     }
     leaf no-psu-redundancy {
       description "Disable N+1 Redundancy for PSUs";
       type empty;
     }
     leaf no-power-budget {
       description "Disable Chassis Power Budget";
       type empty;
     }
     container psu {
       description "Power Supply Unit redundancy configuration";
       uses apply-advanced;
       container redundancy {
         description "PSU Redundancy settings";
         uses apply-advanced;
         leaf n-plus-n {
           description "PSU redundancy: N+N configuration";
           type empty;
         }
       }
     }
     leaf fpc-resync {
       description "Send and receive Nchip cells for newly onlined FPC";
       type empty;
     }
     container optics {
       presence "enable optics";
       description "Optics specific config";
       uses apply-advanced;
       leaf display-3po-pn {
         description "To display third party optics part number";
         type empty;
       }
       container pm {
         presence "enable pm";
         description "Optics Performance Monitoring";
         uses apply-advanced;
         leaf interval-length {
           description "Interval bin length";
           type enumeration {
             enum "10s" {
               description "10 seconds";
             }
             enum "30s" {
               description "30 seconds";
             }
             enum "1min" {
               description "1 minute";
             }
             enum "5min" {
               description "5 minutes";
             }
             enum "15min" {
               description "15 minutes";
             }
           }
         }
       }
       list logical-channel {
         key name;
         ordered-by user;
         description "Optics logical-channel specific config.";
         leaf name {
           description "Logical-channel-index";
           type union {
             type uint32;
             type string {
               pattern "<.*>|$.*";
             }
           }
         }
         uses apply-advanced;
         list logical-channel-assignment {
           key name;
           ordered-by user;
           description "Logical-channel assignment configs";
           leaf name {
             description "Index of assignment";
             type union {
               type uint32;
               type string {
                 pattern "<.*>|$.*";
               }
             }
           }
           uses apply-advanced;
           leaf description {
             description "Description of the logical-channel assignment";
             type string;
           }
           leaf allocation {
             description "Allocation of the logical-channel (Gbps)";
             type union {
               type uint32;
               type string {
                 pattern "<.*>|$.*";
               }
             }
           }
           leaf channel-assignment-type {
             description "Type of logical-channel (optical-channel or logical-channel)";
             type enumeration {
               enum "logical-channel" {
                 description "Channel is logical-channel";
               }
               enum "optical-channel" {
                 description "Channel is optical-channel";
               }
             }
           }
           leaf channel-assignment {
             description "Assignment of the logical-channel";
             type union {
               type uint32;
               type string {
                 pattern "<.*>|$.*";
               }
             }
           }
           leaf optical-channel-reference {
             description "Reference to optical-channel";
             type union {
               type jt:interface-device;
               type string {
                 pattern "<.*>|$.*";
               }
             }
           }
         }
         leaf admin-state {
           description "Logical-channel admin-state";
           default "enabled";
           type enumeration {
             enum "enabled" {
               description "Logical-channel is enabled";
             }
             enum "disabled" {
               description "Logical-channel is disabled";
             }
             enum "maint" {
               description "Logical-channel is set to maintainance mode";
             }
           }
         }
         leaf logical-channel-type {
           description "Type which determines the config/PM parameters";
           type enumeration {
             enum "ethernet" {
               description "Channel is logical-channel-type of Ethernet";
             }
             enum "otn" {
               description "Channel is logical-channel-type of OTN";
             }
           }
         }
         leaf trib-protocol {
           description "Protocol framing of the tributary signal";
           type enumeration {
             enum "1ge" {
               description "Protocol is 1G Ethernet";
             }
             enum "10ge-lan" {
               description "Protocol is 10G Ethernet LAN";
             }
             enum "10ge-wan" {
               description "Protocol is 10G Ethernet WAN";
             }
             enum "40ge" {
               description "Protocol is 400G Ethernet";
             }
             enum "100ge" {
               description "Protocol is 100G Ethernet";
             }
             enum "400ge" {
               description "Protocol is 400G Ethernet";
             }
             enum "800ge" {
               description "Protocol is 800G Ethernet";
             }
           }
         }
         leaf rate-class {
           description "Protocol framing of the tributary signal";
           type enumeration {
             enum "1g" {
               description "Tributary signal rate 1G";
             }
             enum "10g" {
               description "Tributary signal rate 10G";
             }
             enum "40g" {
               description "Tributary signal rate 40G";
             }
             enum "100g" {
               description "Tributary signal rate 100G";
             }
             enum "400g" {
               description "Tributary signal rate 400G";
             }
             enum "200g" {
               description "Tributary signal rate 200G";
             }
             enum "800g" {
               description "Tributary signal rate 800G";
             }
           }
         }
         leaf description {
           description "Description of the logical-channel";
           type string;
         }
         leaf ingress-channel-reference {
           description "Reference to ingress interface";
           type union {
             type jt:interface-device;
             type string {
               pattern "<.*>|$.*";
             }
           }
         }
       }
     }
     leaf craft-lockout {
       description "Disable craft interface input";
       type empty;
     }
     container config-button {
       description "Config button behavior settings";
       leaf no-rescue {
         description "Don't reset to rescue configuration";
         type empty;
       }
       leaf no-clear {
         description "Don't reset to factory-default configuration";
         type empty;
       }
     }
     leaf routing-engine-power-off-button-disable {
       description "Disable RE power off button";
       type empty;
     }
     choice source-route-choice {
       leaf source-route {
         description "Enable IP source-route processing";
         status deprecated;
         type empty;
       }
       leaf no-source-route {
         description "Don't enable IP source-route processing";
         status deprecated;
         type empty;
       }
     }
     choice packet-scheduling-choice {
       leaf packet-scheduling {
         description "Enable DX2.0 packet scheduling";
         type empty;
       }
       leaf no-packet-scheduling {
         description "Don't enable DX2.0 packet scheduling";
         type empty;
       }
     }
     leaf route-memory-enhanced {
       description "Enhance memory allocation for routes";
       status deprecated;
       type empty;
     }
     leaf policer-drop-probability-low {
       description "Set policer probabilistic drop probability to Minimum";
       type empty;
     }
     leaf policer-limit {
       description "Limit the policer tick unit to 32 bytes";
       type empty;
     }
     leaf enhanced-policer {
       description "Enhanced Policer Counters";
       type empty;
     }
     leaf firewall-async-stats {
       description "Enables Firewall Async Stats";
       type empty;
     }
     leaf effective-shaping-rate {
       description "Report effective shaping rate";
       type empty;
     }
     container memory-enhanced {
       presence "enable memory-enhanced";
       description "Enhance memory allocation";
       uses apply-advanced;
       leaf route {
         description "Enhance memory allocation for routes";
         type empty;
       }
       leaf filter {
         description "Enhance memory allocation for filter";
         type empty;
       }
       leaf vpn-label {
         description "Enhance memory allocation for L3 VPN label";
         type empty;
       }
     }
     leaf vrf-mtu-check {
       description "Enable Internet Processor II-based MTU check";
       type empty;
     }
     container icmp {
       description "ICMP protocol";
       uses apply-advanced;
       leaf rate-limit {
         description "Icmp rate-limit for non ttl-expired pkts in range";
         default "1";
         type union {
           type string {
             pattern "<.*>|$.*";
           }
           type uint32 {
             range "1 .. 1000";
           }
         }
       }
       leaf per-iff-rate-limit {
         description "Configure icmp per iff rate limit value in the range 50-500";
         default "50";
         type union {
           type string {
             pattern "<.*>|$.*";
           }
           type uint32 {
             range "50 .. 500";
           }
         }
       }
     }
     container routing-performance {
       description "Alter routing performance";
       uses apply-advanced;
     }
     container icmp6 {
       description "ICMP version 6 protocol";
       uses apply-advanced;
       leaf rate-limit {
         description "Icmp rate-limit for non ttl-expired pkts in range";
         default "1";
         type union {
           type string {
             pattern "<.*>|$.*";
           }
           type uint32 {
             range "1 .. 1000";
           }
         }
       }
       leaf per-iff-rate-limit {
         description "Configure icmp6 per iff rate limit value in the range 50-500";
         default "50";
         type union {
           type string {
             pattern "<.*>|$.*";
           }
           type uint32 {
             range "50 .. 500";
           }
         }
       }
     }
     leaf maximum-ecmp {
       description "Maximum ECMP limit for nexthops";
       type enumeration {
         enum "16" {
           description "Maximum 16 ECMP routes";
         }
         enum "32" {
           description "Maximum 32 ECMP routes";
         }
         enum "64" {
           description "Maximum 64 ECMP routes";
         }
         enum "96" {
           description "Maximum 96 ECMP routes";
         }
         enum "128" {
           description "Maximum 128 ECMP routes";
         }
         enum "160" {
           description "Maximum 160 ECMP routes";
         }
         enum "192" {
           description "Maximum 192 ECMP routes";
         }
         enum "224" {
           description "Maximum 224 ECMP routes";
         }
         enum "256" {
           description "Maximum 256 ECMP routes";
         }
         enum "288" {
           description "Maximum 288 ECMP routes";
         }
         enum "320" {
           description "Maximum 320 ECMP routes";
         }
         enum "352" {
           description "Maximum 352 ECMP routes";
         }
         enum "384" {
           description "Maximum 384 ECMP routes";
         }
         enum "416" {
           description "Maximum 416 ECMP routes";
         }
         enum "448" {
           description "Maximum 448 ECMP routes";
         }
         enum "480" {
           description "Maximum 480 ECMP routes";
         }
         enum "512" {
           description "Maximum 512 ECMP routes";
         }
       }
     }
     container ecmp-alb {
       presence "enable ecmp-alb";
       description "Enable adaptive load balancing for ECMP nexthops";
       uses apply-advanced;
       leaf tolerance {
         description "Adaptive tolerance in percentage (default 20%)";
         default "20";
         units "percent";
         type union {
           type string {
             pattern "<.*>|$.*";
           }
           type uint32 {
             range "1 .. 100";
           }
         }
       }
     }
     container redundancy {
       description "Redundancy settings";
       uses chassis_redundancy_type;
     }
     container routing-engine {
       description "Routing Engine settings";
       uses chassis_routing_engine_type;
     }
     container port-extender {
       presence "enable port-extender";
       description "Port extender settings";
       uses apply-advanced;
       list fpc-slot {
         key name;
         ordered-by user;
         description "Virtual FPC settings";
         leaf name {
           description "Virtual slot of the satellite device";
           type union {
             type string {
               pattern "<.*>|$.*";
             }
             type uint8 {
               range "65 .. 254";
             }
           }
         }
         uses apply-advanced;
         leaf desc {
           description "Description of the satellite device";
           type string;
         }
         leaf device {
           description "Model of the satellite device";
           type enumeration {
             enum "ex4400-48p" {
               description "Select EX4400-48P as the satellite";
             }
             enum "ex4400-48t" {
               description "Select EX4400-48T as the satellite";
             }
             enum "qfx5120-48t-6c" {
               description "Select QFX5120-48T-CHAS as the satellite";
             }
             enum "qfx5120-48y-8c" {
               description "Select JNP48Y8C-CHAS as the satellite";
             }
           }
         }
         leaf satellite-mgmt-ip {
           description "Management IP of the satellite device";
           type jt:ipv4addr;
         }
         list cascade-port {
           key name;
           ordered-by user;
           description "List of cascade ports";
           leaf name {
             description "AE interface name";
             type string {
             }
           }
           uses apply-advanced;
         }
         leaf target-mode {
           description "Enable EP targeting";
           type empty;
         }
         list pic-slot {
           key name;
           ordered-by user;
           description "PIC slot";
           leaf name {
             description "PIC slot number";
             type union {
               type string {
                 pattern "<.*>|$.*";
               }
               type uint8 {
                 range 0;
               }
             }
           }
           uses apply-advanced;
           list port {
             key name;
             ordered-by user;
             description "Port settings";
             leaf name {
               description "Port number";
               type union {
                 type string {
                   pattern "<.*>|$.*";
                 }
                 type uint16 {
                   range "0 .. 47";
                 }
               }
             }
             uses apply-advanced;
             leaf speed {
               description "Port speed";
               type enumeration {
                 enum "speed-100mbps" {
                   description "Sets the interface speed to 100Mbps";
                 }
                 enum "speed-1gbps" {
                   description "Sets the interface speed to 1Gbps";
                 }
                 enum "speed-10gbps" {
                   description "Sets the interface speed to 10Gbps";
                 }
                 enum "speed-25gbps" {
                   description "Sets the interface speed to 25Gbps";
                 }
               }
             }
           }
         }
       }
     }
     container aggregated-devices {
       description "Aggregated devices configuration";
       uses chassis_agg_dev_type;
     }
     list disk-partition {
       key name;
       ordered-by user;
       description "Chassis disk monitor configuration";
       leaf name {
         description "Choose disk partition to monitor";
         type enumeration {
           enum "/var" {
             description "Monitor /var partition";
           }
           enum "/config" {
             description "Monitor /config partition";
           }
         }
       }
       uses apply-advanced;
       list level {
         key name;
         ordered-by user;
         description "Threshold level";
         leaf name {
           type enumeration {
             enum "high" {
               description "Set high level of threshold";
             }
             enum "full" {
               description "Set full level of threshold";
             }
           }
         }
         uses apply-advanced;
         container free-space {
           description "Enter threshold value & choose the metric";
           leaf thres-free {
             description "Enter free space threshold value";
             type union {
               type string {
                 pattern "<.*>|$.*";
               }
               type uint32 {
                 range "0 .. 100";
               }
             }
           }
           choice thres-metric {
             case case_1 {
               leaf percent {
                 description "Free space threshold in %";
                 type empty;
               }
             }
             case case_2 {
               leaf mb {
                 description "Free space threshold in MB";
                 type empty;
               }
             }
           }
         }
       }
     }
     container container-devices {
       description "Container devices configuration";
       uses chassisd_agg_container_type;
     }
     container pseudowire-service {
       description "Pseudowire L3 termination device configuration";
       presence "enable pseudowire-service";
       uses chassis-pw-type;
     }
     container provider-instance-devices {
       description "Provider instance devices configuration";
       uses chassisd_provider_instance_type;
     }
     container power-off-ports-on-no-master-re {
       description "Power off line card ports at once in the absence of any master RE";
       uses chassis_power_off_ports_on_no_master_re_type;
     }
     container redundancy-group {
       description "Redundancy group configuration";
       uses chassisd-redundancy-group-type;
     }
     container fabric {
       description "Switch fabric settings";
       uses chassis_fabric_type;
     }
     list fpc {
       key name;
       description "Flexible PIC Concentrator parameters";
       uses chassis_fpc_type;
     }
     leaf node-id {
       description "Chassis identifier";
       status deprecated;
       type union {
         type string {
           pattern "<.*>|$.*";
         }
         type uint64 {
           range "1 .. 18446744073709551615";
         }
       }
     }
     container p4rt {
       presence "enable p4rt";
       description "Chassis p4rt";
       uses apply-advanced;
       leaf node-id {
         description "Chassis identifier";
         type union {
           type string {
             pattern "<.*>|$.*";
           }
           type uint64 {
             range "1 .. 18446744073709551615";
           }
         }
       }
     }
     list cb {
       key name;
       description "Control Board parameters";
       uses chassis_cb_type;
     }
     list ftc {
       key name;
       description "Ftc parameters";
       uses chassis_ftc_type;
     }
     list sfb {
       key name;
       description "Switch Fabric parameters";
       uses chassis_sfb_type;
     }
     leaf disable-fm {
       description "Disable Fabric Manager";
       type empty;
     }
     leaf disable-power-management {
       description "Disable Power Management in this chassis";
       type empty;
     }
     leaf monitor-pem-inputs {
       description "Enable low current usage monitoring";
       type empty;
     }
     leaf dedicated-ukern-cpu {
       description "Run Microkernel on a dedicated CPU core";
       type empty;
     }
     leaf realtime-ukern-thread {
       description "Run Microkernel on a realtime CPU thread";
       type empty;
     }
     container fpc-feb-connectivity {
       description "Connectivity between Flexible PIC Concentrators and Forwarding Engine Boards";
       uses apply-advanced;
       list fpc {
         key name;
         leaf name {
           description "FPC slot number";
           type union {
             type string {
               pattern "<.*>|$.*";
             }
             type uint32;
           }
         }
         uses apply-advanced;
         container feb {
           description "FEB slot number";
           choice feb-slot-choice {
             case case_1 {
               leaf none {
                 description "FPC not connected to any FEB";
                 type empty;
               }
             }
             case case_2 {
               leaf feb-slot {
                 description "FEB slot number";
                 type union {
                   type string {
                     pattern "<.*>|$.*";
                   }
                   type uint32;
                 }
               }
             }
           }
         }
       }
     }
     container ioc-npc-connectivity {
       description "Connectivity between IOC and NPC";
       uses apply-advanced;
       list ioc {
         key name;
         leaf name {
           description "IOC-FPC slot number";
           type union {
             type string {
               pattern "<.*>|$.*";
             }
             type uint32;
           }
         }
         uses apply-advanced;
         container npc {
           description "NPC-FPC slot number";
           choice npc-slot-choice {
             case case_1 {
               leaf none {
                 description "IOC not connected to any NPC";
                 type empty;
               }
             }
             case case_2 {
               leaf npc-slot {
                 description "NPC-FPC slot number";
                 type union {
                   type string {
                     pattern "<.*>|$.*";
                   }
                   type uint32;
                 }
               }
             }
           }
         }
       }
     }
     container pem {
       description "Power supply (PEM) parameters";
       uses chassis_pem_type;
     }
     container sib {
       description "Switch Interface Board parameters";
       uses chassis_sib_type;
     }
     container fabric-card {
       description "Fabric card parameters";
       presence "enable fabric-card";
       uses chassis_fabric_cards_type;
     }
     list sfm {
       key name;
       description "Switching and Forwarding Module parameters";
       uses chassis_sfm_type;
     }
     container feb {
       description "Forwarding Engine Board parameters";
       uses chassis_feb_type;
     }
     container afeb {
       description "Forwarding Engine Board parameters";
       uses chassis_feb_type;
     }
     container tfeb {
       description "Taz Forwarding Engine Board parameters";
       uses chassis_feb_type;
     }
     container alarm {
       description "Global alarm settings";
       uses chassis_alarm_type;
     }
     leaf slow-pfe-alarm {
       description "Enable slow (potential) PFE alarm";
       type empty;
     }
     leaf onbox-av-load-flavor {
       description "Select onbox anti-virus traffic load flavor";
       type enumeration {
         enum "heavy" {
           description "Allocates additional resources for improved performance";
         }
       }
     }
     leaf fpc-ifl-ae-statistics {
       description "Enable fpc ifl ae child statistics";
       type empty;
     }
     leaf ppp-subscriber-services {
       description "Select PPP subscriber services";
       default "disable";
       type enumeration {
         enum "disable" {
           description "Disable PPP subscriber services";
         }
         enum "enable" {
           description "Enable PPP subscriber services";
         }
       }
     }
     leaf ambient-temperature {
       description "Chassis ambient-temperature value in degree celsius";
       type enumeration {
         enum "55C" {
           description "55 degree celsius";
         }
         enum "40C" {
           description "40 degree celsius";
         }
         enum "25C" {
           description "25 degree celsius";
         }
         enum "32C" {
           description "32 degree celsius";
         }
       }
     }
     container resource-watch {
       description "Chassis routing engine resource watch configuration";
       uses apply-advanced;
       leaf resource-watch-enable {
         description "Enable resource watch";
         type empty;
       }
       leaf cpu-statistics {
         description "Set statistics collection, 0 disable";
         units "seconds";
         type union {
           type string {
             pattern "<.*>|$.*";
           }
           type uint32 {
             range "0 .. 604800";
           }
         }
       }
       leaf junos-statistics {
         description "Set statistics collection, 0 disable";
         units "seconds";
         type union {
           type string {
             pattern "<.*>|$.*";
           }
           type uint32 {
             range "0 .. 604800";
           }
         }
       }
       leaf orange-zone-enable {
         description "Enable orange zone";
         type empty;
       }
       leaf orange-zone-threshold {
         description "Set orange zone value (CPU idle %), default 20";
         type union {
           type string {
             pattern "<.*>|$.*";
           }
           type uint32 {
             range "1 .. 99";
           }
         }
       }
       leaf red-zone-enable {
         description "Enable red zone";
         type empty;
       }
       leaf red-zone-cpu-threshold {
         description "Set red zone value (CPU idle %), default 10";
         type union {
           type string {
             pattern "<.*>|$.*";
           }
           type uint32 {
             range "1 .. 99";
           }
         }
       }
       leaf red-zone-jkl-threshold {
         description "Set red zone value (Junos load %), default 50";
         type union {
           type string {
             pattern "<.*>|$.*";
           }
           type uint32 {
             range "1 .. 99";
           }
         }
       }
       leaf red-zone-snmp-enable {
         description "Enable red zone snmp";
         type empty;
       }
     }
     leaf interoperability {
       description "Chassis chash configuration";
       type enumeration {
         enum "advanced-forwarding" {
           description "Enable only Aft based FPCs";
         }
       }
     }
     leaf network-services {
       description "Chassis network services configuration";
       type enumeration {
         enum "ip" {
           description "IP network services";
         }
         enum "ethernet" {
           description "Ethernet network services";
         }
         enum "enhanced-ip" {
           description "Enhanced IP network services";
         }
         enum "enhanced-ethernet" {
           description "Enhanced ethernet network services";
         }
         enum "enhanced-mode" {
           description "Enhanced network services";
         }
         enum "lan" {
           description "Ethernet LAN services";
         }
       }
     }
     leaf limited-ifl-scaling {
       description "Configured to limit IFL scaling to 64k";
       type empty;
     }
     container alarm-port {
       description "Craft-interface parameters";
       uses chassis_alarm_port_op_type;
     }
     container usb {
       description "USB control flags";
       uses apply-advanced;
       container storage {
         description "USB storage flags";
         uses apply-advanced;
         leaf disable {
           description "Disable USB storage";
           type empty;
         }
       }
     }
     container serdes {
       presence "enable serdes";
       description "Serdes test mode for link training";
       uses apply-advanced;
       leaf test-mode {
         description "Serdes test mode";
         type string;
       }
     }
     list lcc {
       key name;
       description "Line-card chassis configuration";
       leaf name {
         description "LCC number";
         type union {
           type string {
             pattern "<.*>|$.*";
           }
           type uint32;
         }
       }
       uses apply-advanced;
       list fpc {
         key name;
         description "Flexible PIC Concentrator parameters";
         uses chassis_fpc_type;
       }
       container pem {
         description "Power supply (PEM) parameters";
         uses chassis_pem_type;
       }
       container spmb {
         description "Switch Processor Mezzanine Board parameters";
         uses apply-advanced;
       }
       choice state {
         case case_1 {
           leaf online-expected {
             description "LCC is expected to be online";
             type empty;
           }
         }
         case case_2 {
           leaf offline {
             description "LCC is expected to be offline";
             type empty;
           }
         }
       }
     }
     container lcc-mode {
       description "Line card chassis mode T4000/T1600/EMPTY configuration";
       uses apply-advanced;
       list lcc {
         key name;
         leaf name {
           description "LCC number";
           type union {
             type string {
               pattern "<.*>|$.*";
             }
             type uint32;
           }
         }
         uses apply-advanced;
         leaf mode {
           description "Changing Mode of LCC will result in the restart of LCC";
           default "t1600";
           type enumeration {
             enum "t1600" {
               description "LCC Mode will be set to t1600";
             }
             enum "t4000" {
               description "LCC Mode will be set to t4000";
             }
             enum "empty" {
               description "Setting LCC mode to empty will offline the LCC";
             }
           }
         }
       }
     }
     list member {
       key name;
       description "Member chassis configuration";
       leaf name {
         description "Member number";
         type union {
           type string {
             pattern "<.*>|$.*";
           }
           type uint32 {
             range "0 .. 10";
           }
         }
       }
       uses apply-advanced;
       container fabric {
         description "Switch fabric settings";
         uses chassis_fabric_type;
       }
       list fpc {
         key name;
         description "Flexible PIC Concentrator parameters";
         uses chassis_fpc_type;
       }
     }
     container license {
       presence "enable license";
       description "Set license";
       uses apply-advanced;
       leaf bandwidth {
         description "Configure bandwidth of FPC";
         type union {
           type uint32;
           type string {
             pattern "<.*>|$.*";
           }
         }
       }
       leaf scale {
         description "Add scale license";
         type enumeration {
           enum "base" {
             description "Base license";
           }
           enum "advance" {
             description "Advance license";
           }
           enum "premium" {
             description "Premium license";
           }
         }
       }
     }
     container host-outbound {
       description "Host-out bound options ";
       uses apply-advanced;
       leaf media-interface {
         description "Enable processing of media interface features for Host gernated packets";
         type empty;
       }
     }
     container synchronization {
       description "Clock synchronization options";
       uses apply-advanced;
       leaf switchover-mode {
         description "Should system revert to higher priority valid source";
         default "revertive";
         type enumeration {
           enum "non-revertive" {
             description "System uses current source as long as it is valid";
           }
           enum "revertive" {
             description "Automatically switch to higher priority valid source";
           }
         }
       }
       leaf switching-mode {
         description "Should system revert to higher priority valid source";
         default "non-revertive";
         type enumeration {
           enum "non-revertive" {
             description "System uses current source as long as it is valid";
           }
           enum "revertive" {
             description "Automatically switch to higher priority valid source";
           }
         }
       }
       leaf network-option {
         description "EEC synchronization networking type";
         type enumeration {
           enum "option-1" {
             description "Option 1 (EEC1) synchronization networking";
           }
           enum "option-2" {
             description "Option 2 (EEC2) synchronization networking";
           }
         }
       }
       leaf selection-mode {
         description "Selection mode for incoming ESMC quality";
         default "configured-quality";
         type enumeration {
           enum "configured-quality" {
             description "Use source's configured ESMC quality";
           }
           enum "received-quality" {
             description "Use source's received ESMC quality";
           }
         }
       }
       leaf clock-mode {
         description "Synchronous Ethernet Clock selection mode";
         type enumeration {
           enum "free-run" {
             description "Use the free-running local oscillator";
           }
           enum "auto-select" {
             description "Select best clock source";
           }
         }
       }
       leaf quality-mode-enable {
         description "Enable Synchronous Ethernet ESMC Quality mode";
         type empty;
       }
       leaf max-transmit-quality-level {
         description "Maximum transmit quality level";
         type enumeration {
           enum "ePRTC" {
             description "Time quality of enhanced primary reference time clock";
           }
           enum "PRTC" {
             description "Time quality of primary reference time clock";
           }
           enum "ePRC" {
             description "Time quality of enhanced primary reference clock";
           }
           enum "eEEC" {
             description "Time quality of enhanced ethernet equipment clock";
           }
           enum "prc" {
             description "Timing quality of a primary reference clock (option-1 only)";
           }
           enum "ssu-a" {
             description "Timing quality of a type I or IV slave clock (option-1 only)";
           }
           enum "ssu-b" {
             description "Timing quality of a type VI slave clock (option-1 only)";
           }
           enum "sec" {
             description "Timing quality of SDH equipment clock (option-1 only)";
           }
           enum "prs" {
             description "Clock traceable to primary reference source (option-2 only)";
           }
           enum "stu" {
             description "Clock traceable to unknown quality (option-2 only)";
           }
           enum "st2" {
             description "Clock traceable to stratum 2 (option-2 only)";
           }
           enum "tnc" {
             description "Clock traceable to transit node clock (option-2 only)";
           }
           enum "st3e" {
             description "Clock traceable to stratum 3E (option-2 only)";
           }
         }
       }
       leaf enable-extended-ql-tlv {
         description "Enable enhanced ESMC QL support";
         type empty;
       }
       leaf global-wait-to-restore {
         description "Global Port signal up state time before opening for ESMC";
         units "min";
         type union {
           type string {
             pattern "<.*>|$.*";
           }
           type uint32 {
             range "0 .. 12";
           }
         }
       }
       leaf minimum-quality {
         description "Minimum quality threshold";
         type enumeration {
           enum "prc" {
             description "Timing quality of a primary reference clock (option-1 only)";
           }
           enum "ssu-a" {
             description "Timing quality of a type I or IV slave clock (option-1 only)";
           }
           enum "ssu-b" {
             description "Timing quality of a type VI slave clock (option-1 only)";
           }
           enum "sec" {
             description "Timing quality of SDH equipment clock (option-1 only)";
           }
           enum "prs" {
             description "Clock traceable to primary reference source (option-2 only)";
           }
           enum "st2" {
             description "Clock traceable to stratum 2 (option-2 only)";
           }
           enum "tnc" {
             description "Clock traceable to transit node clock (option-2 only)";
           }
           enum "st3e" {
             description "Clock traceable to stratum 3E (option-2 only)";
           }
           enum "st3" {
             description "Clock traceable to stratum 3 (option-2 only)";
           }
           enum "st4" {
             description "Clock traceable to stratum 4 free-run (option-2 only)";
           }
           enum "smc" {
             description "Clock traceable to self-timed SONET (option-2 only)";
           }
           enum "stu" {
             description "Clock traceable to unknown quality (option-2 only)";
           }
         }
       }
       list port {
         key name;
         description "Clock synchronization ports";
         leaf name {
           type enumeration {
             enum "auxiliary" {
               description "Auxiliary port";
             }
             enum "gnss" {
               description "Global Navigation Satellite System - GPS or GLONASS port";
             }
             enum "time-of-day" {
               description "Time of Day(TOD) port";
             }
           }
         }
         uses apply-advanced;
         container client {
           presence "enable client";
           description "Port client receiving external signals";
           uses apply-advanced;
           container time-of-day-format {
             description "Time-of-day format as received on this port";
             uses apply-advanced;
             choice format {
               case case_1 {
                 leaf ascii {
                   description "ASCII Time-of-day message format string";
                   type string {
                     length "1 .. 80";
                   }
                 }
               }
               case case_2 {
               }
               case case_3 {
               }
             }
           }
           leaf cable-length-compensation {
             description "Antenna cable length compensation in nanoseconds";
             type union {
               type uint32;
               type string {
                 pattern "<.*>|$.*";
               }
             }
           }
           leaf antenna-voltage {
             description "Configure antenna voltage";
             type enumeration {
               enum "3.3" {
                 description "3.3 units";
               }
               enum "5" {
                 description "5 units";
               }
             }
           }
           leaf constellation {
             description "Configure constellation of satellites to use";
             type enumeration {
               enum "gps" {
                 description "Global Positioning Satellite(GPS) for clock recovery";
               }
               enum "glonass" {
                 description "Global Navigation Satellite System(GLONASS) constellation";
               }
               enum "gps-and-glonass" {
                 description "All constellations";
               }
               enum "beidou" {
                 description "BEIDOU for clock recovery constellations";
               }
               enum "gps-beidou" {
                 description "GPS and BEIDOU for clock recovery";
               }
               enum "gps-beidou-qzss" {
                 description "GPS ,BEIDOU and qzss for clock recovery";
               }
               enum "galileo" {
                 description "GALILEO for clock recovery";
               }
               enum "gps-galileo" {
                 description "GPS and GALILEO for clock recovery";
               }
               enum "gps-qzss" {
                 description "GPS and QZSS for clock recovery";
               }
               enum "gps-glonass-qzss" {
                 description "GPS,GLONASS and QZSS for clock recovery";
               }
               enum "gps-galileo-qzss" {
                 description "GPS , GALILEO and QZSS for clock recovery";
               }
             }
           }
           leaf anti-jamming {
             description "Enable anti-jamming feature";
             type empty;
           }
         }
         container server {
           presence "enable server";
           description "The role of port is server which transmits signals out";
           uses apply-advanced;
           container time-of-day-format {
             description "RS-232 port time-of-day format";
             uses apply-advanced;
             choice format {
               case case_1 {
                 leaf ascii {
                   description "ASCII Time-of-day message format string";
                   type string {
                     length "1 .. 80";
                   }
                 }
               }
             }
           }
         }
       }
       list interfaces {
         key name;
         description "Interface(s) with upstream clock source";
         leaf name {
           type enumeration {
             enum "external" {
               description "External clock interface";
             }
             enum "external-0/0" {
               description "External clock interface on SCB-0";
             }
             enum "external-0/1" {
               description "External clock interface on SCB-0";
             }
             enum "external-1/0" {
               description "External clock interface on SCB-1";
             }
             enum "external-1/1" {
               description "External clock interface on SCB-1";
             }
             enum "external-a" {
               description "External-A clock interface";
             }
             enum "external-b" {
               description "External-B clock interface";
             }
             enum "external-0" {
               description "External-0 clock interface";
             }
             enum "external-1" {
               description "External-1 clock interface";
             }
             enum "external-2" {
               description "External-2 clock interface";
             }
             enum "bits" {
               description "External BITS interface configuration";
             }
             enum "bits-a" {
               description "External BITS interface A configuration";
             }
             enum "bits-b" {
               description "External BITS interface B configuration";
             }
             enum "gps-0" {
               description "External GPS interface A configuration";
             }
             enum "gps-1" {
               description "External GPS interface B configuration";
             }
           }
         }
         uses apply-advanced;
         leaf signal-type {
           description "Frequency for provided reference clocks";
           type enumeration {
             enum "1mhz" {
               description "1 MHz clock signal";
             }
             enum "5mhz" {
               description "5 MHz clock signal";
             }
             enum "10mhz" {
               description "10 MHz clock signal";
             }
             enum "2048khz" {
               description "E1 unframed 2048Khz G.703 signal";
             }
             enum "e1" {
               description "E1-coded 2048 KHz signal on 120 ohm balanced line";
             }
             enum "t1" {
               description "T1-coded 1.544 MHz signal on 100 ohm balanced line";
             }
             enum "cc-8k" {
               description "Composite Clock 64kHz+8kHz";
             }
             enum "cc-8k-400" {
               description "Composite Clock 64kHz+8kHz+400Hz";
             }
             enum "6312k" {
               description "Japanese Standard 6312kHz";
             }
           }
         }
         leaf pulse-per-second-enable {
           description "Enable pulse-per-second (PPS) receive on the interface";
           type empty;
         }
         container e1-options {
           description "E1 interface-specific options";
           uses apply-advanced;
           leaf line-encoding {
             description "Line encoding";
             default "hdb3";
             type enumeration {
               enum "ami" {
                 description "Automatic mark inversion";
               }
               enum "hdb3" {
                 description "High-density bipolar 3 code";
               }
             }
           }
           leaf framing {
             description "Framing mode";
             default "g704";
             type enumeration {
               enum "g704" {
                 description "G.704 framing format for E1 interfaces";
               }
               enum "g704-no-crc4" {
                 description "G.704 framing without CRC4 for E1 interfaces";
               }
             }
           }
           leaf sabit {
             description "The sabit used for exchanging SSM quality";
             default "4";
             type union {
               type string {
                 pattern "<.*>|$.*";
               }
               type uint32 {
                 range "4 .. 8";
               }
             }
           }
         }
         container t1-options {
           description "T1 interface-specific options";
           uses apply-advanced;
           leaf line-encoding {
             description "Line encoding";
             default "b8zs";
             type enumeration {
               enum "ami" {
                 description "Automatic mark inversion";
               }
               enum "b8zs" {
                 description "8-bit zero suppression";
               }
             }
           }
           leaf framing {
             description "Framing mode";
             default "esf";
             type enumeration {
               enum "esf" {
                 description "Extended Super Frame";
               }
               enum "sf" {
                 description "Super Frame";
               }
             }
           }
         }
       }
       container output {
         description "External clock interface related";
         uses apply-advanced;
         list interfaces {
           key name;
           description "Interface(s) to output source to";
           leaf name {
             type enumeration {
               enum "external" {
                 description "External clock interface";
               }
               enum "external-0/0" {
                 description "External clock interface on SCB-0";
               }
               enum "external-0/1" {
                 description "External clock interface on SCB-0";
               }
               enum "external-1/0" {
                 description "External clock interface on SCB-1";
               }
               enum "external-1/1" {
                 description "External clock interface on SCB-1";
               }
               enum "external-a" {
                 description "External-A clock interface";
               }
               enum "external-b" {
                 description "External-B clock interface";
               }
               enum "bits" {
                 description "External BITS interface configuration";
               }
               enum "external-0" {
                 description "External-0 clock interface";
               }
               enum "external-1" {
                 description "External-1 clock interface";
               }
               enum "external-2" {
                 description "External-2 clock interface";
               }
             }
           }
           uses apply-advanced;
           container ssm {
             description "SSM Message config";
             uses apply-advanced;
             leaf option-2 {
               description "Select generation";
               type enumeration {
                 enum "GEN-1" {
                   description "SSM Message type GEN-1";
                 }
                 enum "GEN-2" {
                   description "SSM Message type GEN-2";
                 }
               }
             }
           }
           container squelch {
             presence "enable squelch";
             description "Squelch a interface";
             uses apply-advanced;
             leaf method {
               description "Type of Squelch to be done";
               type enumeration {
                 enum "ais" {
                   description "Send AIS";
                 }
                 enum "ql-dnu" {
                   description "Send DNU Quality level out";
                 }
                 enum "rai" {
                   description "Method RAI";
                 }
                 enum "shut" {
                   description "Shutdown";
                 }
               }
             }
           }
           leaf wander-filter-disable {
             description "Disables wander filtering";
             type empty;
           }
           leaf holdover-mode-disable {
             description "Disables holdover";
             type empty;
           }
           leaf source-mode {
             description "Source mode for selecting source to output";
             default "line";
             type enumeration {
               enum "chassis" {
                 description "The chassis clock is output";
               }
               enum "line" {
                 description "The best line clock source is output";
               }
               enum "equipment-clock" {
                 description "The chassis clock is output";
               }
               enum "ptp-clock" {
                 description "The best line clock source is output";
               }
             }
           }
           leaf tx-dnu-to-line-source-enable {
             description "Sets Tx QL to DNU/DUS on line source interface";
             type empty;
           }
           leaf minimum-quality {
             description "Minimum quality threshold";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
       }
       container source {
         description "ESMC source(s) related";
         uses apply-advanced;
         container external-a {
           presence "enable external-a";
           description "External Clock source A";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         container external-b {
           presence "enable external-b";
           description "External Clock source B";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         container gps {
           presence "enable gps";
           description "Global Positioning System 10MHz input";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf no-ssm-support {
             description "No SSM support available for this interface";
             type empty;
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         container gps-0 {
           presence "enable gps-0";
           description "Global Positioning System input A";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         container gps-1 {
           presence "enable gps-1";
           description "Global Positioning System input B";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         container bits {
           presence "enable bits";
           description "External Building Integrated Timing Supply input";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf no-ssm-support {
             description "No SSM support available for this interface";
             type empty;
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         container bits-a {
           presence "enable bits-a";
           description "External Building Integrated Timing Supply input A";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         container bits-b {
           presence "enable bits-b";
           description "External Building Integrated Timing Supply input B";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         container virtual-port {
           presence "enable virtual-port";
           description "Virtual port";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         list interfaces {
           key name;
           description "Interface(s) with upstream clock source";
           leaf name {
             type string;
           }
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf no-ssm-support {
             description "No SSM support available for this interface";
             type empty;
           }
           leaf hold-off-time {
             description "Port signal down state time before closing for ESMC";
             units "milliseconds";
             type union {
               type string {
                 pattern "<.*>|$.*";
               }
               type uint32 {
                 range "300 .. 1800";
               }
             }
           }
           leaf aggregated-ether {
             description "Aggregated sources group name";
             type string;
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
       }
       container esmc-transmit {
         description "ESMC transmit parameters";
         uses apply-advanced;
         list interfaces {
           key name;
           ordered-by user;
           description "Interface(s) on which to permit ESMC transmit messages";
           leaf name {
             type string;
           }
           uses apply-advanced;
           container squelch {
             presence "enable squelch";
             description "Squelch a interface";
             uses apply-advanced;
             leaf method {
               description "Type of Squelch to be done";
               type enumeration {
                 enum "ais" {
                   description "Send AIS";
                 }
                 enum "ql-dnu" {
                   description "Send DNU Quality level out";
                 }
                 enum "rai" {
                   description "Method RAI";
                 }
                 enum "shut" {
                   description "Shutdown";
                 }
               }
             }
             leaf quality-level {
               description "ESMC Quality level below which output is squelched";
               type enumeration {
                 enum "ePRTC" {
                   description "Time quality of enhanced primary reference time clock";
                 }
                 enum "PRTC" {
                   description "Time quality of primary reference time clock";
                 }
                 enum "ePRC" {
                   description "Time quality of enhanced primary reference clock";
                 }
                 enum "eEEC" {
                   description "Time quality of enhanced ethernet equipment clock";
                 }
                 enum "prc" {
                   description "Timing quality of a primary reference clock (option-1 only)";
                 }
                 enum "ssu-a" {
                   description "Timing quality of a type I or IV slave clock (option-1 only)";
                 }
                 enum "ssu-b" {
                   description "Timing quality of a type VI slave clock (option-1 only)";
                 }
                 enum "sec" {
                   description "Timing quality of SDH equipment clock (option-1 only)";
                 }
                 enum "prs" {
                   description "Clock traceable to primary reference source (option-2 only)";
                 }
                 enum "st2" {
                   description "Clock traceable to stratum 2 (option-2 only)";
                 }
                 enum "tnc" {
                   description "Clock traceable to transit node clock (option-2 only)";
                 }
                 enum "st3e" {
                   description "Clock traceable to stratum 3E (option-2 only)";
                 }
                 enum "st3" {
                   description "Clock traceable to stratum 3 (option-2 only)";
                 }
                 enum "st4" {
                   description "Clock traceable to stratum 4 free-run (option-2 only)";
                 }
                 enum "smc" {
                   description "Clock traceable to self-timed SONET (option-2 only)";
                 }
                 enum "stu" {
                   description "Clock traceable to unknown quality (option-2 only)";
                 }
               }
             }
           }
         }
       }
       container hold-interval {
         description "Hold interval";
         uses apply-advanced;
         leaf switchover {
           description "Switchover wait time after clock recovery";
           default "30";
           units "sec";
           type union {
             type string {
               pattern "<.*>|$.*";
             }
             type uint32 {
               range "30 .. 60";
             }
           }
         }
         leaf configuration-change {
           description "Clock select wait time after change in config";
           default "15";
           units "sec";
           type union {
             type string {
               pattern "<.*>|$.*";
             }
             type uint32 {
               range "15 .. 60";
             }
           }
         }
         leaf restart {
           description "Clock select wait time after reboot";
           default "120";
           units "sec";
           type union {
             type string {
               pattern "<.*>|$.*";
             }
             type uint32 {
               range "60 .. 180";
             }
           }
         }
       }
       leaf validation-interval {
         description "Time between frequency measurements";
         default "90";
         units "seconds";
         type union {
           type string {
             pattern "<.*>|$.*";
           }
           type uint32 {
             range "90 .. 86400";
           }
         }
       }
       leaf slave-free-run {
         description "Slave Clock running mode";
         type empty;
       }
       leaf y-cable-line-termination {
         description "A single signal is wired to both CBs via Y-cable";
         type empty;
       }
       leaf transmitter-enable {
         description "Control whether diagnostic timing signal is transmitted";
         type empty;
       }
       leaf signal-type {
         description "Frequency for provided reference clocks";
         default "t1";
         type enumeration {
           enum "e1" {
             description "E1-coded 2048 Khz signal on 120 ohm balanced line";
           }
           enum "t1" {
             description "T1-coded 1.544 Mhz signal on 100 ohm balanced line";
           }
           enum "cc-8k" {
             description "Composite Clock 64kHz+8kHz";
           }
           enum "cc-8k-400" {
             description "Composite Clock 64kHz+8kHz+400Hz";
           }
           enum "6312k" {
             description "Japanese Standard 6312kHz";
           }
         }
       }
       leaf primary {
         description "Best choice synchronization reference source list";
         type enumeration {
           enum "external-a" {
             description "Use external-a as a primary source";
           }
           enum "external-b" {
             description "Use external-b as a primary source";
           }
           enum "bits-a" {
             description "Use bits-a as a primary source";
           }
           enum "bits-b" {
             description "Use bits-b as a primary source";
           }
           enum "gps-0" {
             description "Use gps-0 as a primary source";
           }
           enum "gps-1" {
             description "Use gps-1 as a primary source";
           }
           enum "fpc-0" {
             description "Use fpc-0 as a primary source";
           }
           enum "fpc-1" {
             description "Use fpc-1 as a primary source";
           }
           enum "fpc-2" {
             description "Use fpc-2 as a primary source";
           }
           enum "fpc-3" {
             description "Use fpc-3 as a primary source";
           }
           enum "fpc-4" {
             description "Use fpc-4 as a primary source";
           }
           enum "fpc-5" {
             description "Use fpc-5 as a primary source";
           }
           enum "fpc-6" {
             description "Use fpc-6 as a primary source";
           }
           enum "fpc-7" {
             description "Use fpc-7 as a primary source";
           }
           enum "fpc-8" {
             description "Use fpc-8 as a primary source";
           }
           enum "fpc-9" {
             description "Use fpc-9 as a primary source";
           }
           enum "fpc-10" {
             description "Use fpc-10 as a primary source";
           }
           enum "fpc-11" {
             description "Use fpc-11 as a primary source";
           }
           enum "fpc-12" {
             description "Use fpc-12 as a primary source";
           }
           enum "fpc-13" {
             description "Use fpc-13 as a primary source";
           }
           enum "fpc-14" {
             description "Use fpc-14 as a primary source";
           }
           enum "fpc-15" {
             description "Use fpc-15 as a primary source";
           }
         }
       }
       leaf secondary {
         description "Alternative choice synchronization reference source list";
         type enumeration {
           enum "external-a" {
             description "Use external-a as a secondary source";
           }
           enum "external-b" {
             description "Use external-b as a secondary source";
           }
           enum "bits-a" {
             description "Use bits-a as a secondary source";
           }
           enum "bits-b" {
             description "Use bits-b as a secondary source";
           }
           enum "gps-0" {
             description "Use gps-0 as a secondary source";
           }
           enum "gps-1" {
             description "Use gps-1 as a secondary source";
           }
           enum "fpc-0" {
             description "Use fpc-0 as a secondary source";
           }
           enum "fpc-1" {
             description "Use fpc-1 as a secondary source";
           }
           enum "fpc-2" {
             description "Use fpc-2 as a secondary source";
           }
           enum "fpc-3" {
             description "Use fpc-3 as a secondary source";
           }
           enum "fpc-4" {
             description "Use fpc-4 as a secondary source";
           }
           enum "fpc-5" {
             description "Use fpc-5 as a secondary source";
           }
           enum "fpc-6" {
             description "Use fpc-6 as a secondary source";
           }
           enum "fpc-7" {
             description "Use fpc-7 as a secondary source";
           }
           enum "fpc-8" {
             description "Use fpc-8 as a secondary source";
           }
           enum "fpc-9" {
             description "Use fpc-9 as a secondary source";
           }
           enum "fpc-10" {
             description "Use fpc-10 as a secondary source";
           }
           enum "fpc-11" {
             description "Use fpc-11 as a secondary source";
           }
           enum "fpc-12" {
             description "Use fpc-12 as a secondary source";
           }
           enum "fpc-13" {
             description "Use fpc-13 as a secondary source";
           }
           enum "fpc-14" {
             description "Use fpc-14 as a secondary source";
           }
           enum "fpc-15" {
             description "Use fpc-15 as a secondary source";
           }
         }
       }
       list gnss-receiver {
         key name;
         description "Global Navigation Satellite System receiver configs";
         leaf name {
           description "GNSS port/slot number";
           type union {
             type string {
               pattern "<.*>|$.*";
             }
             type uint32;
           }
         }
         uses apply-advanced;
         leaf interface {
           description "Enable/Disable GNSS port/slot communication";
           type empty;
         }
         leaf disable-log {
           description "Enable/Disable logging of gnss-receiver messages";
           type empty;
         }
         leaf snr-threshold {
           description "Satellites with signal levels above this value are used in positioning- in dBHz";
           type union {
             type string {
               pattern "<.*>|$.*";
             }
             type uint32 {
               range "0 .. 99";
             }
           }
         }
         container receiver-type {
           description "GNSS receiver type";
           uses apply-advanced;
           leaf tb-1 {
             description "External receiver: type tb-1 ";
             type empty;
           }
           leaf internal {
             description "Receiver type is internal";
             type empty;
           }
         }
         container position-mode {
           description "GNSS Receiver's different positioning modes";
           uses apply-advanced;
           container survey-mode {
             description "Set survey mode and length of survey in minutes";
             uses apply-advanced;
             leaf survey-length {
               description "GNSS Receiver's number of position fixes, before switching to position-fix mode- in mins";
               type union {
                 type string {
                   pattern "<.*>|$.*";
                 }
                 type int32 {
                   range "0 .. 10080";
                 }
               }
             }
           }
           container position-fix-mode {
             description "Set gnss receiver to fixed position mode";
             uses apply-advanced;
             leaf latitude {
               description "GNSS Receiver's latitude in decimal degrees, range -90.000000 to 90.000000";
               type decimal64 {
                 fraction-digits 9;
                 range "-90 .. 90";
               }
             }
             leaf longitude {
               description "GNSS Receiver's longitude in decimal degrees, range -180.000000 to 180.000000";
               type decimal64 {
                 fraction-digits 9;
                 range "-180 .. 180";
               }
             }
             leaf altitude {
               description "GNSS Receiver's altitude in meters, range -1000.000000 to 18000.000000";
               type decimal64 {
                 fraction-digits 9;
                 range "-1000 .. 18000";
               }
             }
           }
         }
         leaf cable-delay-compensation {
           description "GNSS Receiver Unit to Router RF cable delay compensation in nanoseconds";
           type union {
             type string {
               pattern "<.*>|$.*";
             }
             type int32 {
               range "-100000 .. 100000";
             }
           }
         }
         container constellation {
           description "GNSS Receiver's different constellation and bands";
           uses apply-advanced;
           container gps {
             description "GPS constellation";
             uses apply-advanced;
             leaf l1ca {
               description "GPS L1 band";
               type empty;
             }
           }
           container glonass {
             description "GLONASS constellation";
             uses apply-advanced;
             leaf l1of {
               description "GLONASS L1 band";
               type empty;
             }
           }
           container galileo {
             description "GALILEO constellation";
             uses apply-advanced;
             leaf e1 {
               description "GALILEO E1 band";
               type empty;
             }
           }
           container qzss {
             description "QZSS constellation";
             uses apply-advanced;
             leaf l1ca {
               description "QZSS L1 band";
               type empty;
             }
           }
         }
       }
     }
     container lcd {
       description "Chassis LCD";
       status deprecated;
       uses apply-advanced;
       list fpc {
         key name;
         ordered-by user;
         leaf name {
           description "FPC slot number";
           type union {
             type string {
               pattern "<.*>|$.*";
             }
             type uint32;
           }
         }
         choice menu-item {
           case case_1 {
             leaf maintenance-menu {
               description "LCD maintenance menu";
               type empty;
             }
           }
         }
         choice enable-disable {
           case case_1 {
             leaf disable {
               description "Disable maintenance-menu";
               type empty;
             }
           }
         }
       }
       choice menu-item {
         case case_1 {
           leaf maintenance-menu {
             description "LCD maintenance menu";
             type empty;
           }
         }
       }
       choice enable-disable {
         case case_1 {
           leaf disable {
             description "Disable maintenance-menu";
             type empty;
           }
         }
       }
     }
     container forwarding-options {
       description "Configure options to control packet forwarding";
       uses apply-advanced;
       choice uft_object {
         case case_1 {
           container l2-profile-one {
             presence "enable l2-profile-one";
             description "MAC: 288K L3-host: 16K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_2 {
           container l2-profile-two {
             presence "enable l2-profile-two";
             description "MAC: 224K L3-host: 80K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_3 {
           container l2-profile-three {
             presence "enable l2-profile-three";
             description "(default) MAC: 160K L3-host: 144K LPM: 16K, needs reboot for VC;restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_4 {
           container l3-profile {
             presence "enable l3-profile";
             description "MAC: 96K L3-host: 208K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_5 {
           container lpm-profile {
             presence "enable lpm-profile";
             description "MAC: 32K L3-host: 16K LPM: 128K EM:0, needs reboot for VC; restarts PFE if standalone";
             uses apply-advanced;
             leaf prefix-65-127-disable {
               description "Disable IPV6 prefixes with length > 64";
               type empty;
             }
             leaf unicast-in-lpm {
               description "Install unicast host entries in LPM table";
               type empty;
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_6 {
           container exact-match-profile {
             presence "enable exact-match-profile";
             description "MAC: 8K L3-host: 8K LPM: 16K EM: 64K, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_7 {
           container vxlan-gbp-profile {
             presence "enable vxlan-gbp-profile";
             description "MAC: 48K L3-host: 48K LPM: 16K EM:16K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_8 {
           container vxlan-gbp-l2-profile {
             presence "enable vxlan-gbp-l2-profile";
             description "MAC: 64K L3-host: 32K LPM: 16K EM:16K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_9 {
           container vxlan-gbp-l3-profile {
             presence "enable vxlan-gbp-l3-profile";
             description "MAC: 32K L3-host: 64K LPM: 16K EM:16K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_10 {
           container vxlan-gbp-mc-profile {
             presence "enable vxlan-gbp-mc-profile";
             description "MAC: 32K L3-host: 64K LPM: 16K EM:16K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_11 {
           container em-hw-profile {
             presence "enable em-hw-profile";
             description "MAC: 48K L3-host: 48K LPM: 16K EM:32K, needs reboot for VC; restarts PFE if standalone";
           }
         }
         case case_12 {
           container gbp-pure-l2-profile {
             presence "enable gbp-pure-l2-profile";
             description "MAC: 48K L3-host: 48K LPM: 16K EM:16K, needs reboot for VC; restarts PFE if standalone";
           }
         }
         case case_13 {
           container default-profile {
             presence "enable default-profile";
             description "MAC: 64K L3-host: 32K LPM: 24K IFP: 12K, needs reboot for VC; restarts PFE if standalone";
           }
         }
         case case_14 {
           container ifp-profile {
             presence "enable ifp-profile";
             description "MAC: 64K L3-host: 32K LPM: 12K IFP: 18K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_15 {
           container custom-profile {
             description "(Partition the shared banks, will automatically restart the PFE when configured)";
             uses apply-advanced;
             container l2-entries {
               description "Customize l2 entries needed";
               uses apply-advanced;
               leaf num-banks {
                 description "Number of banks needed for entries of this type";
                 default "0";
                 type union {
                   type string {
                     pattern "<.*>|$.*";
                   }
                   type int32 {
                     range "0 .. 4";
                   }
                 }
               }
             }
             container l3-entries {
               description "Customize l3 entries needed";
               uses apply-advanced;
               leaf num-banks {
                 description "Number of banks needed for entries of this type";
                 default "0";
                 type union {
                   type string {
                     pattern "<.*>|$.*";
                   }
                   type int32 {
                     range "0 .. 4";
                   }
                 }
               }
             }
             container exact-match-entries {
               description "Customize exact match entries needed";
               uses apply-advanced;
               leaf num-banks {
                 description "Number of banks needed for entries of this type";
                 default "0";
                 type union {
                   type string {
                     pattern "<.*>|$.*";
                   }
                   type int32 {
                     range "0 .. 4";
                   }
                 }
               }
             }
             container lpm-entries {
               description "Customize lpm banks needed";
               uses apply-advanced;
               leaf num-banks {
                 description "Number of banks needed for entries of this type";
                 default "0";
                 type enumeration {
                   enum "0" {
                   }
                   enum "2" {
                   }
                   enum "4" {
                   }
                 }
               }
               leaf prefix-65-127-disable {
                 description "Disable IPV6 prefixes with length > 64";
                 type empty;
               }
             }
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
       }
     }
     leaf loopback-firewallv6-optimization {
       description "Increase ACL scale for loopback IPv6 filters; restarts PFE";
       type empty;
     }
     leaf ipv6linklocal-sourcechecking {
       description "Enable ipv6 linklocal source checking. This will restart PFE";
       type empty;
     }
     leaf input-firewall-optimized-profile {
       description "Optimal default filter usage when IFA/FCoe/FIPsnooping is not used; restarts PFE";
       type empty;
     }
     leaf ivacl-firewall-no-portrange-profile {
       description "L4 Src/Dst Port range optimize is not needed; restarts PFE";
       type empty;
     }
     leaf iracl-firewall-ipv4-profile {
       description "IPv6 address match is not needed for IRACL filters; restarts PFE";
       type empty;
     }
     leaf ipvacl-firewall-l2-profile {
       description "Only Src/Dst MAC,VLAN,EtherType match is needed for IPACL/IVACL filters; restarts PFE";
       type empty;
     }
     leaf loopback-firewall-optimization {
       description "Optimal TCAM use,reboot(VC);restarts PFE(IP rsrved mcast dest&ttl=0/1,config explicitly)";
       type empty;
     }
     leaf loopback-firewall-per-vrf {
       description "Enable per vrf control, needs reboot for VC; restarts PFE if standalone";
       type empty;
     }
     leaf epacl-firewall-optimization {
       description "Maximizes Egress Port ACLs TCAM use and restarts PFE";
       type empty;
     }
     leaf per-logical-interface-firewall {
       description "Ingress port firewall can be supported per logical interface, restarts PFE";
       type empty;
     }
     container lcd-menu {
       description "Chassis LCD menu";
       uses apply-advanced;
       list fpc {
         key name;
         ordered-by user;
         leaf name {
           description "FPC slot number";
           type union {
             type string {
               pattern "<.*>|$.*";
             }
             type uint32;
           }
         }
         uses apply-advanced;
         list menu-item {
           key name;
           ordered-by user;
           description "LCD menu item";
           leaf name {
             description "LCD menu name";
             type string;
           }
           leaf disable {
             description "Disable LCD menu";
             type empty;
           }
         }
       }
       list menu-item {
         key name;
         ordered-by user;
         description "LCD menu item";
         leaf name {
           description "LCD menu name";
           type string;
         }
         leaf disable {
           description "Disable LCD menu";
           type empty;
         }
       }
     }
     leaf fru-poweron-sequence {
       description "FRUs power on sequence like 0 1 2 3 ... within double quotes";
       type string {
       }
     }
     leaf fru-local-storage-disable {
       description "Disable and erase local storage on FPC.(FPC reboot required)";
       type empty;
     }
     leaf fpc-empolicy-profile {
       description "FPC EM Policy Profile";
       type enumeration {
         enum "low-power-mode" {
           description "Set low power mode";
         }
       }
     }
     container em-policy {
       presence "enable em-policy";
       description "EM Policy Configuration";
       uses apply-advanced;
       leaf fire-fru-shutdown {
         description "Enable/Disable fire fru shutdown";
         type enumeration {
           enum "Enable" {
             description "Enable Fire Fru Shutdown";
           }
           enum "Disable" {
             description "Disable Fire Fru Shutdown";
           }
         }
       }
       leaf fan-max-pwm {
         description "Set max pwm fan speed %";
         type union {
           type string {
             pattern "<.*>|$.*";
           }
           type uint32 {
             range "30 .. 100";
           }
         }
       }
     }
     container psm {
       description "Power supply module";
       uses apply-advanced;
       container redundancy {
         description "PSM Source/Feed Redundancy configuration";
         uses apply-advanced;
         leaf source-redundancy {
           description "Toggle source redundancy for PSM";
           type empty;
         }
         container feed-redundancy {
           description "Toggle feed redundancy for a PSM slot";
           uses apply-advanced;
           list slot {
             key name;
             description "PSM slot number";
             leaf name {
               description "Select PSM slot";
               type union {
                 type string {
                   pattern "<.*>|$.*";
                 }
                 type uint32;
               }
             }
             uses apply-advanced;
           }
         }
       }
       leaf min-voltage {
         description "Set minimum input voltage(V)";
         type union {
           type uint32;
           type string {
             pattern "<.*>|$.*";
           }
         }
       }
       leaf max-power {
         description "Configure power capacity for the PSM (W)";
         type union {
           type uint32;
           type string {
             pattern "<.*>|$.*";
           }
         }
       }
     }
     leaf auto-image-upgrade {
       description "Auto image upgrade using DHCP";
       type empty;
     }
     container route-localization {
       description "Route-Localization settings";
       uses apply-advanced;
       leaf inet {
         description "Route-Localization inet";
         type empty;
       }
       leaf inet6 {
         description "Route-Localization inet6";
         type empty;
       }
     }
     container state {
       description "Set SFB upgrade state.";
       uses apply-advanced;
       leaf cb-upgrade {
         description "Set CB upgrade state on/off.";
         default "off";
         type enumeration {
           enum "off" {
             description "Set after CB upgrade is complete";
           }
           enum "on" {
             description "Set before the start of CB upgrade.";
           }
         }
       }
       leaf sfb-upgrade {
         description "Set SFB upgrade state on/off.";
         default "off";
         type enumeration {
           enum "off" {
             description "Set after SFB upgrade is complete";
           }
           enum "on" {
             description "Set before the start of SFB upgrade.";
           }
         }
       }
     }
     container multicast-loadbalance {
       description "Multicast load balancing settings";
       presence "enable multicast-loadbalance";
       uses chassis_ae_lb_type;
     }
     leaf extended-statistics {
       description "Enable extended system statistics";
       type empty;
     }
     container error {
       description "Error level configuration for all FPC";
       uses chassis_junos_fru_error_type;
     }
     container oss-map {
       description "Translate Operation Supported System's requirements";
       uses apply-advanced;
       leaf model-name {
         description "Override chassis model name for specific show/snmp output";
         type enumeration {
           enum "t640" {
             description "Set to T640's model";
           }
           enum "t1600" {
             description "Set to T1600's model";
           }
         }
       }
     }
     container jnu-management {
       description "JNU Management configuration";
       uses apply-advanced;
       leaf mode {
         description "JNU Mode";
         type enumeration {
           enum "feature-rich" {
             description "Feature Rich Mode";
           }
           enum "bng-control-plane" {
             description "BNG control-plane mode";
           }
         }
       }
       leaf satellite-name {
         description "Satellite name";
         type string;
       }
       leaf device-group {
         description "Satellite device group";
         type string;
       }
       list device-group-map {
         key name;
         ordered-by user;
         description "Common groups mapping to device groups";
         leaf name {
           description "Satellite Device Group";
           type string;
         }
         uses apply-advanced;
         leaf-list include-groups {
           ordered-by user;
           description "Common groups list";
           type string;
         }
       }
       list satellite {
         key name;
         ordered-by user;
         description "List of satellites";
         leaf name {
           description "Satellite name";
           type string;
         }
         uses apply-advanced;
         leaf device-group {
           description "Satellite Device Group";
           type string;
         }
         leaf model {
           description "Satellite model";
           type string;
         }
         leaf version {
           description "Satellite version";
           type string {
           }
         }
       }
       leaf user {
         description "Satellite User Name";
         type string;
       }
       leaf-list controller {
         ordered-by user;
         description "Controller Name";
         type string;
       }
       leaf other-controller {
         description "Dual controller Name";
         type string;
       }
       leaf authentication {
         description "Authentication string";
         type jt:unreadable;
       }
     }
     list satellite {
       key name;
       ordered-by user;
       description "List of available satellite configurations";
       leaf name {
         description "Satellite name";
         type string;
       }
       uses apply-advanced;
     }
     leaf preserve-fpc-poweron-sequence {
       description "Preserve MPC poweron sequence for consistency across reboot";
       type empty;
     }
     leaf auto-satellite-conversion {
       description "Enable remote conversion to satellite device-mode";
       type empty;
     }
     container satellite-management {
       presence "enable satellite-management";
       description "Satellite management configuration";
       uses apply-advanced;
       container designated-event-forwarding {
         presence "enable designated-event-forwarding";
         description "Designated event forwarding";
       }
       container traceoptions {
         description "Global satelite discovery and provisioning trace options";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             units "bytes";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "parse" {
                 description "Trace configuration parsing";
               }
               enum "config-internal" {
                 description "Trace configuration internals";
               }
               enum "normal" {
                 description "Trace normal events";
               }
               enum "general" {
                 description "Trace general events";
               }
               enum "state" {
                 description "Trace state transitions";
               }
               enum "task" {
                 description "Trace SDPD task processing";
               }
               enum "timer" {
                 description "Trace SDPD task timer processing";
               }
               enum "krt" {
                 description "Trace communication over routing socket";
               }
               enum "lldp" {
                 description "Trace LLDP events";
               }
               enum "provision" {
                 description "Trace provisioning events";
               }
               enum "extended-port" {
                 description "Trace extended-port events";
               }
               enum "multi-chassis" {
                 description "Trace multi-chassis events";
               }
               enum "upgrade-group" {
                 description "Trace sw-update events";
               }
               enum "device" {
                 description "Trace device FSM events";
               }
               enum "tcp" {
                 description "Trace TCP events";
               }
               enum "interface" {
                 description "Trace interface events";
               }
               enum "cluster" {
                 description "Trace cluster events";
               }
               enum "all" {
                 description "Trace everything";
               }
             }
           }
           leaf disable {
             description "Disable this trace flag";
             type empty;
           }
         }
       }
       leaf cluster-policy {
         description "Cluster policy";
         type string;
       }
       list cluster {
         key name;
         description "Configure a satellite device cluster";
         leaf name {
           description "Satellite cluster name";
           type string {
             length "1 .. 16";
           }
         }
         uses apply-advanced;
         leaf cluster-id {
           description "Satellite cluster identifier";
           type union {
             type string {
               pattern "<.*>|$.*";
             }
             type uint32 {
               range "1 .. 32";
             }
           }
         }
         leaf-list cascade-ports {
           description "Cascade ports";
           type union {
             type jt:interface-device;
             type string {
               pattern "<.*>|$.*";
             }
           }
         }
         leaf cluster-policy {
           description "Candidate uplink policy";
           type string;
         }
         list fpc {
           key name;
           leaf name {
             description "Satellite slot identifier";
             type union {
               type string {
                 pattern "<.*>|$.*";
               }
               type uint32 {
                 range "65 .. 254";
               }
             }
           }
           uses apply-advanced;
           leaf alias {
             description "Satellite alias";
             type string {
               length "1 .. 16";
             }
           }
           leaf description {
             description "Satellite description";
             type string {
               length "1 .. 64";
             }
           }
           leaf member-id {
             description "Satellite member id";
             type union {
               type string {
                 pattern "<.*>|$.*";
               }
               type uint32 {
                 range "0 .. 62";
               }
             }
           }
           leaf system-id {
             description "Satellite system id";
             type jt:mac-addr;
           }
           leaf cluster-policy {
             description "Candidate uplink policy";
             type string;
           }
         }
       }
       list fpc {
         key name;
         description "FPC identifier for a satellite device";
         leaf name {
           description "Satellite slot identifier";
           type union {
             type string {
               pattern "<.*>|$.*";
             }
             type uint32 {
               range "65 .. 254";
             }
           }
         }
         uses apply-advanced;
         leaf serial-number {
           description "Satellite serial number";
           type string {
             length "1 .. 16";
           }
         }
         leaf system-id {
           description "Satellite system id";
           type jt:mac-addr;
         }
         leaf target-mode {
           description "Enable target mode forwarding for extended-ports";
           type empty;
         }
         leaf alias {
           description "Satellite alias";
           type string {
             length "1 .. 16";
           }
         }
         leaf description {
           description "Satellite description";
           type string {
             length "1 .. 64";
           }
         }
         container management-address {
           presence "enable management-address";
           description "Satellite Management Interface IP";
           uses apply-advanced;
           leaf address {
             description "Satellite Management Interface IP address";
             type jt:ipv4prefix;
           }
           leaf gateway {
             description "Satellite Management Interface Gateway IP address";
             type jt:ipv4addr;
           }
         }
         leaf-list cascade-ports {
           description "Cascade ports";
           type union {
             type jt:interface-device;
             type string {
               pattern "<.*>|$.*";
             }
           }
         }
         leaf extended-ports-template {
           description "Extended ports template";
           type string;
         }
         choice ufd_type {
           case case_1 {
             container uplink-failure-detection {
               presence "enable uplink-failure-detection";
               description "Enable uplink-failure-detection";
               uses apply-advanced;
               leaf candidate-uplink-policy {
                 description "Candidate uplink policy";
                 type string;
               }
             }
           }
         }
         leaf environment-monitoring-policy {
           description "Environment monitoring policy";
           type string;
         }
         choice forwarding-policy-type {
           case case_1 {
             container forwarding-policy {
               presence "enable forwarding-policy";
               description "Enable a forwarding policy";
               uses apply-advanced;
               leaf forwarding-policy-alias {
                 description "Define forwarding policy alias";
                 type string;
               }
             }
           }
         }
       }
       leaf extended-ports-policy {
         description "Extended ports policy";
         type string;
       }
       choice ufd_type {
         case case_1 {
           container uplink-failure-detection {
             presence "enable uplink-failure-detection";
             description "Enable uplink-failure-detection";
             uses apply-advanced;
             leaf candidate-uplink-policy {
               description "Candidate uplink policy";
               type string;
             }
           }
         }
       }
       container psu {
         description "Power Supply Unit redundancy configuration";
         uses apply-advanced;
         container redundancy {
           description "PSU Redundancy settings";
           uses apply-advanced;
           leaf n-plus-n {
             description "PSU redundancy: N+N configuration";
             type empty;
           }
         }
       }
       container environment-monitoring-policy {
         presence "enable environment-monitoring-policy";
         description "Environment monitoring policy";
         uses apply-advanced;
         leaf policy-name {
           description "Default environment monitoring policy";
           type string;
         }
       }
       choice forwarding-policy-type {
         case case_1 {
           container forwarding-policy {
             presence "enable forwarding-policy";
             description "Enable a forwarding policy";
             uses apply-advanced;
             leaf forwarding-policy-alias {
               description "Define forwarding policy alias";
               type string;
             }
           }
         }
       }
       container redundancy-groups {
         description "Redundancy groups configuration";
         uses apply-advanced;
         leaf chassis-id {
           description "Chassis identifier";
           type union {
             type string {
               pattern "<.*>|$.*";
             }
             type uint32 {
               range "1 .. 4";
             }
           }
         }
         list rg-group {
           key name;
           ordered-by user;
           description "Redundancy groups";
           uses redundancy-group-type;
         }
       }
       container upgrade-groups {
         description "Upgrade group configuration";
         uses apply-advanced;
         list upgrade-group {
           key name;
           description "Upgrade group";
           uses upgrade-group-type;
         }
       }
       container auto-satellite-conversion {
         description "Enable automatic satellite conversion";
         uses apply-advanced;
         leaf-list satellite {
           ordered-by user;
           description "Satellite slot-id or range or all";
           type string {
             length "1 .. 100";
           }
         }
       }
       container single-home {
         description "Devices are connected to local aggregation device only";
         uses apply-advanced;
         leaf-list satellite {
           ordered-by user;
           description "Satellite slot-id or range or all";
           type string {
             length "1 .. 100";
           }
         }
       }
       leaf aging-timer {
         description "Aging-timer";
         units "minutes";
         type union {
           type string {
             pattern "<.*>|$.*";
           }
           type uint32 {
             range "2 .. 60000";
           }
         }
       }
       leaf block-console-access {
         description "Block console access";
         type empty;
       }
       container firewall {
         description "Define a firewall configuration";
         uses apply-advanced;
         container family {
           description "Protocol family";
           container bridge {
             description "Protocol family BRIDGE for firewall filter";
             uses apply-advanced;
             list filter {
               key name;
               ordered-by user;
               uses satellite-bridge-filter;
             }
           }
           container ethernet-switching {
             description "Protocol family Ethernet Switching for firewall filter";
             uses apply-advanced;
             list filter {
               key name;
               ordered-by user;
               description "Define an Ethernet Switching firewall filter";
               uses satellite-bridge-filter;
             }
           }
         }
       }
     }
     container periodic {
       description "Chassisd periodic options";
       uses apply-advanced;
       leaf yield-cpu {
         description "Yield cpu in FRU periodic";
         type empty;
       }
       leaf one-sib-per-check {
         description "Check one SIB per periodic";
         type empty;
       }
       leaf no-sib-asic-stats {
         description "Disable asic statis for all SIBs in periodic";
         type empty;
       }
       leaf slow-fpc-check {
         description "Slow FPC check in periodic";
         type empty;
       }
       leaf ch-power-check-interval {
         description "Chassis power check interval, 0=default";
         default "0";
         units "seconds";
         type union {
           type string {
             pattern "<.*>|$.*";
           }
           type uint32 {
             range "0 .. 60";
           }
         }
       }
       leaf re-check-interval {
         description "Chassis RE check interval, 0=default";
         default "0";
         units "seconds";
         type union {
           type string {
             pattern "<.*>|$.*";
           }
           type uint32 {
             range "0 .. 60";
           }
         }
       }
     }
     leaf turbotx-disable {
       description "Disable turbotx processing";
       type empty;
     }
     container thermal-health-check {
       presence "enable thermal-health-check";
       description "Enable Thermal Health check of the chassis";
       uses apply-advanced;
       container fet-failure-check {
         presence "enable fet-failure-check";
         uses apply-advanced;
         leaf action-onfail {
           description "Set the action when Oring FET detected";
           default "none";
           type enumeration {
             enum "none" {
               description "No action when Oring FET detected";
             }
             enum "auto-shutdown" {
               description "Shutdown when Oring FET detected";
             }
           }
         }
       }
     }
     container fpc-down-on-repeated-conn-drops {
       description "Bring FPC down if connection drops repeatedly";
       uses apply-advanced;
       leaf max-drop-count {
         description "Number of connection drops to shutdown FPC";
         default "0";
         type union {
           type uint32;
           type string {
             pattern "<.*>|$.*";
           }
         }
       }
       leaf time-interval {
         description "Interval in minutes over which connection drops are counted";
         default "0";
         units "minutes";
         type union {
           type uint32;
           type string {
             pattern "<.*>|$.*";
           }
         }
       }
     }
     container utilization {
       presence "enable utilization";
       description "Set chassis resource utilization";
       uses apply-advanced;
       container forwarding {
         presence "enable forwarding";
         description "Set forwarding resource utilization";
         uses apply-advanced;
         container fabric {
           description "Set fabric resource utilization for PFE";
           uses apply-advanced;
           list fpc {
             key name;
             leaf name {
               description "FPC slot number";
               type string {
                 length "0 .. 63";
               }
             }
             uses apply-advanced;
             leaf used-threshold-upper {
               description "Upper threshold in percentage";
               default "2";
               type union {
                 type string {
                   pattern "<.*>|$.*";
                 }
                 type uint32 {
                   range "2 .. 100";
                 }
               }
             }
             leaf used-threshold-upper-clear {
               description "Upper threshold clear in percentage";
               default "1";
               type union {
                 type string {
                   pattern "<.*>|$.*";
                 }
                 type uint32 {
                   range "1 .. 99";
                 }
               }
             }
             list pfe {
               key name;
               leaf name {
                 description "PFE(Packet forwarding engine) identifier";
                 type string {
                   length "0 .. 8";
                 }
               }
               uses apply-advanced;
               leaf used-threshold-upper {
                 description "Upper threshold in percentage";
                 default "2";
                 type union {
                   type string {
                     pattern "<.*>|$.*";
                   }
                   type uint32 {
                     range "2 .. 100";
                   }
                 }
               }
               leaf used-threshold-upper-clear {
                 description "Upper threshold clear in percentage";
                 default "1";
                 type union {
                   type string {
                     pattern "<.*>|$.*";
                   }
                   type uint32 {
                     range "1 .. 99";
                   }
                 }
               }
             }
           }
           leaf used-threshold-upper {
             description "Upper threshold in percentage";
             default "2";
             type union {
               type string {
                 pattern "<.*>|$.*";
               }
               type uint32 {
                 range "2 .. 100";
               }
             }
           }
           leaf used-threshold-upper-clear {
             description "Upper threshold clear in percentage";
             default "1";
             type union {
               type string {
                 pattern "<.*>|$.*";
               }
               type uint32 {
                 range "1 .. 99";
               }
             }
           }
         }
       }
     }
     container mode {
       description "Set FRU mode";
       uses apply-advanced;
       container standalone {
         presence "enable standalone";
         description "Bringup FRU in standalone mode1";
         uses apply-advanced;
         list fpc {
           key name;
           leaf name {
             description "FPC slot number";
             type string {
               length "1 .. 4";
             }
           }
           uses apply-advanced;
           container loopback {
             description "Loopback Configuration for Mode & Type";
             uses apply-advanced;
             leaf wan {
               default "serdes";
               type enumeration {
                 enum "serdes" {
                   description "Serdes type loopback";
                 }
                 enum "retimer" {
                   description "Retimer type loopback";
                 }
               }
             }
             leaf fabric {
               default "serdes";
               type enumeration {
                 enum "serdes" {
                   description "Serdes type loopback";
                 }
                 enum "retimer" {
                   description "Retimer type loopback";
                 }
               }
             }
           }
         }
         list fabric-card {
           key name;
           ordered-by user;
           description "Fabric Card Loopback setting";
           uses chassis_fabric_card_type;
         }
       }
       choice power-mode {
         case case_1 {
           leaf power-optimized {
             description "Set power mode to power-optimized";
             type empty;
           }
         }
       }
     }
     leaf local-station-mac {
       description "Local station mac address configuration";
       type jt:mac-unicast;
     }
     container system-domains {
       presence "enable system-domains";
       description "Root and protected system domain configuration";
       uses apply-advanced;
       leaf root-domain-id {
         description "Root domain identifier";
         type union {
           type string {
             pattern "<.*>|$.*";
           }
           type uint32 {
             range "1 .. 3";
           }
         }
       }
       list protected-system-domains {
         key name;
         description "Protected system domain configuration";
         uses juniper-protected-system-domain;
       }
       container traceoptions {
         description "Protected system domain traceoptions";
         uses juniper-protected-system-domain-traceoptions;
       }
     }
     container network-slices {
       presence "enable network-slices";
       description "Network slices configuration";
       uses apply-advanced;
       container guest-network-functions {
         presence "enable guest-network-functions";
         description "Guest network function configuration";
         uses apply-advanced;
         list gnf {
           key name;
           description "Guest network function";
           uses juniper-gnf;
         }
       }
       leaf vlan-isolation {
         description "Enable VLAN isolation for Control Plane";
         type empty;
       }
     }
     container cluster {
       description "Chassis cluster configuration";
       uses apply-advanced;
       container traceoptions {
         description "Set chassis cluster traceoptions";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             units "bytes";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "cli" {
                 description "Trace CLI events";
               }
               enum "configuration" {
                 description "Trace configuration events";
               }
               enum "eventlib" {
                 description "Trace event library events";
               }
               enum "fsm" {
                 description "Trace finite state machine events";
               }
               enum "heartbeat" {
                 description "Trace JSRPD heartbeats";
               }
               enum "interface" {
                 description "Trace interface related events";
               }
               enum "routing-socket" {
                 description "Trace routing socket events";
               }
               enum "uspipc" {
                 description "Trace USP IPC events";
               }
               enum "init" {
                 description "Trace initialization events";
               }
               enum "socket" {
                 description "Trace socket events";
               }
               enum "snmp" {
                 description "Trace snmp events";
               }
               enum "ip-monitoring" {
                 description "Trace IP monitoring events";
               }
               enum "hw-monitoring" {
                 description "Trace HW  monitoring events";
               }
               enum "fabric-monitoring" {
                 description "Trace fabric monitoring events";
               }
               enum "health-monitoring" {
                 description "Trace health monitoring events";
               }
               enum "schedule-monitoring" {
                 description "Trace schedule monitoring events";
               }
               enum "heartbeat-tlv" {
                 description "Trace TLV based heart-beat";
               }
               enum "ha-peer" {
                 description "Trace HA peer related info";
               }
               enum "srg" {
                 description "Trace HA srg related info";
               }
               enum "all" {
                 description "Trace all events";
               }
             }
           }
         }
         leaf level {
           description "Set level of tracing";
           default "info";
           type enumeration {
             enum "emergency" {
               description "Match emergency conditions";
             }
             enum "alert" {
               description "Match alert conditions";
             }
             enum "critical" {
               description "Match critical conditions";
             }
             enum "error" {
               description "Match error conditions";
             }
             enum "warning" {
               description "Match warning messages";
             }
             enum "notice" {
               description "Match notice level messages";
             }
             enum "info" {
               description "Match informational messages";
             }
             enum "debug" {
               description "Match debug messages";
             }
             enum "all" {
               description "Match all levels";
             }
           }
         }
       }
       leaf control-link-recovery {
         description "Enable automatic control link recovery";
         type empty;
       }
       leaf health-monitoring {
         description "Enable ha health monitoring";
         type empty;
       }
       leaf redundancy-mode {
         description "Redundancy mode for the cluster (Reboot all nodes simultaneously after change)";
         default "active-active";
         type enumeration {
           enum "active-active" {
             description "Primary and secondary nodes in active mode";
           }
           enum "active-backup" {
             description "Primary in active, secondary in backup mode";
           }
         }
       }
       leaf reth-count {
         description "Number of redundant ethernet interfaces";
         type union {
           type string {
             pattern "<.*>|$.*";
           }
           type uint16;
         }
       }
       container control-interface {
         description "Disable/enable HA control-link interface";
         uses apply-advanced;
         list node {
           key name;
           ordered-by user;
           description "Set node specific parameters";
           leaf name {
             description "Node identifier";
             type union {
               type string {
                 pattern "<.*>|$.*";
               }
               type uint32 {
                 range "0 .. 1";
               }
             }
           }
           leaf disable {
             description "Disable HA control interface";
             type empty;
           }
         }
       }
       list redundant-interface {
         key name;
         ordered-by user;
         description "Redundant peer configuration";
         max-elements 10;
         leaf name {
           description "Redundant backend L3 interface";
           type union {
             type jt:interface-device;
             type string {
               pattern "<.*>|$.*";
             }
           }
         }
         uses apply-advanced;
         leaf mapping-interface {
           description "Mapping interface to L3 redundant interface";
           type union {
             type jt:interface-device;
             type string {
               pattern "<.*>|$.*";
             }
           }
         }
       }
       list fabric-member {
         key name;
         ordered-by user;
         description "Fabric member interface configuration";
         leaf name {
           description "Fabric member interface";
           type union {
             type jt:interface-device;
             type string {
               pattern "<.*>|$.*";
             }
           }
         }
         uses apply-advanced;
         leaf vlan-id {
           description "VLAN ID for fabric member interface";
           type union {
             type string {
               pattern "<.*>|$.*";
             }
             type uint32 {
               range "1 .. 4094";
             }
           }
         }
         container virtual-interface {
           presence "enable virtual-interface";
           description "Name of the virtual mapped hsxe interface";
           uses apply-advanced;
           leaf virtual-interface-name {
             description "Name of the hsxe interface";
             type string {
               length "1 .. 5";
             }
           }
         }
       }
       list control-ports {
         key "fpc port";
         ordered-by user;
         description "Enable specific chassis cluster control ports";
         leaf fpc {
           description "FPC slot number";
           type union {
             type string {
               pattern "<.*>|$.*";
             }
             type uint32;
           }
         }
         leaf port {
           description "Port number";
           type union {
             type string {
               pattern "<.*>|$.*";
             }
             type uint32 {
               range "0 .. 2";
             }
           }
         }
       }
       list scb-control-ports {
         key name;
         ordered-by user;
         description "Enable specific chassis cluster SCB control ports";
         leaf name {
           description "Control Board number";
           type union {
             type string {
               pattern "<.*>|$.*";
             }
             type uint32 {
               range "0 .. 2";
             }
           }
         }
       }
       leaf heartbeat-interval {
         description "Interval between successive heartbeats";
         default "1000";
         units "milliseconds";
         type union {
           type string {
             pattern "<.*>|$.*";
           }
           type uint32;
         }
       }
       leaf heartbeat-threshold {
         description "Number of consecutive missed heartbeats to indicate device failure";
         default "3";
         type union {
           type string {
             pattern "<.*>|$.*";
           }
           type uint32;
         }
       }
       container network-management {
         description "Define parameters for network management";
         uses apply-advanced;
         leaf cluster-master {
           description "Enable in-band management on cluster-master";
           type empty;
         }
       }
       list node {
         key name;
         ordered-by user;
         description "Set the list of nodes in the cluster";
         status deprecated;
         leaf name {
           description "Node identifier";
           type enumeration {
             enum "0" {
               description "Node identifier 0";
             }
             enum "1" {
               description "Node identifier 1";
             }
           }
         }
         uses apply-advanced;
       }
       list redundancy-group {
         key name;
         ordered-by user;
         description "Set redundancy-group parameters";
         leaf name {
           description "Redundancy-group number";
           type union {
             type string {
               pattern "<.*>|$.*";
             }
             type uint8;
           }
         }
         uses apply-advanced;
         list node {
           key name;
           ordered-by user;
           description "Set node specific parameters";
           leaf name {
             description "Node identifier";
             type enumeration {
               enum "0" {
                 description "Node identifier 0";
               }
               enum "1" {
                 description "Node identifier 1";
               }
             }
           }
           leaf priority {
             description "Priority of the node in the redundancy-group";
             type union {
               type string {
                 pattern "<.*>|$.*";
               }
               type uint8 {
                 range "1 .. 254";
               }
             }
           }
         }
         container preempt {
           presence "enable preempt";
           description "Allow preemption of primaryship based on priority";
           uses apply-advanced;
           leaf delay {
             description "Time to wait before taking over mastership";
             units "seconds";
             type union {
               type string {
                 pattern "<.*>|$.*";
               }
               type uint16 {
                 range "1 .. 21600";
               }
             }
           }
           leaf limit {
             description "Max number of preemptive failovers allowed";
             type union {
               type string {
                 pattern "<.*>|$.*";
               }
               type uint16 {
                 range "1 .. 50";
               }
             }
           }
           leaf period {
             description "Time period during which the limit is applied";
             units "seconds";
             type union {
               type string {
                 pattern "<.*>|$.*";
               }
               type uint16 {
                 range "1 .. 1400";
               }
             }
           }
         }
         leaf gratuitous-arp-count {
           description "Number of gratuitous ARPs to send on an active interface after failover";
           type union {
             type string {
               pattern "<.*>|$.*";
             }
             type uint8 {
               range "1 .. 16";
             }
           }
         }
         leaf hold-down-interval {
           description "RG failover interval. RG0(300-1800) RG1+(0-1800)";
           units "seconds";
           type union {
             type string {
               pattern "<.*>|$.*";
             }
             type uint16 {
               range "0 .. 1800";
             }
           }
         }
         list interface-monitor {
           key name;
           ordered-by user;
           description "Define interfaces to monitor";
           leaf name {
             description "Name of the interface to monitor";
             type union {
               type jt:interface-device;
               type string {
                 pattern "<.*>|$.*";
               }
             }
           }
           leaf weight {
             description "Weight assigned to this interface that influences failover";
             type union {
               type string {
                 pattern "<.*>|$.*";
               }
               type uint16 {
                 range "0 .. 255";
               }
             }
           }
         }
         container ip-monitoring {
           description "Define parameters for IP monitoring feature";
           uses apply-advanced;
           leaf global-weight {
             description "Define global weight for IP monitoring";
             default "255";
             type union {
               type string {
                 pattern "<.*>|$.*";
               }
               type uint16 {
                 range "0 .. 255";
               }
             }
           }
           leaf global-threshold {
             description "Define global threshold for IP monitoring";
             default "0";
             type union {
               type string {
                 pattern "<.*>|$.*";
               }
               type uint16 {
                 range "0 .. 255";
               }
             }
           }
           leaf retry-interval {
             description "Define the time interval in seconds between retries.";
             default "1";
             type union {
               type string {
                 pattern "<.*>|$.*";
               }
               type uint16 {
                 range "1 .. 30";
               }
             }
           }
           leaf retry-count {
             description "Number of retries needed to declare reachablity failure";
             default "5";
             type union {
               type string {
                 pattern "<.*>|$.*";
               }
               type uint16 {
                 range "5 .. 15";
               }
             }
           }
           container family {
             description "Define protocol family";
             uses apply-advanced;
             container inet {
               description "Define IPv4 related parameters";
               uses apply-advanced;
               list address {
                 key name;
                 description "Define IP address related parameters";
                 uses ip-monitoring-address-type;
               }
             }
           }
         }
       }
       container configuration-synchronize {
         description "Cluster configuration action";
         uses apply-advanced;
         leaf no-secondary-bootup-auto {
           description "Disable auto configuration synchronize on secondary bootup";
           type empty;
         }
       }
       leaf use-actual-mac-on-physical-interfaces {
         description "Use Hypervisor provided MAC for physical interfaces on virtual platforms";
         type empty;
       }
       leaf use-active-child-mac-on-reth {
         description "Copy Child's physical MAC on RETH parent's current MAC";
         type empty;
       }
     }
     container high-availability {
       presence "enable high-availability";
       description "Enable High Availability mode";
       uses apply-advanced;
       leaf software-upgrade {
         description "Enable software upgrade state";
         type empty;
       }
       leaf hardware-upgrade {
         description "Enable hardware upgrade state";
         type empty;
       }
       container local-id {
         description "Local Identifier";
         uses apply-advanced;
         leaf id {
           description "Local identifier number";
           type union {
             type string {
               pattern "<.*>|$.*";
             }
             type uint8 {
               range "1 .. 10";
             }
           }
         }
         leaf local-ip {
           description "Local IPv4/IPv6 address";
           type jt:ipaddr;
         }
         container local-forwarding-ip {
           description "Local Forwarding ip";
           uses apply-advanced;
           leaf loopback-address {
             description "Local IPv4/IPv6 loopback address";
             type jt:ipaddr;
           }
         }
       }
       container local-domain-id {
         description "Local Domain Identifier";
         uses apply-advanced;
         leaf id {
           description "Local domain identifier number";
           type union {
             type string {
               pattern "<.*>|$.*";
             }
             type uint8 {
               range "1 .. 2";
             }
           }
         }
         leaf domain-size {
           description "Local domain size";
           default "2";
           type union {
             type string {
               pattern "<.*>|$.*";
             }
             type uint8 {
               range "1 .. 2";
             }
           }
         }
       }
       container grid-id {
         description "Grid Identifier";
         uses apply-advanced;
         leaf id {
           description "Grid identifier number";
           type union {
             type string {
               pattern "<.*>|$.*";
             }
             type uint8 {
               range "1 .. 15";
             }
           }
         }
       }
       list peer-id {
         key name;
         ordered-by user;
         description "Peer related information";
         leaf name {
           description "Peer Identifier";
           type union {
             type string {
               pattern "<.*>|$.*";
             }
             type uint8 {
               range "1 .. 10";
             }
           }
         }
         uses apply-advanced;
         leaf desc {
           description "Peer Description";
           type string {
             length "1 .. 255";
           }
         }
         leaf peer-ip {
           description "Peer IPv4/IPv6 address";
           type jt:ipaddr;
         }
         leaf interface {
           description "Name of the interface";
           type union {
             type jt:interface-name;
             type string {
               pattern "<.*>|$.*";
             }
           }
         }
         leaf routing-instance {
           description "Routing instance to locate the peer route";
           type string {
           }
         }
         leaf vpn-profile {
           description "VPN Profile name for HA link Encryption";
           type string {
             length "1 .. 255";
           }
         }
         container peer-forwarding-ip {
           description "Peer Forwarding ip";
           uses apply-advanced;
           leaf loopback-address {
             description "Peer IPv4/IPv6 loopback address";
             type jt:ipaddr;
           }
           leaf interface {
             description "Name of the interface";
             type union {
               type jt:interface-name;
               type string {
                 pattern "<.*>|$.*";
               }
             }
           }
           container liveness-detection {
             presence "enable liveness-detection";
             description "Bidirectional Forwarding IP Detection options for ICD link";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32;
               }
             }
             leaf minimum-transmit-interval {
               description "Minimum transmit interval";
               status deprecated;
               units "milliseconds";
               type union {
                 type string {
                   pattern "<.*>|$.*";
                 }
                 type uint32;
               }
             }
             leaf minimum-receive-interval {
               description "Minimum receive interval";
               units "milliseconds";
               type union {
                 type string {
                   pattern "<.*>|$.*";
                 }
                 type uint32;
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32;
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
           }
         }
         container liveness-detection {
           presence "enable liveness-detection";
           description "Bidirectional Forwarding Detection options for the peer";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32;
             }
           }
           leaf minimum-transmit-interval {
             description "Minimum transmit interval";
             status deprecated;
             units "milliseconds";
             type union {
               type string {
                 pattern "<.*>|$.*";
               }
               type uint32;
             }
           }
           leaf minimum-receive-interval {
             description "Minimum receive interval";
             units "milliseconds";
             type union {
               type string {
                 pattern "<.*>|$.*";
               }
               type uint32;
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32;
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
         }
       }
       list peer-domain-id {
         key name;
         ordered-by user;
         description "Peer domain related information";
         leaf name {
           description "Peer Domain Identifier";
           type union {
             type string {
               pattern "<.*>|$.*";
             }
             type uint8 {
               range "1 .. 2";
             }
           }
         }
         uses apply-advanced;
         leaf domain-size {
           description "Peer Domain Size";
           default "2";
           type union {
             type string {
               pattern "<.*>|$.*";
             }
             type uint8 {
               range "1 .. 2";
             }
           }
         }
         list peer-id {
           key name;
           ordered-by user;
           description "Peer domain peer node identifier";
           leaf name {
             description "Peer Node Identifier in Peer Domain";
             type union {
               type string {
                 pattern "<.*>|$.*";
               }
               type uint8 {
                 range "1 .. 10";
               }
             }
           }
           uses apply-advanced;
           leaf local-ip {
             description "IPv4/IPv6 address for Local node in Peer Domain";
             type jt:ipaddr;
           }
           leaf desc {
             description "Peer Description";
             type string {
               length "1 .. 255";
             }
           }
           leaf peer-ip {
             description "IPv4/IPv6 address for Peer node in Peer Domain";
             type jt:ipaddr;
           }
           leaf interface {
             description "Name of the interface beween local node and node in peer domain";
             type union {
               type jt:interface-name;
               type string {
                 pattern "<.*>|$.*";
               }
             }
           }
           leaf routing-instance {
             description "Routing instance to locate the peer route";
             type string {
             }
           }
           leaf vpn-profile {
             description "VPN Profile name for HA link Encryption";
             type string {
               length "1 .. 255";
             }
           }
           container liveness-detection {
             presence "enable liveness-detection";
             description "Bidirectional Forwarding Detection options for the peer";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32;
               }
             }
             leaf minimum-transmit-interval {
               description "Minimum transmit interval";
               status deprecated;
               units "milliseconds";
               type union {
                 type string {
                   pattern "<.*>|$.*";
                 }
                 type uint32;
               }
             }
             leaf minimum-receive-interval {
               description "Minimum receive interval";
               units "milliseconds";
               type union {
                 type string {
                   pattern "<.*>|$.*";
                 }
                 type uint32;
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32;
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
           }
         }
       }
       container traceoptions {
         description "Set chassis l3-ha traceoptions";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             units "bytes";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "cli" {
                 description "Trace CLI events";
               }
               enum "configuration" {
                 description "Trace configuration events";
               }
               enum "eventlib" {
                 description "Trace event library events";
               }
               enum "fsm" {
                 description "Trace finite state machine events";
               }
               enum "heartbeat" {
                 description "Trace JSRPD heartbeats";
               }
               enum "interface" {
                 description "Trace interface related events";
               }
               enum "routing-socket" {
                 description "Trace routing socket events";
               }
               enum "uspipc" {
                 description "Trace USP IPC events";
               }
               enum "init" {
                 description "Trace initialization events";
               }
               enum "socket" {
                 description "Trace socket events";
               }
               enum "snmp" {
                 description "Trace snmp events";
               }
               enum "ip-monitoring" {
                 description "Trace IP monitoring events";
               }
               enum "hw-monitoring" {
                 description "Trace HW  monitoring events";
               }
               enum "fabric-monitoring" {
                 description "Trace fabric monitoring events";
               }
               enum "health-monitoring" {
                 description "Trace health monitoring events";
               }
               enum "schedule-monitoring" {
                 description "Trace schedule monitoring events";
               }
               enum "heartbeat-tlv" {
                 description "Trace TLV based heart-beat";
               }
               enum "ha-peer" {
                 description "Trace HA peer related info";
               }
               enum "srg" {
                 description "Trace HA srg related info";
               }
               enum "all" {
                 description "Trace all events";
               }
             }
           }
         }
         leaf level {
           description "Set level of tracing";
           default "info";
           type enumeration {
             enum "emergency" {
               description "Match emergency conditions";
             }
             enum "alert" {
               description "Match alert conditions";
             }
             enum "critical" {
               description "Match critical conditions";
             }
             enum "error" {
               description "Match error conditions";
             }
             enum "warning" {
               description "Match warning messages";
             }
             enum "notice" {
               description "Match notice level messages";
             }
             enum "info" {
               description "Match informational messages";
             }
             enum "debug" {
               description "Match debug messages";
             }
             enum "all" {
               description "Match all levels";
             }
           }
         }
       }
       list services-redundancy-group {
         key name;
         ordered-by user;
         description "Define the services level failover domain";
         leaf name {
           description "Services redundancy group identifier";
           type union {
             type string {
               pattern "<.*>|$.*";
             }
             type uint8 {
               range "0 .. 20";
             }
           }
         }
         uses apply-advanced;
         list peer-domain-id {
           key name;
           ordered-by user;
           description "Peer domain related information";
           leaf name {
             description "Peer Domain Identifier";
             type union {
               type string {
                 pattern "<.*>|$.*";
               }
               type uint8 {
                 range "1 .. 2";
               }
             }
           }
           uses apply-advanced;
           list peer-id {
             key name;
             ordered-by user;
             description "Peer domain peer node identifier";
             leaf name {
               description "Peer Node Identifier in Peer Domain";
               type union {
                 type string {
                   pattern "<.*>|$.*";
                 }
                 type uint8 {
                   range "1 .. 10";
                 }
               }
             }
             uses apply-advanced;
             leaf priority {
               description "Priority of the node in the services-redundancy-group";
               type union {
                 type string {
                   pattern "<.*>|$.*";
                 }
                 type uint8 {
                   range "1 .. 254";
                 }
               }
             }
           }
         }
         list shutdown-on-failure {
           key name;
           ordered-by user;
           description "Interfaces to be shut down in case of internal failures";
           leaf name {
             description "Name of the interface";
             type union {
               type jt:interface-device;
               type string {
                 pattern "<.*>|$.*";
               }
             }
           }
           uses apply-advanced;
         }
         leaf deployment-type {
           description "Deployment type of the Services Redundancy Group";
           default "routing";
           type enumeration {
             enum "cloud" {
               description "Cloud deployment";
             }
             enum "hybrid" {
               description "Hybrid deployment";
             }
             enum "routing" {
               description "Routing deployment";
             }
             enum "switching" {
               description "Switching deployment";
             }
           }
         }
         container peer-id {
           presence "enable peer-id";
           description "Peer related information";
           uses apply-advanced;
           leaf id {
             description "Peer Identifier";
             type union {
               type string {
                 pattern "<.*>|$.*";
               }
               type uint8 {
                 range "1 .. 10";
               }
             }
           }
         }
         list interface {
           key name;
           ordered-by user;
           description "Name of the interface for virtual mac";
           leaf name {
             description "Name of the interface for Virtual Mac Id";
             type string;
           }
           uses apply-advanced;
           leaf virtual-mac-id {
             description "Virtual Mac Identifier";
             type union {
               type string {
                 pattern "<.*>|$.*";
               }
               type uint8 {
                 range "0 .. 15";
               }
             }
           }
         }
         container activeness-probe {
           description "The probe destination IP for activeness determination";
           uses apply-advanced;
           container dest-ip {
             description "Destination IPV4/IPV6 address";
             uses apply-advanced;
             leaf ip-address {
               description "Destination IPV4/IPV6 address";
               type jt:ipaddr;
             }
             leaf src-ip {
               description "Source IPV4/IPV6 address for activeness probe";
               type jt:ipaddr;
             }
             leaf routing-instance {
               description "Routing instance";
               type string {
               }
             }
           }
           leaf minimum-interval {
             description "Define the time interval in milliseconds between activeness probing retries.";
             type union {
               type string {
                 pattern "<.*>|$.*";
               }
               type uint32 {
                 range 1000;
               }
             }
           }
           leaf multiplier {
             description "Number of retries needed to declare activeness probing failure";
             type union {
               type string {
                 pattern "<.*>|$.*";
               }
               type uint8 {
                 range "2 .. 15";
               }
             }
           }
           container bfd-liveliness {
             description "Configure BFD monitoring";
             uses apply-advanced;
             leaf source-ip {
               description "Source IPV4/IPV6 address for BFD monitoring";
               type jt:ipaddr;
             }
             leaf destination-ip {
               description "Destination IPV4/IPV6 address for BFD monitoring";
               type jt:ipaddr;
             }
             leaf interface {
               description "Name of the interface for single-hop sessions";
               type union {
                 type jt:interface-name;
                 type string {
                   pattern "<.*>|$.*";
                 }
               }
             }
             leaf routing-instance {
               description "Routing instance to locate the route";
               type string {
               }
             }
             leaf minimum-interval {
               description "Minimum transmit and receive interval";
               units "milliseconds";
               type union {
                 type string {
                   pattern "<.*>|$.*";
                 }
                 type uint32;
               }
             }
             leaf multiplier {
               description "Detection time multiplier";
               type union {
                 type string {
                   pattern "<.*>|$.*";
                 }
                 type uint32 {
                   range "1 .. 255";
                 }
               }
             }
           }
         }
         list virtual-ip {
           key name;
           ordered-by user;
           description "HA virtual IP ";
           leaf name {
             description "Virtual IP Identifier";
             type union {
               type string {
                 pattern "<.*>|$.*";
               }
               type uint16 {
                 range "1 .. 2000";
               }
             }
           }
           uses apply-advanced;
           list ip {
             key name;
             ordered-by user;
             description "Define a named set of address prefixes";
             leaf name {
               description "IPV4/IPV6 prefix, should be in the same subnet as the interface IP";
               type jt:ipprefix-mandatory;
             }
             uses apply-advanced;
           }
           leaf interface {
             description "Name of the interface";
             type union {
               type jt:interface-name;
               type string {
                 pattern "<.*>|$.*";
               }
             }
           }
           leaf use-virtual-mac {
             description "Use virtual mac for SRG role enforcement";
             type empty;
           }
         }
         container monitor {
           description "Configure the BFD and IP monitoring";
           uses apply-advanced;
           list ip {
             key name;
             ordered-by user;
             description "Destination IPV4/IPV6 address for monitoring";
             leaf name {
               description "Destination IPV4/IPV6 address";
               type jt:ipaddr;
             }
             uses apply-advanced;
             leaf routing-instance {
               description "Routing instance to locate the destination route";
               type string {
               }
             }
           }
           list bfd-liveliness {
             key name;
             ordered-by user;
             description "Configure BFD monitoring";
             leaf name {
               description "Destination IPV4/IPV6 address for BFD monitoring";
               type jt:ipaddr;
             }
             uses apply-advanced;
             leaf src-ip {
               description "Source IPV4/IPV6 address for BFD monitoring";
               type jt:ipaddr;
             }
             leaf routing-instance {
               description "Routing instance to locate the route";
               type string {
               }
             }
             leaf session-type {
               description "BFD Mon Session Type";
               type enumeration {
                 enum "singlehop" {
                   description "Single hop";
                 }
                 enum "multihop" {
                   description "Multihop";
                 }
               }
             }
             leaf interface {
               description "Name of the interface for single-hop sessions";
               type union {
                 type jt:interface-name;
                 type string {
                   pattern "<.*>|$.*";
                 }
               }
             }
           }
           list interface {
             key name;
             ordered-by user;
             description "Define interfaces to monitor";
             leaf name {
               description "Name of the interface to monitor";
               type union {
                 type jt:interface-device;
                 type string {
                   pattern "<.*>|$.*";
                 }
               }
             }
             uses apply-advanced;
           }
           list monitor-object {
             key name;
             ordered-by user;
             description "SRG monitoring object";
             leaf name {
               description "SRG monitoring object name 1..32 characters";
               type string {
               }
             }
             uses apply-advanced;
             leaf object-threshold {
               description "SRG monitoring object threshold value";
               type union {
                 type string {
                   pattern "<.*>|$.*";
                 }
                 type uint32 {
                   range "1 .. 1000";
                 }
               }
             }
             container ip {
               presence "enable ip";
               description "Configure IP monitoring";
               uses apply-advanced;
               leaf threshold {
                 description "SRG monitoring object ip monitoring threshold value";
                 type union {
                   type string {
                     pattern "<.*>|$.*";
                   }
                   type uint32 {
                     range "1 .. 1000";
                   }
                 }
               }
               list destination-ip {
                 key name;
                 ordered-by user;
                 description "Destination IPV4/IPV6 address for monitoring";
                 leaf name {
                   description "Destination IPV4/IPV6 address";
                   type jt:ipaddr;
                 }
                 uses apply-advanced;
                 leaf routing-instance {
                   description "Routing instance to locate the destination route";
                   type string {
                   }
                 }
                 leaf weight {
                   description "SRG monitoring object ip monitoring entry weight";
                   type union {
                     type string {
                       pattern "<.*>|$.*";
                     }
                     type uint32 {
                       range "1 .. 1000";
                     }
                   }
                 }
               }
             }
             container bfd-liveliness {
               presence "enable bfd-liveliness";
               description "Configure BFD monitoring";
               uses apply-advanced;
               leaf threshold {
                 description "SRG monitoring object BFD monitoring threshold value";
                 type union {
                   type string {
                     pattern "<.*>|$.*";
                   }
                   type uint32 {
                     range "1 .. 1000";
                   }
                 }
               }
               list destination-ip {
                 key name;
                 ordered-by user;
                 description "Destination IPV4/IPV6 address for monitoring";
                 leaf name {
                   description "Destination IPV4/IPV6 address for BFD monitoring";
                   type jt:ipaddr;
                 }
                 uses apply-advanced;
                 leaf src-ip {
                   description "Source IPV4/IPV6 address for BFD monitoring";
                   type jt:ipaddr;
                 }
                 leaf routing-instance {
                   description "Routing instance to locate the route";
                   type string {
                   }
                 }
                 leaf session-type {
                   description "BFD Mon Session Type";
                   type enumeration {
                     enum "singlehop" {
                       description "Single hop";
                     }
                     enum "multihop" {
                       description "Multihop";
                     }
                   }
                 }
                 leaf interface {
                   description "Name of the interface for single-hop sessions";
                   type union {
                     type jt:interface-name;
                     type string {
                       pattern "<.*>|$.*";
                     }
                   }
                 }
                 leaf weight {
                   description "SRG monitoring object bfd monitoring entry weight";
                   type union {
                     type string {
                       pattern "<.*>|$.*";
                     }
                     type uint32 {
                       range "1 .. 1000";
                     }
                   }
                 }
               }
             }
             container interface {
               presence "enable interface";
               description "Define interfaces to monitor";
               uses apply-advanced;
               leaf threshold {
                 description "SRG monitoring object interface monitoring threshold value";
                 type union {
                   type string {
                     pattern "<.*>|$.*";
                   }
                   type uint32 {
                     range "1 .. 1000";
                   }
                 }
               }
               list interface-name {
                 key name;
                 ordered-by user;
                 description "Destination IPV4/IPV6 address for monitoring";
                 leaf name {
                   description "Name of the interface to monitor";
                   type union {
                     type jt:interface-device;
                     type string {
                       pattern "<.*>|$.*";
                     }
                   }
                 }
                 uses apply-advanced;
                 leaf weight {
                   description "SRG monitoring object interface monitoring entry weight";
                   type union {
                     type string {
                       pattern "<.*>|$.*";
                     }
                     type uint32 {
                       range "1 .. 1000";
                     }
                   }
                 }
               }
             }
           }
           leaf srg-threshold {
             description "SRG monitoring threshold value";
             type union {
               type string {
                 pattern "<.*>|$.*";
               }
               type uint32 {
                 range "1 .. 1000";
               }
             }
           }
         }
         container active-signal-route {
           description "Configure the active signal route";
           uses apply-advanced;
           leaf ip-address {
             description "Active IPv4 address";
             type jt:ipv4addr;
           }
           leaf routing-instance {
             description "Routing instance to install the active signal route";
             type string {
             }
           }
           container inet6 {
             description "IPv6 configuration for active signal route";
             uses apply-advanced;
             leaf ipv6-address {
               description "Active IPv6 address";
               type jt:ipv6addr;
             }
             leaf routing-instance {
               description "Routing instance to install the active signal route";
               type string {
               }
             }
           }
         }
         container backup-signal-route {
           description "Configure the backup signal route";
           uses apply-advanced;
           leaf ip-address {
             description "Backup IPv4 address";
             type jt:ipv4addr;
           }
           leaf routing-instance {
             description "Routing instance to install the backup signal route";
             type string {
             }
           }
           container inet6 {
             description "IPv6 configuration for backup signal route";
             uses apply-advanced;
             leaf ipv6-address {
               description "Backup IPv6 address";
               type jt:ipv6addr;
             }
             leaf routing-instance {
               description "Routing instance to install the backup signal route";
               type string {
               }
             }
           }
         }
         container install-on-failure-route {
           description "Configure the signal route to install upon failure";
           uses apply-advanced;
           leaf ip-address {
             description "Install on failure IPv4 address";
             type jt:ipv4addr;
           }
           leaf routing-instance {
             description "Routing instance to install the failure signal route";
             type string {
             }
           }
           container inet6 {
             description "IPv6 configuration for install-on-failure route";
             uses apply-advanced;
             leaf ipv6-address {
               description "Install on failure IPv6 address";
               type jt:ipv6addr;
             }
             leaf routing-instance {
               description "Routing instance to install the failure signal route";
               type string {
               }
             }
           }
         }
         list prefix-list {
           key name;
           ordered-by user;
           description "Define a named set of address prefixes";
           leaf name {
             description "Prefix list name";
             type string;
           }
           uses apply-advanced;
           leaf routing-instance {
             description "Routing instance";
             type string {
             }
           }
         }
         list managed-services {
           key name;
           description "Define a named set of services to be applicable for this SRG";
           leaf name {
             type enumeration {
               enum "ipsec" {
                 description "IPsec VPN Service";
               }
             }
           }
         }
         leaf preemption {
           description "Allow preemption of activeness based on priority";
           type empty;
         }
         leaf process-packet-on-backup {
           description "Enable PFE to process packets on backup node";
           type empty;
         }
         leaf activeness-priority {
           description "Activeness Priority of the node for this SRG";
           type union {
             type string {
               pattern "<.*>|$.*";
             }
             type uint8 {
               range "1 .. 254";
             }
           }
         }
       }
     }
     list node {
       key name;
       description "Set node specific parameters";
       leaf name {
         description "Node identifier";
         type union {
           type string {
             pattern "<.*>|$.*";
           }
           type uint32 {
             range "0 .. 1";
           }
         }
       }
       uses apply-advanced;
       list fpc {
         key name;
         description "Flexible PIC Concentrator parameters";
         uses chassis_fpc_type;
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping chassis-pw-type {
     uses apply-advanced;
     leaf device-count {
       description "Number of pseudo-wire ps devices";
       type union {
         type string {
           pattern "<.*>|$.*";
         }
         type uint32 {
           range "1 .. 18000";
         }
       }
     }
   }
   grouping chassis_ae_lb_type {
     uses apply-advanced;
     leaf disable {
       description "Disable Multicast load balancing";
       type empty;
     }
     leaf hash-mode {
       description "PFE hash mode";
       type enumeration {
         enum "crc-sgip" {
           description "CRC of Source IP and Group IP";
         }
         enum "crc-gip" {
           description "CRC of Group IP only";
         }
         enum "crc-sip" {
           description "CRC of Source IP only";
         }
         enum "simple-sgip" {
           description "Simple hash of Source IP and Group IP";
         }
         enum "simple-gip" {
           description "Simple hash of Group IP";
         }
         enum "simple-sip" {
           description "Simple hash of Source IP";
         }
         enum "balanced" {
           description "Round-Robin balancing";
         }
       }
     }
   }
   grouping chassis_agg_dev_type {
     uses apply-advanced;
     leaf ae-20 {
       description "Run AE over Container nexthops Infrastructure";
       status deprecated;
       type empty;
     }
     container ethernet {
       description "Aggregated device options for Ethernet";
       uses chassisd_agg_enet_type;
     }
     container sonet {
       description "Aggregated device options for SONET";
       uses chassisd_agg_pos_type;
     }
     leaf maximum-links {
       description "Maximum links limit for aggregated devices";
       type union {
         type int32;
         type string {
           pattern "<.*>|$.*";
         }
       }
     }
   }
   grouping chassis_alarm_port_op_type {
     uses apply-advanced;
     container input {
       description "Input alarm port";
       uses apply-advanced;
       list port {
         key name;
         ordered-by user;
         description "Input Port";
         leaf name {
           description "Alarm port ID";
           type union {
             type string {
               pattern "<.*>|$.*";
             }
             type uint32 {
               range "1 .. 3";
             }
           }
         }
         uses apply-advanced;
         leaf active {
           description "Active signal of alarm IO input port";
           type enumeration {
             enum "low" {
               description "Active signal of alarm IO port to low(default)";
             }
             enum "high" {
               description "Active signal of alarm IO port to high";
             }
           }
         }
         leaf admin-state {
           description "Administrative state of alarm IO input port";
           type enumeration {
             enum "disabled" {
               description "Administrative state of alarm IO port to disable(default)";
             }
             enum "enabled" {
               description "Administrative state of alarm IO port to enabled";
             }
           }
         }
         container description {
           description "Alarm description of alarm IO input port";
           uses apply-advanced;
           leaf descr {
             description "Description to be used for alarm IO output port";
             type string;
           }
         }
         leaf severity {
           description "Set alarm severity of alarm IO input port";
           type enumeration {
             enum "critical" {
               description "Alarm severity of alarm IO input port to ciritical(default)";
             }
             enum "major" {
               description "Alarm severity of alarm IO input port to major";
             }
             enum "minor" {
               description "Alarm severity of alarm IO input port to minor";
             }
             enum "warning" {
               description "Alarm severity of alarm IO input port to warning";
             }
           }
         }
       }
     }
     container output {
       description "Output alarm port";
       uses apply-advanced;
       list port {
         key name;
         ordered-by user;
         description "Output port";
         leaf name {
           description "Alarm IO output port ID";
           type union {
             type string {
               pattern "<.*>|$.*";
             }
             type uint32 {
               range 1;
             }
           }
         }
         uses apply-advanced;
         leaf admin-state {
           description "Administrative state of alarm IO output port";
           type enumeration {
             enum "disabled" {
               description "Administrative state of alarm IO port to disable(default)";
             }
             enum "enabled" {
               description "Administrative state of alarm IO port to enabled";
             }
           }
         }
         container description {
           description "Alarm description of alarm IO output port";
           uses apply-advanced;
           leaf descr {
             description "Description to be used for alarm IO output port";
             type string;
           }
         }
       }
     }
   }
   grouping chassis_alarm_type {
     uses apply-advanced;
     container management-ethernet {
       description "Management Ethernet alarms";
       uses chassis_alarm_ethernet_type;
     }
     container otn-odu {
       description "OTN ODU alarms";
       uses chassis_alarm_otn_odu_type;
     }
     container otn-otu {
       description "OTN OTU alarms";
       uses chassis_alarm_otn_otu_type;
     }
     container sonet {
       description "SONET alarms";
       uses chassis_alarm_sonet_type;
     }
     container t3 {
       description "DS3 alarms";
       uses chassis_alarm_ds3_type;
     }
     container ds1 {
       description "DS1 alarms";
       uses chassis_alarm_ds1_type;
     }
     container ethernet {
       description "Ethernet alarms";
       uses chassis_alarm_ethernet_type;
     }
     container l2-chan-err-ethernet {
       description "L2 channel error ethernet alarms";
       uses chassis_alarm_l2_chan_err_type;
     }
     container integrated-services {
       description "Integrated services alarms";
       uses chassis_alarm_integrated_services_type;
     }
     container services {
       description "Services PIC alarms";
       uses chassis_alarm_services_type;
     }
     container serial {
       description "Serial alarms";
       uses chassis_alarm_serial_type;
     }
     container fibre-channel {
       description "Fibre Channel alarms";
       uses chassis_alarm_fibre-channel_type;
     }
     leaf pem-absence {
       description "Power supply module absence";
       type enumeration {
         enum "ignore" {
           description "Ignore the power supply module absence alarm";
         }
       }
     }
     container relay {
       description "Alarm relays";
       uses chassis_alarm_relay_type;
     }
     list psm {
       key name;
       description "Alarm for psm input feed";
       leaf name {
         description "PSM slot number";
         type union {
           type string {
             pattern "<.*>|$.*";
           }
           type uint32;
         }
       }
       uses apply-advanced;
       container input1 {
         uses apply-advanced;
         leaf ignore {
           description "Ignore input1 alarm of Power Supply Module";
           type empty;
         }
       }
       container input2 {
         uses apply-advanced;
         leaf ignore {
           description "Ignore input2 alarm of Power Supply Module";
           type empty;
         }
       }
     }
     container fru-absence {
       description "FRU module absence";
       uses apply-advanced;
       container ignore {
         description "Ignore the power supply module absence alarm";
         uses apply-advanced;
         list fpc {
           key name;
           ordered-by user;
           description "FPC Slot Number";
           uses chassis_fpc_type_slot;
         }
       }
     }
     leaf ignore-fan-speed-check {
       description "Ignore the Fan speed check alarms";
       type empty;
     }
   }
   grouping chassis_alarm_ds1_type {
     uses apply-advanced;
     leaf ais {
       description "Alarm indicator signal";
       type enumeration {
         enum "red" {
           description "Assert red system alarm";
         }
         enum "yellow" {
           description "Assert yellow system alarm";
         }
         enum "ignore" {
           description "Do not assert any alarm signals";
         }
       }
     }
     leaf ylw {
       description "Yellow alarm";
       type enumeration {
         enum "red" {
           description "Assert red system alarm";
         }
         enum "yellow" {
           description "Assert yellow system alarm";
         }
         enum "ignore" {
           description "Do not assert any alarm signals";
         }
       }
     }
   }
   grouping chassis_alarm_ds3_type {
     uses apply-advanced;
     leaf ais {
       description "Alarm indicator signal";
       type enumeration {
         enum "red" {
           description "Assert red system alarm";
         }
         enum "yellow" {
           description "Assert yellow system alarm";
         }
         enum "ignore" {
           description "Do not assert any alarm signals";
         }
       }
     }
     leaf exz {
       description "Excessive zeros";
       type enumeration {
         enum "red" {
           description "Assert red system alarm";
         }
         enum "yellow" {
           description "Assert yellow system alarm";
         }
         enum "ignore" {
           description "Do not assert any alarm signals";
         }
       }
     }
     leaf ferf {
       description "Far-end failure";
       type enumeration {
         enum "red" {
           description "Assert red system alarm";
         }
         enum "yellow" {
           description "Assert yellow system alarm";
         }
         enum "ignore" {
           description "Do not assert any alarm signals";
         }
       }
     }
     leaf idle {
       description "Idle alarm";
       type enumeration {
         enum "red" {
           description "Assert red system alarm";
         }
         enum "yellow" {
           description "Assert yellow system alarm";
         }
         enum "ignore" {
           description "Do not assert any alarm signals";
         }
       }
     }
     leaf lcv {
       description "Line code violation";
       type enumeration {
         enum "red" {
           description "Assert red system alarm";
         }
         enum "yellow" {
           description "Assert yellow system alarm";
         }
         enum "ignore" {
           description "Do not assert any alarm signals";
         }
       }
     }
     leaf lof {
       description "Loss of frame";
       type enumeration {
         enum "red" {
           description "Assert red system alarm";
         }
         enum "yellow" {
           description "Assert yellow system alarm";
         }
         enum "ignore" {
           description "Do not assert any alarm signals";
         }
       }
     }
     leaf los {
       description "Loss of signal";
       type enumeration {
         enum "red" {
           description "Assert red system alarm";
         }
         enum "yellow" {
           description "Assert yellow system alarm";
         }
         enum "ignore" {
           description "Do not assert any alarm signals";
         }
       }
     }
     leaf pll {
       description "Phase-locked loop out of lock";
       type enumeration {
         enum "red" {
           description "Assert red system alarm";
         }
         enum "yellow" {
           description "Assert yellow system alarm";
         }
         enum "ignore" {
           description "Do not assert any alarm signals";
         }
       }
     }
     leaf ylw {
       description "Yellow alarm";
       type enumeration {
         enum "red" {
           description "Assert red system alarm";
         }
         enum "yellow" {
           description "Assert yellow system alarm";
         }
         enum "ignore" {
           description "Do not assert any alarm signals";
         }
       }
     }
   }
   grouping chassis_alarm_ethernet_type {
     uses apply-advanced;
     leaf link-down {
       description "Link has gone down";
       type enumeration {
         enum "red" {
           description "Assert red system alarm";
         }
         enum "yellow" {
           description "Assert yellow system alarm";
         }
         enum "ignore" {
           description "Do not assert any alarm signals";
         }
       }
     }
   }
   grouping chassis_alarm_fibre-channel_type {
     uses apply-advanced;
     leaf link-down {
       description "Link has gone down";
       type enumeration {
         enum "red" {
           description "Assert red system alarm";
         }
         enum "yellow" {
           description "Assert yellow system alarm";
         }
         enum "ignore" {
           description "Do not assert any alarm signals";
         }
       }
     }
   }
   grouping chassis_alarm_integrated_services_type {
     uses apply-advanced;
     leaf failure {
       description "Integrated Services failure";
       type enumeration {
         enum "red" {
           description "Assert red system alarm";
         }
         enum "yellow" {
           description "Assert yellow system alarm";
         }
         enum "ignore" {
           description "Do not assert any alarm signals";
         }
       }
     }
   }
   grouping chassis_alarm_l2_chan_err_type {
     uses apply-advanced;
     leaf l2-channel-errors {
       description "Received L2 channel error";
       type enumeration {
         enum "red" {
           description "Assert red system alarm";
         }
         enum "yellow" {
           description "Assert yellow system alarm";
         }
         enum "ignore" {
           description "Do not assert any alarm signals";
         }
       }
     }
     leaf l2-channel-error-threshold {
       description "L2 channel error threshold - 50,000 as default";
       type union {
         type string {
           pattern "<.*>|$.*";
         }
         type uint32 {
           range "1 .. 4294967295";
         }
       }
     }
   }
   grouping chassis_alarm_otn_odu_type {
     uses apply-advanced;
     leaf odu-bdi {
       description "ODU backward-defect-indicator, ODU-BDI failure";
       type enumeration {
         enum "red" {
           description "Assert red system alarm";
         }
         enum "yellow" {
           description "Assert yellow system alarm";
         }
         enum "ignore" {
           description "Do not assert any alarm signals";
         }
       }
     }
     leaf odu-ttim {
       description "ODU trail-trace-identifier-mismatch, ODU-TTIM failure";
       type enumeration {
         enum "red" {
           description "Assert red system alarm";
         }
         enum "yellow" {
           description "Assert yellow system alarm";
         }
         enum "ignore" {
           description "Do not assert any alarm signals";
         }
       }
     }
     leaf odu-ptim {
       description "ODU payload-type-mismatch, ODU-PTIM failure";
       type enumeration {
         enum "red" {
           description "Assert red system alarm";
         }
         enum "yellow" {
           description "Assert yellow system alarm";
         }
         enum "ignore" {
           description "Do not assert any alarm signals";
         }
       }
     }
   }
   grouping chassis_alarm_otn_otu_type {
     uses apply-advanced;
     leaf oc-los {
       description "Loss of signal, LOS failure";
       type enumeration {
         enum "red" {
           description "Assert red system alarm";
         }
         enum "yellow" {
           description "Assert yellow system alarm";
         }
         enum "ignore" {
           description "Do not assert any alarm signals";
         }
       }
     }
     leaf oc-lof {
       description "Loss of framing, LOF failure";
       type enumeration {
         enum "red" {
           description "Assert red system alarm";
         }
         enum "yellow" {
           description "Assert yellow system alarm";
         }
         enum "ignore" {
           description "Do not assert any alarm signals";
         }
       }
     }
     leaf oc-lom {
       description "Loss of multiframe, LOM failure";
       type enumeration {
         enum "red" {
           description "Assert red system alarm";
         }
         enum "yellow" {
           description "Assert yellow system alarm";
         }
         enum "ignore" {
           description "Do not assert any alarm signals";
         }
       }
     }
     leaf wavelength-lock {
       description "Wavelength lock alarm";
       type enumeration {
         enum "red" {
           description "Assert red system alarm";
         }
         enum "yellow" {
           description "Assert yellow system alarm";
         }
         enum "ignore" {
           description "Do not assert any alarm signals";
         }
       }
     }
     leaf otu-bdi {
       description "OTU backward-defect-indicator, OTU-BDI failure";
       type enumeration {
         enum "red" {
           description "Assert red system alarm";
         }
         enum "yellow" {
           description "Assert yellow system alarm";
         }
         enum "ignore" {
           description "Do not assert any alarm signals";
         }
       }
     }
     leaf otu-iae {
       description "OTU incoming-alignment-error, OTU-IAE failure";
       type enumeration {
         enum "red" {
           description "Assert red system alarm";
         }
         enum "yellow" {
           description "Assert yellow system alarm";
         }
         enum "ignore" {
           description "Do not assert any alarm signals";
         }
       }
     }
     leaf otu-ttim {
       description "OTU trail-trace-identifier-mismatch, OTU-TTIM failure";
       type enumeration {
         enum "red" {
           description "Assert red system alarm";
         }
         enum "yellow" {
           description "Assert yellow system alarm";
         }
         enum "ignore" {
           description "Do not assert any alarm signals";
         }
       }
     }
     leaf otu-fec-excessive-errs {
       description "OTU fec-excessive-errors, OTU-FEC_EXE failure";
       type enumeration {
         enum "red" {
           description "Assert red system alarm";
         }
         enum "yellow" {
           description "Assert yellow system alarm";
         }
         enum "ignore" {
           description "Do not assert any alarm signals";
         }
       }
     }
   }
   grouping chassis_alarm_relay_type {
     uses apply-advanced;
     container input {
       description "Input relays";
       uses apply-advanced;
       list port {
         key name;
         ordered-by user;
         leaf name {
           description "Relay port number";
           type union {
             type string {
               pattern "<.*>|$.*";
             }
             type uint32 {
               range "0 .. 3";
             }
           }
         }
         uses apply-advanced;
         leaf mode {
           description "Relay mode in de-active state";
           type enumeration {
             enum "open" {
               description "Normally open";
             }
             enum "close" {
               description "Normally closed";
             }
           }
         }
         leaf trigger {
           description "Relay triggered";
           type enumeration {
             enum "red" {
               description "Assert red system alarm";
             }
             enum "yellow" {
               description "Assert yellow system alarm";
             }
             enum "ignore" {
               description "Do not assert any alarm signals";
             }
           }
         }
       }
     }
     container output {
       description "Output relays";
       uses apply-advanced;
       list port {
         key name;
         ordered-by user;
         leaf name {
           description "Relay port number";
           type union {
             type string {
               pattern "<.*>|$.*";
             }
             type uint32 {
               range "0 .. 3";
             }
           }
         }
         uses apply-advanced;
         leaf mode {
           description "Relay mode in de-active state";
           type enumeration {
             enum "open" {
               description "Normally open";
             }
             enum "close" {
               description "Normally closed";
             }
           }
         }
         leaf temperature {
           description "Trigger on temperature alarm red";
           type empty;
         }
         leaf input-relay {
           description "Trigger on input relay trigger";
           type union {
             type string {
               pattern "<.*>|$.*";
             }
             type uint32 {
               range "0 .. 3";
             }
           }
         }
       }
     }
   }
   grouping chassis_alarm_serial_type {
     uses apply-advanced;
     leaf loss-of-rx-clock {
       description "RX clock absent";
       type enumeration {
         enum "red" {
           description "Assert red system alarm";
         }
         enum "yellow" {
           description "Assert yellow system alarm";
         }
         enum "ignore" {
           description "Do not assert any alarm signals";
         }
       }
     }
     leaf loss-of-tx-clock {
       description "TX clock absent";
       type enumeration {
         enum "red" {
           description "Assert red system alarm";
         }
         enum "yellow" {
           description "Assert yellow system alarm";
         }
         enum "ignore" {
           description "Do not assert any alarm signals";
         }
       }
     }
     leaf dcd-absent {
       description "DCD signal absent";
       type enumeration {
         enum "red" {
           description "Assert red system alarm";
         }
         enum "yellow" {
           description "Assert yellow system alarm";
         }
         enum "ignore" {
           description "Do not assert any alarm signals";
         }
       }
     }
     leaf cts-absent {
       description "CTS signal absent";
       type enumeration {
         enum "red" {
           description "Assert red system alarm";
         }
         enum "yellow" {
           description "Assert yellow system alarm";
         }
         enum "ignore" {
           description "Do not assert any alarm signals";
         }
       }
     }
     leaf dsr-absent {
       description "DSR signal absent";
       type enumeration {
         enum "red" {
           description "Assert red system alarm";
         }
         enum "yellow" {
           description "Assert yellow system alarm";
         }
         enum "ignore" {
           description "Do not assert any alarm signals";
         }
       }
     }
     leaf tm-absent {
       description "TM signal absent";
       type enumeration {
         enum "red" {
           description "Assert red system alarm";
         }
         enum "yellow" {
           description "Assert yellow system alarm";
         }
         enum "ignore" {
           description "Do not assert any alarm signals";
         }
       }
     }
   }
   grouping chassis_alarm_services_type {
     uses apply-advanced;
     leaf pic-reset {
       description "Services PIC reset";
       type enumeration {
         enum "red" {
           description "Assert red system alarm";
         }
         enum "yellow" {
           description "Assert yellow system alarm";
         }
         enum "ignore" {
           description "Do not assert any alarm signals";
         }
       }
     }
     leaf pic-hold-reset {
       description "Services PIC held in reset";
       type enumeration {
         enum "red" {
           description "Assert red system alarm";
         }
         enum "yellow" {
           description "Assert yellow system alarm";
         }
         enum "ignore" {
           description "Do not assert any alarm signals";
         }
       }
     }
     leaf linkdown {
       description "Services PIC linkdown";
       type enumeration {
         enum "red" {
           description "Assert red system alarm";
         }
         enum "yellow" {
           description "Assert yellow system alarm";
         }
         enum "ignore" {
           description "Do not assert any alarm signals";
         }
       }
     }
     leaf rx-errors {
       description "Services PIC excessive rx errors";
       type enumeration {
         enum "red" {
           description "Assert red system alarm";
         }
         enum "yellow" {
           description "Assert yellow system alarm";
         }
         enum "ignore" {
           description "Do not assert any alarm signals";
         }
       }
     }
     leaf tx-errors {
       description "Services PIC excessive tx errors";
       type enumeration {
         enum "red" {
           description "Assert red system alarm";
         }
         enum "yellow" {
           description "Assert yellow system alarm";
         }
         enum "ignore" {
           description "Do not assert any alarm signals";
         }
       }
     }
     leaf sw-down {
       description "Services PIC software problem";
       type enumeration {
         enum "red" {
           description "Assert red system alarm";
         }
         enum "yellow" {
           description "Assert yellow system alarm";
         }
         enum "ignore" {
           description "Do not assert any alarm signals";
         }
       }
     }
     leaf hw-down {
       description "Services PIC hardware problem";
       type enumeration {
         enum "red" {
           description "Assert red system alarm";
         }
         enum "yellow" {
           description "Assert yellow system alarm";
         }
         enum "ignore" {
           description "Do not assert any alarm signals";
         }
       }
     }
   }
   grouping chassis_alarm_sonet_type {
     uses apply-advanced;
     leaf lol {
       description "Loss of light";
       type enumeration {
         enum "red" {
           description "Assert red system alarm";
         }
         enum "yellow" {
           description "Assert yellow system alarm";
         }
         enum "ignore" {
           description "Do not assert any alarm signals";
         }
       }
     }
     leaf pll {
       description "Phase locked loop out of lock";
       type enumeration {
         enum "red" {
           description "Assert red system alarm";
         }
         enum "yellow" {
           description "Assert yellow system alarm";
         }
         enum "ignore" {
           description "Do not assert any alarm signals";
         }
       }
     }
     leaf lof {
       description "Loss of framing, LOF failure";
       type enumeration {
         enum "red" {
           description "Assert red system alarm";
         }
         enum "yellow" {
           description "Assert yellow system alarm";
         }
         enum "ignore" {
           description "Do not assert any alarm signals";
         }
       }
     }
     leaf los {
       description "Loss of signal, LOS failure";
       type enumeration {
         enum "red" {
           description "Assert red system alarm";
         }
         enum "yellow" {
           description "Assert yellow system alarm";
         }
         enum "ignore" {
           description "Do not assert any alarm signals";
         }
       }
     }
     leaf ais-l {
       description "Line alarm indication signal, AIS-L failure";
       type enumeration {
         enum "red" {
           description "Assert red system alarm";
         }
         enum "yellow" {
           description "Assert yellow system alarm";
         }
         enum "ignore" {
           description "Do not assert any alarm signals";
         }
       }
     }
     leaf ais-p {
       description "Path alarm indication signal, AIS-P failure";
       type enumeration {
         enum "red" {
           description "Assert red system alarm";
         }
         enum "yellow" {
           description "Assert yellow system alarm";
         }
         enum "ignore" {
           description "Do not assert any alarm signals";
         }
       }
     }
     leaf lop-p {
       description "Loss of pointer, LOP-P failure";
       type enumeration {
         enum "red" {
           description "Assert red system alarm";
         }
         enum "yellow" {
           description "Assert yellow system alarm";
         }
         enum "ignore" {
           description "Do not assert any alarm signals";
         }
       }
     }
     leaf ber-sd {
       description "Signal Degrade (SD), bit error rate > 1E-6";
       type enumeration {
         enum "red" {
           description "Assert red system alarm";
         }
         enum "yellow" {
           description "Assert yellow system alarm";
         }
         enum "ignore" {
           description "Do not assert any alarm signals";
         }
       }
     }
     leaf ber-sf {
       description "Signal Fail (SF), bit error rate > 1E-3";
       type enumeration {
         enum "red" {
           description "Assert red system alarm";
         }
         enum "yellow" {
           description "Assert yellow system alarm";
         }
         enum "ignore" {
           description "Do not assert any alarm signals";
         }
       }
     }
     leaf rfi-l {
       description "Line remote failure indication, RFI-L, line FERF";
       type enumeration {
         enum "red" {
           description "Assert red system alarm";
         }
         enum "yellow" {
           description "Assert yellow system alarm";
         }
         enum "ignore" {
           description "Do not assert any alarm signals";
         }
       }
     }
     leaf rfi-p {
       description "Path remote failure indication, RFI-P, STS path yellow";
       type enumeration {
         enum "red" {
           description "Assert red system alarm";
         }
         enum "yellow" {
           description "Assert yellow system alarm";
         }
         enum "ignore" {
           description "Do not assert any alarm signals";
         }
       }
     }
     leaf uneq-p {
       description "STS Path (C2) unequipped, UNEQ-P failure";
       type enumeration {
         enum "red" {
           description "Assert red system alarm";
         }
         enum "yellow" {
           description "Assert yellow system alarm";
         }
         enum "ignore" {
           description "Do not assert any alarm signals";
         }
       }
     }
     leaf locd {
       description "Loss of cell delineation (ATM only)";
       type enumeration {
         enum "red" {
           description "Assert red system alarm";
         }
         enum "yellow" {
           description "Assert yellow system alarm";
         }
         enum "ignore" {
           description "Do not assert any alarm signals";
         }
       }
     }
     leaf plm-p {
       description "STS payload label (C2) mismatch, PLM-P failure";
       type enumeration {
         enum "red" {
           description "Assert red system alarm";
         }
         enum "yellow" {
           description "Assert yellow system alarm";
         }
         enum "ignore" {
           description "Do not assert any alarm signals";
         }
       }
     }
   }
   grouping chassis_cb_type {
     leaf name {
       description "CB slot number";
       type union {
         type string {
           pattern "<.*>|$.*";
         }
         type uint32;
       }
     }
     uses apply-advanced;
     container temperature-threshold {
       description "CB temperature thresholds";
       uses chassis-temperature-threshold-type;
     }
     list temperature-sensor {
       key name;
       description "CB temperature sensor";
       uses chassis-temperature-sensor-type;
     }
   }
   grouping chassis-temperature-sensor-type {
     leaf name {
       description "Temperature sensor name";
       type string;
     }
     uses apply-advanced;
     container temperature-threshold {
       description "Temperature thresholds";
       uses chassis-temperature-threshold-type;
     }
   }
   grouping chassis-temperature-threshold-type {
     description "Chassis temperature thresholds";
     uses apply-advanced;
     leaf fans-to-normal-speed {
       description "Threshold at which fans return to normal speed";
       units "degrees C";
       type union {
         type uint32;
         type string {
           pattern "<.*>|$.*";
         }
       }
     }
     leaf fans-on-intermediate-speed {
       description "Threshold at which fans run intermediate speed";
       units "degrees C";
       type union {
         type uint32;
         type string {
           pattern "<.*>|$.*";
         }
       }
     }
     leaf fans-on-full-speed {
       description "Threshold at which fans run full speed";
       units "degrees C";
       type union {
         type uint32;
         type string {
           pattern "<.*>|$.*";
         }
       }
     }
     leaf fans-on-full-speed-if-failed-fan {
       description "Threshold at which fans run full speed when bad fan present";
       units "degrees C";
       type union {
         type uint32;
         type string {
           pattern "<.*>|$.*";
         }
       }
     }
     leaf yellow-alarm {
       description "Threshold at which yellow alarm is set";
       units "degrees C";
       type union {
         type uint32;
         type string {
           pattern "<.*>|$.*";
         }
       }
     }
     leaf yellow-alarm-if-failed-fan {
       description "Threshold at which yellow alarm is set when bad fan present";
       units "degrees C";
       type union {
         type uint32;
         type string {
           pattern "<.*>|$.*";
         }
       }
     }
     leaf red-alarm {
       description "Threshold at which red alarm is set";
       units "degrees C";
       type union {
         type uint32;
         type string {
           pattern "<.*>|$.*";
         }
       }
     }
     leaf red-alarm-if-failed-fan {
       description "Threshold at which red alarm is set when bad fan present";
       units "degrees C";
       type union {
         type uint32;
         type string {
           pattern "<.*>|$.*";
         }
       }
     }
     leaf fire-shutdown {
       description "Threshold at which router will be shutdown within 10 seconds";
       units "degrees C";
       type union {
         type uint32;
         type string {
           pattern "<.*>|$.*";
         }
       }
     }
   }
   grouping chassis_fabric_card_type {
     leaf name {
       description "Fabric Card slot number";
       type string {
         length "1 .. 5";
       }
     }
     uses apply-advanced;
     container loopback {
       description "Loopback Configuration for Mode & Type";
       uses apply-advanced;
       leaf serdes {
         description "Fabric Card serdes setting";
         type empty;
       }
       leaf retimer {
         description "Fabric card retimer setting";
         type empty;
       }
     }
   }
   grouping chassis_fabric_cards_type {
     uses apply-advanced;
     leaf reset-count {
       description "Number of times sib can be reset by cmerror";
       type union {
         type string {
           pattern "<.*>|$.*";
         }
         type uint32 {
           range "1 .. 10";
         }
       }
     }
   }
   grouping chassis_fabric_type {
     uses apply-advanced;
     leaf upgrade-mode {
       description "Enable online switch fabric upgrade";
       type enumeration {
         enum "default" {
           description "Fabric upgrade";
         }
         enum "t4000" {
           description "T4000 Fabric upgrade";
         }
         enum "3d-fabric" {
           description "TXP-3D Fabric upgrade";
         }
       }
     }
     container event {
       description "Fabric events";
       uses apply-advanced;
       container link-failure {
         presence "enable link-failure";
         description "Fabric link failure";
         uses apply-advanced;
         container action {
           presence "enable action";
           description "Fabric action to be taken";
           uses apply-advanced;
         }
       }
       container reachability-fault {
         presence "enable reachability-fault";
         description "Fabric reachability fault detection";
         uses apply-advanced;
         container degraded {
           presence "enable degraded";
           description "Degraded fabric configuration";
           uses apply-advanced;
           container error-threshold {
             presence "enable error-threshold";
             description "Fabric error threshold for degraded case";
             uses apply-advanced;
             container degradation {
               presence "enable degradation";
               description "Degradation attributes";
               uses apply-advanced;
               leaf percentage {
                 description "The percentage degradation on which action is taken";
                 type union {
                   type string {
                     pattern "<.*>|$.*";
                   }
                   type uint32 {
                     range "1 .. 99";
                   }
                 }
               }
             }
           }
         }
         container actions {
           description "Reachability fault actions";
           uses apply-advanced;
           leaf fpc-restart-disable {
             description "Disable fpc restart action for FHP";
             type empty;
           }
           container recovery-failure {
             description "Recovery failure action to be taken for FHP";
             uses apply-advanced;
             leaf pfe-offline {
               description "Proceed with PFE offline action for FHP";
               type empty;
             }
           }
         }
       }
     }
     container oam {
       description "Fabric OAM configuration";
       uses apply-advanced;
       leaf detection-disable {
         description "Disable fabric OAM";
         type empty;
       }
       leaf runtime-disable {
         description "Disable runtime fabric OAM";
         type empty;
       }
     }
     container degraded {
       presence "enable degraded";
       description "Degraded fabric configuration";
       uses apply-advanced;
       leaf action-fpc-restart-disable {
         description "Limit degraded fabric actions to Plane restart only";
         type empty;
       }
       leaf degraded-fpc-bad-plane-threshold {
         description "No of bad planes to declare a FPC degraded";
         default "4";
         type union {
           type string {
             pattern "<.*>|$.*";
           }
           type uint32 {
             range "4 .. 18";
           }
         }
       }
       leaf degraded-fabric-detection-enable {
         description "Enable degraded FPC detection";
         type empty;
       }
       leaf fpc-restart {
         description "Restart fpc on zero planes";
         type empty;
       }
       leaf auto-recovery-disable {
         description "Disable fabric degraded auto recovery";
         type empty;
       }
       leaf fpc-offline-on-blackholing {
         description "Offline FPC on fabric blackholing";
         type empty;
       }
     }
     container redundancy-mode {
       description "Fabric redundancy mode";
       uses apply-advanced;
       choice mode {
         case case_1 {
           leaf redundant {
             description "Fabric is configured in redundant mode";
             type empty;
           }
         }
         case case_2 {
           leaf increased-bandwidth {
             description "Fabric is configured in increased bandwidth mode";
             type empty;
           }
         }
       }
     }
     leaf disable-grant-bypass {
       description "Disable fabric grant-bypass mode";
       type empty;
     }
   }
   grouping chassis_feb_type {
     uses apply-advanced;
     container sanity-poll {
       description "FPC register sanity poll";
       uses apply-advanced;
       leaf retry-count {
         description "Number of retries before reporting error";
         default "10";
         type union {
           type string {
             pattern "<.*>|$.*";
           }
           type uint32 {
             range "1 .. 30";
           }
         }
       }
       container on-error {
         description "Actions to be taken if inconsistencies are detected";
         uses apply-advanced;
         leaf raise-alarm {
           description "Raise emergency alarm";
           type empty;
         }
         leaf power {
           description "Power cycle or power off FPC";
           type enumeration {
             enum "cycle" {
               description "Write coredump and reboot FPC";
             }
             enum "off" {
               description "Power down FPC indefinitely";
             }
           }
         }
         leaf write-coredump {
           description "Write coredump and continue";
           type empty;
         }
       }
     }
     list slot {
       key name;
       ordered-by user;
       leaf name {
         description "FEB slot number";
         type union {
           type string {
             pattern "<.*>|$.*";
           }
           type uint32;
         }
       }
       uses apply-advanced;
       container sanity-poll {
         description "FPC register sanity poll";
         uses apply-advanced;
         leaf retry-count {
           description "Number of retries before reporting error";
           default "10";
           type union {
             type string {
               pattern "<.*>|$.*";
             }
             type uint32 {
               range "1 .. 30";
             }
           }
         }
         container on-error {
           description "Actions to be taken if inconsistencies are detected";
           uses apply-advanced;
           leaf raise-alarm {
             description "Raise emergency alarm";
             type empty;
           }
           leaf power {
             description "Power cycle or power off FPC";
             type enumeration {
               enum "cycle" {
                 description "Write coredump and reboot FPC";
               }
               enum "off" {
                 description "Power down FPC indefinitely";
               }
             }
           }
           leaf write-coredump {
             description "Write coredump and continue";
             type empty;
           }
         }
       }
       leaf power {
         description "Power FEBs on or off";
         type enumeration {
           enum "off" {
             description "Do not provide power to FEBs";
           }
           enum "on" {
             description "Provide power to FEBs";
           }
         }
       }
       choice mode {
       }
       leaf port-mirror-instance {
         description "Associate a port mirroring instance with the FEB";
         type string {
           length "1 .. 64";
         }
       }
       leaf sampling-instance {
         description "Associate a sampling instance with the FEB";
         type string {
           length "1 .. 64";
         }
       }
       leaf ucode-imem-remap {
         description "Remap the PIC microcode to IMEM on FEB";
         type empty;
       }
       container inline-services {
         uses apply-advanced;
         leaf report-zero-oif-gw-on-discard {
           description "Jflow reports value zero in OIF and GW when traffic is not forwarded";
           type empty;
         }
         leaf flex-flow-sizing {
           description "No fixed size allocation of flow tables for proto families";
           type empty;
         }
         leaf use-extended-flow-memory {
           description "Use extended memory for flow records";
           type empty;
         }
         container flow-table-size {
           uses apply-advanced;
           leaf ipv4-flow-table-size {
             description "IPv4 flow table size in units of 256k";
             type union {
               type string {
                 pattern "<.*>|$.*";
               }
               type uint32 {
                 range "1 .. 245";
               }
             }
           }
           leaf ipv6-flow-table-size {
             description "IPv6 flow table size in units of 256k";
             type union {
               type string {
                 pattern "<.*>|$.*";
               }
               type uint32 {
                 range "1 .. 245";
               }
             }
           }
           leaf vpls-flow-table-size {
             description "VPLS flow table size in units of 256k";
             type union {
               type string {
                 pattern "<.*>|$.*";
               }
               type uint32 {
                 range "1 .. 245";
               }
             }
           }
           leaf bridge-flow-table-size {
             description "BRIDGE flow table size in units of 256k";
             type union {
               type string {
                 pattern "<.*>|$.*";
               }
               type uint32 {
                 range "1 .. 245";
               }
             }
           }
           leaf ipv6-extended-attrib {
             description "Enable extended flow attribute";
             type empty;
           }
           leaf mpls-flow-table-size {
             description "MPLS flow table size in units of 256k";
             type union {
               type string {
                 pattern "<.*>|$.*";
               }
               type uint32 {
                 range "1 .. 245";
               }
             }
           }
         }
       }
       container inline-video-monitoring {
         uses apply-advanced;
         leaf maximum-flows-count {
           description "Maximum number of inline video monitoring flows per PFE instance";
           type union {
             type string {
               pattern "<.*>|$.*";
             }
             type uint32 {
               range "16 .. 8192";
             }
           }
         }
       }
       container error {
         description "Error level configuration for FEB";
         uses chassis_junos_fru_error_type;
       }
       list pfe {
         key name;
         description "Packet forwarding engine parameters";
         uses chassis_pfe_type;
       }
       container openflow {
         description "Openflow configuration";
         uses apply-advanced;
         leaf access-list-partition {
           description "Space reserved for openflow access-list rules";
           units "percents";
           type union {
             type string {
               pattern "<.*>|$.*";
             }
             type uint32 {
               range "0 .. 100";
             }
           }
         }
       }
     }
   }
   grouping chassis_fpc_type {
     leaf name {
       description "FPC slot number";
       type union {
         type string {
           pattern "<.*>|$.*";
         }
         type uint32;
       }
     }
     uses apply-advanced;
     container auto-speed-detection {
       description "Disables auto-speed detection";
       uses apply-advanced;
       choice auto-speed-detections {
         case case_1 {
           leaf disable {
             description "Disables automatic speed detection";
             type empty;
           }
         }
       }
     }
     container linkscan-per-fpc {
       presence "enable linkscan-per-fpc";
       description "Configure linkscan per FPC";
       uses apply-advanced;
       leaf fpc-linkscan-interval {
         description " setting linkscan interval of FPC in microsecond";
         type union {
           type string {
             pattern "<.*>|$.*";
           }
           type uint32 {
             range "10000 .. 500000";
           }
         }
       }
       leaf software-based {
         description "Override linkscan mode to software based";
         type empty;
       }
     }
     container ukern-trace {
       description "Set ukern trace";
       uses apply-advanced;
       container log {
         description "Set ukern-trace log";
         uses apply-advanced;
         leaf app-type {
           description "Name of application with ukern-trace logs";
           type enumeration {
             enum "dfw" {
               description "All dfw ukern-trace logs";
             }
           }
         }
         leaf logging {
           description "Enable or Disable ukern-trace logging of an app-type";
           type enumeration {
             enum "off" {
               description "Disable logging";
             }
             enum "on" {
               description "Enable logging";
             }
           }
         }
       }
     }
     container sanity-poll {
       description "FPC register sanity poll";
       uses apply-advanced;
       leaf retry-count {
         description "Number of retries before reporting error";
         default "10";
         type union {
           type string {
             pattern "<.*>|$.*";
           }
           type uint32 {
             range "1 .. 30";
           }
         }
       }
       container on-error {
         description "Actions to be taken if inconsistencies are detected";
         uses apply-advanced;
         leaf raise-alarm {
           description "Raise emergency alarm";
           type empty;
         }
         leaf power {
           description "Power cycle or power off FPC";
           type enumeration {
             enum "cycle" {
               description "Write coredump and reboot FPC";
             }
             enum "off" {
               description "Power down FPC indefinitely";
             }
           }
         }
         leaf write-coredump {
           description "Write coredump and continue";
           type empty;
         }
       }
     }
     container forwarding-options {
       description "Configure options to control packet forwarding";
       uses apply-advanced;
       choice uft_object {
         case case_1 {
           container l2-profile-one {
             presence "enable l2-profile-one";
             description "MAC: 288K L3-host: 16K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_2 {
           container l2-profile-two {
             presence "enable l2-profile-two";
             description "MAC: 224K L3-host: 80K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_3 {
           container l2-profile-three {
             presence "enable l2-profile-three";
             description "(default) MAC: 160K L3-host: 144K LPM: 16K, needs reboot for VC;restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_4 {
           container l3-profile {
             presence "enable l3-profile";
             description "MAC: 96K L3-host: 208K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_5 {
           container lpm-profile {
             presence "enable lpm-profile";
             description "MAC: 32K L3-host: 16K LPM: 128K EM:0, needs reboot for VC; restarts PFE if standalone";
             uses apply-advanced;
             leaf prefix-65-127-disable {
               description "Disable IPV6 prefixes with length > 64";
               type empty;
             }
             leaf unicast-in-lpm {
               description "Install unicast host entries in LPM table";
               type empty;
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_6 {
           container exact-match-profile {
             presence "enable exact-match-profile";
             description "MAC: 8K L3-host: 8K LPM: 16K EM: 64K, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_7 {
           container vxlan-gbp-profile {
             presence "enable vxlan-gbp-profile";
             description "MAC: 48K L3-host: 48K LPM: 16K EM:16K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_8 {
           container vxlan-gbp-l2-profile {
             presence "enable vxlan-gbp-l2-profile";
             description "MAC: 64K L3-host: 32K LPM: 16K EM:16K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_9 {
           container vxlan-gbp-l3-profile {
             presence "enable vxlan-gbp-l3-profile";
             description "MAC: 32K L3-host: 64K LPM: 16K EM:16K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_10 {
           container vxlan-gbp-mc-profile {
             presence "enable vxlan-gbp-mc-profile";
             description "MAC: 32K L3-host: 64K LPM: 16K EM:16K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_11 {
           container em-hw-profile {
             presence "enable em-hw-profile";
             description "MAC: 48K L3-host: 48K LPM: 16K EM:32K, needs reboot for VC; restarts PFE if standalone";
           }
         }
         case case_12 {
           container gbp-pure-l2-profile {
             presence "enable gbp-pure-l2-profile";
             description "MAC: 48K L3-host: 48K LPM: 16K EM:16K, needs reboot for VC; restarts PFE if standalone";
           }
         }
         case case_13 {
           container default-profile {
             presence "enable default-profile";
             description "MAC: 64K L3-host: 32K LPM: 24K IFP: 12K, needs reboot for VC; restarts PFE if standalone";
           }
         }
         case case_14 {
           container ifp-profile {
             presence "enable ifp-profile";
             description "MAC: 64K L3-host: 32K LPM: 12K IFP: 18K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_15 {
           container custom-profile {
             description "(Partition the shared banks, will automatically restart the PFE when configured)";
             uses apply-advanced;
             container l2-entries {
               description "Customize l2 entries needed";
               uses apply-advanced;
               leaf num-banks {
                 description "Number of banks needed for entries of this type";
                 default "0";
                 type union {
                   type string {
                     pattern "<.*>|$.*";
                   }
                   type int32 {
                     range "0 .. 4";
                   }
                 }
               }
             }
             container l3-entries {
               description "Customize l3 entries needed";
               uses apply-advanced;
               leaf num-banks {
                 description "Number of banks needed for entries of this type";
                 default "0";
                 type union {
                   type string {
                     pattern "<.*>|$.*";
                   }
                   type int32 {
                     range "0 .. 4";
                   }
                 }
               }
             }
             container exact-match-entries {
               description "Customize exact match entries needed";
               uses apply-advanced;
               leaf num-banks {
                 description "Number of banks needed for entries of this type";
                 default "0";
                 type union {
                   type string {
                     pattern "<.*>|$.*";
                   }
                   type int32 {
                     range "0 .. 4";
                   }
                 }
               }
             }
             container lpm-entries {
               description "Customize lpm banks needed";
               uses apply-advanced;
               leaf num-banks {
                 description "Number of banks needed for entries of this type";
                 default "0";
                 type enumeration {
                   enum "0" {
                   }
                   enum "2" {
                   }
                   enum "4" {
                   }
                 }
               }
               leaf prefix-65-127-disable {
                 description "Disable IPV6 prefixes with length > 64";
                 type empty;
               }
             }
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
       }
     }
     list pic {
       key name;
       description "Physical Interface Card number";
       uses chassis_pic_type;
     }
     list mic {
       key name;
       description "Modular Interface Card number";
       uses chassis_mic_type;
     }
     container optical-options {
       description "Integrated Photonic Line Card settings";
       uses apply-advanced;
       choice disable-edfa-choice {
         leaf disable-edfa {
           description "Disable both EDFA";
           type empty;
         }
         leaf no-disable-edfa {
           description "Don't disable both EDFA";
           type empty;
         }
       }
       choice disable-osc-choice {
         leaf disable-osc {
           description "Disable OSC";
           type empty;
         }
         leaf no-disable-osc {
           description "Don't disable OSC";
           type empty;
         }
       }
       list wavelength {
         key name;
         description "Wavelength Selective Switch";
         leaf name {
           description "Wavelength of the WSS channel for 50Ghz/100Ghz spacing";
           type enumeration {
             enum "1611.79" {
               description "1611.79 nm/186.000000 THz 3.125/6.25/12.5/50/75/100GHz spacing";
             }
             enum "1611.76" {
               description "1611.76 nm/186.003125 THz 3.125GHz spacing";
             }
             enum "1611.73" {
               description "1611.73 nm/186.006250 THz 3.125/6.25GHz spacing";
             }
             enum "1611.71" {
               description "1611.71 nm/186.009375 THz 3.125GHz spacing";
             }
             enum "1611.68" {
               description "1611.68 nm/186.012500 THz 3.125/6.25/12.5GHz spacing";
             }
             enum "1611.65" {
               description "1611.65 nm/186.015625 THz 3.125GHz spacing";
             }
             enum "1611.62" {
               description "1611.62 nm/186.018750 THz 3.125/6.25GHz spacing";
             }
             enum "1611.60" {
               description "1611.60 nm/186.021875 THz 3.125GHz spacing";
             }
             enum "1611.57" {
               description "1611.57 nm/186.025000 THz 3.125/6.25/12.5GHz spacing";
             }
             enum "1611.54" {
               description "1611.54 nm/186.028125 THz 3.125GHz spacing";
             }
             enum "1611.52" {
               description "1611.52 nm/186.031250 THz 3.125/6.25GHz spacing";
             }
             enum "1611.49" {
               description "1611.49 nm/186.034375 THz 3.125GHz spacing";
             }
             enum "1611.46" {
               description "1611.46 nm/186.037500 THz 3.125/6.25/12.5GHz spacing";
             }
             enum "1611.44" {
               description "1611.44 nm/186.040625 THz 3.125GHz spacing";
             }
             enum "1611.41" {
               description "1611.41 nm/186.043750 THz 3.125/6.25GHz spacing";
             }
             enum "1611.38" {
               description "1611.38 nm/186.046875 THz 3.125GHz spacing";
             }
             enum "1611.35" {
               description "1611.35 nm/186.050000 THz 3.125/6.25/12.5/50/75GHz spacing";
             }
             enum "1611.33" {
               description "1611.33 nm/186.053125 THz 3.125GHz spacing";
             }
             enum "1611.30" {
               description "1611.30 nm/186.056250 THz 3.125/6.25GHz spacing";
             }
             enum "1611.27" {
               description "1611.27 nm/186.059375 THz 3.125GHz spacing";
             }
             enum "1611.25" {
               description "1611.25 nm/186.062500 THz 3.125/6.25/12.5GHz spacing";
             }
             enum "1611.22" {
               description "1611.22 nm/186.065625 THz 3.125GHz spacing";
             }
             enum "1611.19" {
               description "1611.19 nm/186.068750 THz 3.125/6.25GHz spacing";
             }
             enum "1611.16" {
               description "1611.16 nm/186.071875 THz 3.125GHz spacing";
             }
             enum "1611.14" {
               description "1611.14 nm/186.075000 THz 3.125/6.25/12.5GHz spacing";
             }
             enum "1611.11" {
               description "1611.11 nm/186.078125 THz 3.125GHz spacing";
             }
             enum "1611.08" {
               description "1611.08 nm/186.081250 THz 3.125/6.25GHz spacing";
             }
             enum "1611.06" {
               description "1611.06 nm/186.084375 THz 3.125GHz spacing";
             }
             enum "1611.03" {
               description "1611.03 nm/186.087500 THz 3.125/6.25/12.5GHz spacing";
             }
             enum "1611.00" {
               description "1611.00 nm/186.090625 THz 3.125GHz spacing";
             }
             enum "1610.98" {
               description "1610.98 nm/186.093750 THz 3.125/6.25GHz spacing";
             }
             enum "1610.95" {
               description "1610.95 nm/186.096875 THz 3.125GHz spacing";
             }
             enum "1610.92" {
               description "1610.92 nm/186.100000 THz 3.125/6.25/12.5/100GHz spacing";
             }
             enum "1610.89" {
               description "1610.89 nm/186.103125 THz 3.125GHz spacing";
             }
             enum "1610.87" {
               description "1610.87 nm/186.106250 THz 3.125/6.25GHz spacing";
             }
             enum "1610.84" {
               description "1610.84 nm/186.109375 THz 3.125GHz spacing";
             }
             enum "1610.81" {
               description "1610.81 nm/186.112500 THz 3.125/6.25/12.5GHz spacing";
             }
             enum "1610.79" {
               description "1610.79 nm/186.115625 THz 3.125GHz spacing";
             }
             enum "1610.76" {
               description "1610.76 nm/186.118750 THz 3.125/6.25GHz spacing";
             }
             enum "1610.73" {
               description "1610.73 nm/186.121875 THz 3.125GHz spacing";
             }
             enum "1610.70" {
               description "1610.70 nm/186.125000 THz 3.125/6.25/12.5/75GHz spacing";
             }
             enum "1610.68" {
               description "1610.68 nm/186.128125 THz 3.125GHz spacing";
             }
             enum "1610.65" {
               description "1610.65 nm/186.131250 THz 3.125/6.25GHz spacing";
             }
             enum "1610.62" {
               description "1610.62 nm/186.134375 THz 3.125GHz spacing";
             }
             enum "1610.60" {
               description "1610.60 nm/186.137500 THz 3.125/6.25/12.5GHz spacing";
             }
             enum "1610.57" {
               description "1610.57 nm/186.140625 THz 3.125GHz spacing";
             }
             enum "1610.54" {
               description "1610.54 nm/186.143750 THz 3.125/6.25GHz spacing";
             }
             enum "1610.52" {
               description "1610.52 nm/186.146875 THz 3.125GHz spacing";
             }
             enum "1610.49" {
               description "1610.49 nm/186.150000 THz 3.125/6.25/12.5/50GHz spacing";
             }
             enum "1610.46" {
               description "1610.46 nm/186.153125 THz 3.125GHz spacing";
             }
             enum "1610.43" {
               description "1610.43 nm/186.156250 THz 3.125/6.25GHz spacing";
             }
             enum "1610.41" {
               description "1610.41 nm/186.159375 THz 3.125GHz spacing";
             }
             enum "1610.38" {
               description "1610.38 nm/186.162500 THz 3.125/6.25/12.5GHz spacing";
             }
             enum "1610.35" {
               description "1610.35 nm/186.165625 THz 3.125GHz spacing";
             }
             enum "1610.33" {
               description "1610.33 nm/186.168750 THz 3.125/6.25GHz spacing";
             }
             enum "1610.30" {
               description "1610.30 nm/186.171875 THz 3.125GHz spacing";
             }
             enum "1610.27" {
               description "1610.27 nm/186.175000 THz 3.125/6.25/12.5GHz spacing";
             }
             enum "1610.25" {
               description "1610.25 nm/186.178125 THz 3.125GHz spacing";
             }
             enum "1610.22" {
               description "1610.22 nm/186.181250 THz 3.125/6.25GHz spacing";
             }
             enum "1610.19" {
               description "1610.19 nm/186.184375 THz 3.125GHz spacing";
             }
             enum "1610.16" {
               description "1610.16 nm/186.187500 THz 3.125/6.25/12.5GHz spacing";
             }
             enum "1610.14" {
               description "1610.14 nm/186.190625 THz 3.125GHz spacing";
             }
             enum "1610.11" {
               description "1610.11 nm/186.193750 THz 3.125/6.25GHz spacing";
             }
             enum "1610.08" {
               description "1610.08 nm/186.196875 THz 3.125GHz spacing";
             }
             enum "1610.06" {
               description "1610.06 nm/186.200000 THz 3.125/6.25/12.5/100GHz spacing";
             }
             enum "1610.03" {
               description "1610.03 nm/186.203125 THz 3.125GHz spacing";
             }
             enum "1610.00" {
               description "1610.00 nm/186.206250 THz 3.125/6.25GHz spacing";
             }
             enum "1609.98" {
               description "1609.98 nm/186.209375 THz 3.125GHz spacing";
             }
             enum "1609.95" {
               description "1609.95 nm/186.212500 THz 3.125/6.25/12.5GHz spacing";
             }
             enum "1609.92" {
               description "1609.92 nm/186.215625 THz 3.125GHz spacing";
             }
             enum "1609.89" {
               description "1609.89 nm/186.218750 THz 3.125/6.25GHz spacing";
             }
             enum "1609.87" {
               description "1609.87 nm/186.221875 THz 3.125GHz spacing";
             }
             enum "1609.84" {
               description "1609.84 nm/186.225000 THz 3.125/6.25/12.5GHz spacing";
             }
             enum "1609.81" {
               description "1609.81 nm/186.228125 THz 3.125GHz spacing";
             }
             enum "1609.79" {
               description "1609.79 nm/186.231250 THz 3.125/6.25GHz spacing";
             }
             enum "1609.76" {
               description "1609.76 nm/186.234375 THz 3.125GHz spacing";
             }
             enum "1609.73" {
               description "1609.73 nm/186.237500 THz 3.125/6.25/12.5GHz spacing";
             }
             enum "1609.70" {
               description "1609.70 nm/186.240625 THz 3.125GHz spacing";
             }
             enum "1609.68" {
               description "1609.68 nm/186.243750 THz 3.125/6.25GHz spacing";
             }
             enum "1609.65" {
               description "1609.65 nm/186.246875 THz 3.125GHz spacing";
             }
             enum "1609.62" {
               description "1609.62 nm/186.250000 THz 3.125/6.25/12.5/50GHz spacing";
             }
             enum "1609.60" {
               description "1609.60 nm/186.253125 THz 3.125GHz spacing";
             }
             enum "1609.57" {
               description "1609.57 nm/186.256250 THz 3.125/6.25GHz spacing";
             }
             enum "1609.54" {
               description "1609.54 nm/186.259375 THz 3.125GHz spacing";
             }
             enum "1609.52" {
               description "1609.52 nm/186.262500 THz 3.125/6.25/12.5GHz spacing";
             }
             enum "1609.49" {
               description "1609.49 nm/186.265625 THz 3.125GHz spacing";
             }
             enum "1609.46" {
               description "1609.46 nm/186.268750 THz 3.125/6.25GHz spacing";
             }
             enum "1609.43" {
               description "1609.43 nm/186.271875 THz 3.125GHz spacing";
             }
             enum "1609.41" {
               description "1609.41 nm/186.275000 THz 3.125/6.25/12.5/75GHz spacing";
             }
             enum "1609.38" {
               description "1609.38 nm/186.278125 THz 3.125GHz spacing";
             }
             enum "1609.35" {
               description "1609.35 nm/186.281250 THz 3.125/6.25GHz spacing";
             }
             enum "1609.33" {
               description "1609.33 nm/186.284375 THz 3.125GHz spacing";
             }
             enum "1609.30" {
               description "1609.30 nm/186.287500 THz 3.125/6.25/12.5GHz spacing";
             }
             enum "1609.27" {
               description "1609.27 nm/186.290625 THz 3.125GHz spacing";
             }
             enum "1609.25" {
               description "1609.25 nm/186.293750 THz 3.125/6.25GHz spacing";
             }
             enum "1609.22" {
               description "1609.22 nm/186.296875 THz 3.125GHz spacing";
             }
             enum "1609.19" {
               description "1609.19 nm/186.300000 THz 3.125/6.25/12.5/50/75/100GHz spacing";
             }
             enum "1609.16" {
               description "1609.16 nm/186.303125 THz 3.125GHz spacing";
             }
             enum "1609.14" {
               description "1609.14 nm/186.306250 THz 3.125/6.25GHz spacing";
             }
             enum "1609.11" {
               description "1609.11 nm/186.309375 THz 3.125GHz spacing";
             }
             enum "1609.08" {
               description "1609.08 nm/186.312500 THz 3.125/6.25/12.5GHz spacing";
             }
             enum "1609.06" {
               description "1609.06 nm/186.315625 THz 3.125GHz spacing";
             }
             enum "1609.03" {
               description "1609.03 nm/186.318750 THz 3.125/6.25GHz spacing";
             }
             enum "1609.00" {
               description "1609.00 nm/186.321875 THz 3.125GHz spacing";
             }
             enum "1608.98" {
               description "1608.98 nm/186.325000 THz 3.125/6.25/12.5GHz spacing";
             }
             enum "1608.95" {
               description "1608.95 nm/186.328125 THz 3.125GHz spacing";
             }
             enum "1608.92" {
               description "1608.92 nm/186.331250 THz 3.125/6.25GHz spacing";
             }
             enum "1608.90" {
               description "1608.90 nm/186.334375 THz 3.125GHz spacing";
             }
             enum "1608.87" {
               description "1608.87 nm/186.337500 THz 3.125/6.25/12.5GHz spacing";
             }
             enum "1608.84" {
               description "1608.84 nm/186.340625 THz 3.125GHz spacing";
             }
             enum "1608.81" {
               description "1608.81 nm/186.343750 THz 3.125/6.25GHz spacing";
             }
             enum "1608.79" {
               description "1608.79 nm/186.346875 THz 3.125GHz spacing";
             }
             enum "1608.76" {
               description "1608.76 nm/186.350000 THz 3.125/6.25/12.5/50/75GHz spacing";
             }
             enum "1608.73" {
               description "1608.73 nm/186.353125 THz 3.125GHz spacing";
             }
             enum "1608.71" {
               description "1608.71 nm/186.356250 THz 3.125/6.25GHz spacing";
             }
             enum "1608.68" {
               description "1608.68 nm/186.359375 THz 3.125GHz spacing";
             }
             enum "1608.65" {
               description "1608.65 nm/186.362500 THz 3.125/6.25/12.5GHz spacing";
             }
             enum "1608.63" {
               description "1608.63 nm/186.365625 THz 3.125GHz spacing";
             }
             enum "1608.60" {
               description "1608.60 nm/186.368750 THz 3.125/6.25GHz spacing";
             }
             enum "1608.57" {
               description "1608.57 nm/186.371875 THz 3.125GHz spacing";
             }
             enum "1608.54" {
               description "1608.54 nm/186.375000 THz 3.125/6.25/12.5GHz spacing";
             }
             enum "1608.52" {
               description "1608.52 nm/186.378125 THz 3.125GHz spacing";
             }
             enum "1608.49" {
               description "1608.49 nm/186.381250 THz 3.125/6.25GHz spacing";
             }
             enum "1608.46" {
               description "1608.46 nm/186.384375 THz 3.125GHz spacing";
             }
             enum "1608.44" {
               description "1608.44 nm/186.387500 THz 3.125/6.25/12.5GHz spacing";
             }
             enum "1608.41" {
               description "1608.41 nm/186.390625 THz 3.125GHz spacing";
             }
             enum "1608.38" {
               description "1608.38 nm/186.393750 THz 3.125/6.25GHz spacing";
             }
             enum "1608.36" {
               description "1608.36 nm/186.396875 THz 3.125GHz spacing";
             }
             enum "1608.33" {
               description "1608.33 nm/186.400000 THz 3.125/6.25/12.5/100GHz spacing";
             }
             enum "1608.30" {
               description "1608.30 nm/186.403125 THz 3.125GHz spacing";
             }
             enum "1608.27" {
               description "1608.27 nm/186.406250 THz 3.125/6.25GHz spacing";
             }
             enum "1608.25" {
               description "1608.25 nm/186.409375 THz 3.125GHz spacing";
             }
             enum "1608.22" {
               description "1608.22 nm/186.412500 THz 3.125/6.25/12.5GHz spacing";
             }
             enum "1608.19" {
               description "1608.19 nm/186.415625 THz 3.125GHz spacing";
             }
             enum "1608.17" {
               description "1608.17 nm/186.418750 THz 3.125/6.25GHz spacing";
             }
             enum "1608.14" {
               description "1608.14 nm/186.421875 THz 3.125GHz spacing";
             }
             enum "1608.11" {
               description "1608.11 nm/186.425000 THz 3.125/6.25/12.5/75GHz spacing";
             }
             enum "1608.09" {
               description "1608.09 nm/186.428125 THz 3.125GHz spacing";
             }
             enum "1608.06" {
               description "1608.06 nm/186.431250 THz 3.125/6.25GHz spacing";
             }
             enum "1608.03" {
               description "1608.03 nm/186.434375 THz 3.125GHz spacing";
             }
             enum "1608.01" {
               description "1608.01 nm/186.437500 THz 3.125/6.25/12.5GHz spacing";
             }
             enum "1607.98" {
               description "1607.98 nm/186.440625 THz 3.125GHz spacing";
             }
             enum "1607.95" {
               description "1607.95 nm/186.443750 THz 3.125/6.25GHz spacing";
             }
             enum "1607.92" {
               description "1607.92 nm/186.446875 THz 3.125GHz spacing";
             }
             enum "1607.90" {
               description "1607.90 nm/186.450000 THz 3.125/6.25/12.5/50GHz spacing";
             }
             enum "1607.87" {
               description "1607.87 nm/186.453125 THz 3.125GHz spacing";
             }
             enum "1607.84" {
               description "1607.84 nm/186.456250 THz 3.125/6.25GHz spacing";
             }
             enum "1607.82" {
               description "1607.82 nm/186.459375 THz 3.125GHz spacing";
             }
             enum "1607.79" {
               description "1607.79 nm/186.462500 THz 3.125/6.25/12.5GHz spacing";
             }
             enum "1607.76" {
               description "1607.76 nm/186.465625 THz 3.125GHz spacing";
             }
             enum "1607.74" {
               description "1607.74 nm/186.468750 THz 3.125/6.25GHz spacing";
             }
             enum "1607.71" {
               description "1607.71 nm/186.471875 THz 3.125GHz spacing";
             }
             enum "1607.68" {
               description "1607.68 nm/186.475000 THz 3.125/6.25/12.5GHz spacing";
             }
             enum "1607.65" {
               description "1607.65 nm/186.478125 THz 3.125GHz spacing";
             }
             enum "1607.63" {
               description "1607.63 nm/186.481250 THz 3.125/6.25GHz spacing";
             }
             enum "1607.60" {
               description "1607.60 nm/186.484375 THz 3.125GHz spacing";
             }
             enum "1607.57" {
               description "1607.57 nm/186.487500 THz 3.125/6.25/12.5GHz spacing";
             }
             enum "1607.55" {
               description "1607.55 nm/186.490625 THz 3.125GHz spacing";
             }
             enum "1607.52" {
               description "1607.52 nm/186.493750 THz 3.125/6.25GHz spacing";
             }
             enum "1607.49" {
               description "1607.49 nm/186.496875 THz 3.125GHz spacing";
             }
             enum "1607.47" {
               description "1607.47 nm/186.500000 THz 3.125/6.25/12.5/100GHz spacing";
             }
             enum "1607.44" {
               description "1607.44 nm/186.503125 THz 3.125GHz spacing";
             }
             enum "1607.41" {
               description "1607.41 nm/186.506250 THz 3.125/6.25GHz spacing";
             }
             enum "1607.39" {
               description "1607.39 nm/186.509375 THz 3.125GHz spacing";
             }
             enum "1607.36" {
               description "1607.36 nm/186.512500 THz 3.125/6.25/12.5GHz spacing";
             }
             enum "1607.33" {
               description "1607.33 nm/186.515625 THz 3.125GHz spacing";
             }
             enum "1607.30" {
               description "1607.30 nm/186.518750 THz 3.125/6.25GHz spacing";
             }
             enum "1607.28" {
               description "1607.28 nm/186.521875 THz 3.125GHz spacing";
             }
             enum "1607.25" {
               description "1607.25 nm/186.525000 THz 3.125/6.25/12.5GHz spacing";
             }
             enum "1607.22" {
               description "1607.22 nm/186.528125 THz 3.125GHz spacing";
             }
             enum "1607.20" {
               description "1607.20 nm/186.531250 THz 3.125/6.25GHz spacing";
             }
             enum "1607.17" {
               description "1607.17 nm/186.534375 THz 3.125GHz spacing";
             }
             enum "1607.14" {
               description "1607.14 nm/186.537500 THz 3.125/6.25/12.5GHz spacing";
             }
             enum "1607.12" {
               description "1607.12 nm/186.540625 THz 3.125GHz spacing";
             }
             enum "1607.09" {
               description "1607.09 nm/186.543750 THz 3.125/6.25GHz spacing";
             }
             enum "1607.06" {
               description "1607.06 nm/186.546875 THz 3.125GHz spacing";
             }
             enum "1607.04" {
               description "1607.04 nm/186.550000 THz 3.125/6.25/12.5/50GHz spacing";
             }
             enum "1607.01" {
               description "1607.01 nm/186.553125 THz 3.125GHz spacing";
             }
             enum "1606.98" {
               description "1606.98 nm/186.556250 THz 3.125/6.25GHz spacing";
             }
             enum "1606.95" {
               description "1606.95 nm/186.559375 THz 3.125GHz spacing";
             }
             enum "1606.93" {
               description "1606.93 nm/186.562500 THz 3.125/6.25/12.5GHz spacing";
             }
             enum "1606.90" {
               description "1606.90 nm/186.565625 THz 3.125GHz spacing";
             }
             enum "1606.87" {
               description "1606.87 nm/186.568750 THz 3.125/6.25GHz spacing";
             }
             enum "1606.85" {
               description "1606.85 nm/186.571875 THz 3.125GHz spacing";
             }
             enum "1606.82" {
               description "1606.82 nm/186.575000 THz 3.125/6.25/12.5/75GHz spacing";
             }
             enum "1606.79" {
               description "1606.79 nm/186.578125 THz 3.125GHz spacing";
             }
             enum "1606.77" {
               description "1606.77 nm/186.581250 THz 3.125/6.25GHz spacing";
             }
             enum "1606.74" {
               description "1606.74 nm/186.584375 THz 3.125GHz spacing";
             }
             enum "1606.71" {
               description "1606.71 nm/186.587500 THz 3.125/6.25/12.5GHz spacing";
             }
             enum "1606.69" {
               description "1606.69 nm/186.590625 THz 3.125GHz spacing";
             }
             enum "1606.66" {
               description "1606.66 nm/186.593750 THz 3.125/6.25GHz spacing";
             }
             enum "1606.63" {
               description "1606.63 nm/186.596875 THz 3.125GHz spacing";
             }
             enum "1606.60" {
               description "1606.60 nm/186.600000 THz 3.125/6.25/12.5/50/75/100GHz spacing";
             }
             enum "1606.58" {
               description "1606.58 nm/186.603125 THz 3.125GHz spacing";
             }
             enum "1606.55" {
               description "1606.55 nm/186.606250 THz 3.125/6.25GHz spacing";
             }
             enum "1606.52" {
               description "1606.52 nm/186.609375 THz 3.125GHz spacing";
             }
             enum "1606.50" {
               description "1606.50 nm/186.612500 THz 3.125/6.25/12.5GHz spacing";
             }
             enum "1606.47" {
               description "1606.47 nm/186.615625 THz 3.125GHz spacing";
             }
             enum "1606.44" {
               description "1606.44 nm/186.618750 THz 3.125/6.25GHz spacing";
             }
             enum "1606.42" {
               description "1606.42 nm/186.621875 THz 3.125GHz spacing";
             }
             enum "1606.39" {
               description "1606.39 nm/186.625000 THz 3.125/6.25/12.5GHz spacing";
             }
             enum "1606.36" {
               description "1606.36 nm/186.628125 THz 3.125GHz spacing";
             }
             enum "1606.34" {
               description "1606.34 nm/186.631250 THz 3.125/6.25GHz spacing";
             }
             enum "1606.31" {
               description "1606.31 nm/186.634375 THz 3.125GHz spacing";
             }
             enum "1606.28" {
               description "1606.28 nm/186.637500 THz 3.125/6.25/12.5GHz spacing";
             }
             enum "1606.26" {
               description "1606.26 nm/186.640625 THz 3.125GHz spacing";
             }
             enum "1606.23" {
               description "1606.23 nm/186.643750 THz 3.125/6.25GHz spacing";
             }
             enum "1606.20" {
               description "1606.20 nm/186.646875 THz 3.125GHz spacing";
             }
             enum "1606.17" {
               description "1606.17 nm/186.650000 THz 3.125/6.25/12.5/50/75GHz spacing";
             }
             enum "1606.15" {
               description "1606.15 nm/186.653125 THz 3.125GHz spacing";
             }
             enum "1606.12" {
               description "1606.12 nm/186.656250 THz 3.125/6.25GHz spacing";
             }
             enum "1606.09" {
               description "1606.09 nm/186.659375 THz 3.125GHz spacing";
             }
             enum "1606.07" {
               description "1606.07 nm/186.662500 THz 3.125/6.25/12.5GHz spacing";
             }
             enum "1606.04" {
               description "1606.04 nm/186.665625 THz 3.125GHz spacing";
             }
             enum "1606.01" {
               description "1606.01 nm/186.668750 THz 3.125/6.25GHz spacing";
             }
             enum "1605.99" {
               description "1605.99 nm/186.671875 THz 3.125GHz spacing";
             }
             enum "1605.96" {
               description "1605.96 nm/186.675000 THz 3.125/6.25/12.5GHz spacing";
             }
             enum "1605.93" {
               description "1605.93 nm/186.678125 THz 3.125GHz spacing";
             }
             enum "1605.91" {
               description "1605.91 nm/186.681250 THz 3.125/6.25GHz spacing";
             }
             enum "1605.88" {
               description "1605.88 nm/186.684375 THz 3.125GHz spacing";
             }
             enum "1605.85" {
               description "1605.85 nm/186.687500 THz 3.125/6.25/12.5GHz spacing";
             }
             enum "1605.82" {
               description "1605.82 nm/186.690625 THz 3.125GHz spacing";
             }
             enum "1605.80" {
               description "1605.80 nm/186.693750 THz 3.125/6.25GHz spacing";
             }
             enum "1605.77" {
               description "1605.77 nm/186.696875 THz 3.125GHz spacing";
             }
             enum "1605.74" {
               description "1605.74 nm/186.700000 THz 3.125/6.25/12.5/100GHz spacing";
             }
             enum "1605.72" {
               description "1605.72 nm/186.703125 THz 3.125GHz spacing";
             }
             enum "1605.69" {
               description "1605.69 nm/186.706250 THz 3.125/6.25GHz spacing";
             }
             enum "1605.66" {
               description "1605.66 nm/186.709375 THz 3.125GHz spacing";
             }
             enum "1605.64" {
               description "1605.64 nm/186.712500 THz 3.125/6.25/12.5GHz spacing";
             }
             enum "1605.61" {
               description "1605.61 nm/186.715625 THz 3.125GHz spacing";
             }
             enum "1605.58" {
               description "1605.58 nm/186.718750 THz 3.125/6.25GHz spacing";
             }
             enum "1605.56" {
               description "1605.56 nm/186.721875 THz 3.125GHz spacing";
             }
             enum "1605.53" {
               description "1605.53 nm/186.725000 THz 3.125/6.25/12.5/75GHz spacing";
             }
             enum "1605.50" {
               description "1605.50 nm/186.728125 THz 3.125GHz spacing";
             }
             enum "1605.48" {
               description "1605.48 nm/186.731250 THz 3.125/6.25GHz spacing";
             }
             enum "1605.45" {
               description "1605.45 nm/186.734375 THz 3.125GHz spacing";
             }
             enum "1605.42" {
               description "1605.42 nm/186.737500 THz 3.125/6.25/12.5GHz spacing";
             }
             enum "1605.39" {
               description "1605.39 nm/186.740625 THz 3.125GHz spacing";
             }
             enum "1605.37" {
               description "1605.37 nm/186.743750 THz 3.125/6.25GHz spacing";
             }
             enum "1605.34" {
               description "1605.34 nm/186.746875 THz 3.125GHz spacing";
             }
             enum "1605.31" {
               description "1605.31 nm/186.750000 THz 3.125/6.25/12.5/50GHz spacing";
             }
             enum "1605.29" {
               description "1605.29 nm/186.753125 THz 3.125GHz spacing";
             }
             enum "1605.26" {
               description "1605.26 nm/186.756250 THz 3.125/6.25GHz spacing";
             }
             enum "1605.23" {
               description "1605.23 nm/186.759375 THz 3.125GHz spacing";
             }
             enum "1605.21" {
               description "1605.21 nm/186.762500 THz 3.125/6.25/12.5GHz spacing";
             }
             enum "1605.18" {
               description "1605.18 nm/186.765625 THz 3.125GHz spacing";
             }
             enum "1605.15" {
               description "1605.15 nm/186.768750 THz 3.125/6.25GHz spacing";
             }
             enum "1605.13" {
               description "1605.13 nm/186.771875 THz 3.125GHz spacing";
             }
             enum "1605.10" {
               description "1605.10 nm/186.775000 THz 3.125/6.25/12.5GHz spacing";
             }
             enum "1605.07" {
               description "1605.07 nm/186.778125 THz 3.125GHz spacing";
             }
             enum "1605.05" {
               description "1605.05 nm/186.781250 THz 3.125/6.25GHz spacing";
             }
             enum "1605.02" {
               description "1605.02 nm/186.784375 THz 3.125GHz spacing";
             }
             enum "1604.99" {
               description "1604.99 nm/186.787500 THz 3.125/6.25/12.5GHz spacing";
             }
             enum "1604.97" {
               description "1604.97 nm/186.790625 THz 3.125GHz spacing";
             }
             enum "1604.94" {
               description "1604.94 nm/186.793750 THz 3.125/6.25GHz spacing";
             }
             enum "1604.91" {
               description "1604.91 nm/186.796875 THz 3.125GHz spacing";
             }
             enum "1604.88" {
               description "1604.88 nm/186.800000 THz 3.125/6.25/12.5/100GHz spacing";
             }
             enum "1604.86" {
               description "1604.86 nm/186.803125 THz 3.125GHz spacing";
             }
             enum "1604.83" {
               description "1604.83 nm/186.806250 THz 3.125/6.25GHz spacing";
             }
             enum "1604.80" {
               description "1604.80 nm/186.809375 THz 3.125GHz spacing";
             }
             enum "1604.78" {
               description "1604.78 nm/186.812500 THz 3.125/6.25/12.5GHz spacing";
             }
             enum "1604.75" {
               description "1604.75 nm/186.815625 THz 3.125GHz spacing";
             }
             enum "1604.72" {
               description "1604.72 nm/186.818750 THz 3.125/6.25GHz spacing";
             }
             enum "1604.70" {
               description "1604.70 nm/186.821875 THz 3.125GHz spacing";
             }
             enum "1604.67" {
               description "1604.67 nm/186.825000 THz 3.125/6.25/12.5GHz spacing";
             }
             enum "1604.64" {
               description "1604.64 nm/186.828125 THz 3.125GHz spacing";
             }
             enum "1604.62" {
               description "1604.62 nm/186.831250 THz 3.125/6.25GHz spacing";
             }
             enum "1604.59" {
               description "1604.59 nm/186.834375 THz 3.125GHz spacing";
             }
             enum "1604.56" {
               description "1604.56 nm/186.837500 THz 3.125/6.25/12.5GHz spacing";
             }
             enum "1604.54" {
               description "1604.54 nm/186.840625 THz 3.125GHz spacing";
             }
             enum "1604.51" {
               description "1604.51 nm/186.843750 THz 3.125/6.25GHz spacing";
             }
             enum "1604.48" {
               description "1604.48 nm/186.846875 THz 3.125GHz spacing";
             }
             enum "1604.46" {
               description "1604.46 nm/186.850000 THz 3.125/6.25/12.5/50GHz spacing";
             }
             enum "1604.43" {
               description "1604.43 nm/186.853125 THz 3.125GHz spacing";
             }
             enum "1604.40" {
               description "1604.40 nm/186.856250 THz 3.125/6.25GHz spacing";
             }
             enum "1604.37" {
               description "1604.37 nm/186.859375 THz 3.125GHz spacing";
             }
             enum "1604.35" {
               description "1604.35 nm/186.862500 THz 3.125/6.25/12.5GHz spacing";
             }
             enum "1604.32" {
               description "1604.32 nm/186.865625 THz 3.125GHz spacing";
             }
             enum "1604.29" {
               description "1604.29 nm/186.868750 THz 3.125/6.25GHz spacing";
             }
             enum "1604.27" {
               description "1604.27 nm/186.871875 THz 3.125GHz spacing";
             }
             enum "1604.24" {
               description "1604.24 nm/186.875000 THz 3.125/6.25/12.5/75GHz spacing";
             }
             enum "1604.21" {
               description "1604.21 nm/186.878125 THz 3.125GHz spacing";
             }
             enum "1604.19" {
               description "1604.19 nm/186.881250 THz 3.125/6.25GHz spacing";
             }
             enum "1604.16" {
               description "1604.16 nm/186.884375 THz 3.125GHz spacing";
             }
             enum "1604.13" {
               description "1604.13 nm/186.887500 THz 3.125/6.25/12.5GHz spacing";
             }
             enum "1604.11" {
               description "1604.11 nm/186.890625 THz 3.125GHz spacing";
             }
             enum "1604.08" {
               description "1604.08 nm/186.893750 THz 3.125/6.25GHz spacing";
             }
             enum "1604.05" {
               description "1604.05 nm/186.896875 THz 3.125GHz spacing";
             }
             enum "1604.03" {
               description "1604.03 nm/186.900000 THz 3.125/6.25/12.5/50/75/100GHz spacing";
             }
             enum "1604.00" {
               description "1604.00 nm/186.903125 THz 3.125GHz spacing";
             }
             enum "1603.97" {
               description "1603.97 nm/186.906250 THz 3.125/6.25GHz spacing";
             }
             enum "1603.95" {
               description "1603.95 nm/186.909375 THz 3.125GHz spacing";
             }
             enum "1603.92" {
               description "1603.92 nm/186.912500 THz 3.125/6.25/12.5GHz spacing";
             }
             enum "1603.89" {
               description "1603.89 nm/186.915625 THz 3.125GHz spacing";
             }
             enum "1603.87" {
               description "1603.87 nm/186.918750 THz 3.125/6.25GHz spacing";
             }
             enum "1603.84" {
               description "1603.84 nm/186.921875 THz 3.125GHz spacing";
             }
             enum "1603.81" {
               description "1603.81 nm/186.925000 THz 3.125/6.25/12.5GHz spacing";
             }
             enum "1603.78" {
               description "1603.78 nm/186.928125 THz 3.125GHz spacing";
             }
             enum "1603.76" {
               description "1603.76 nm/186.931250 THz 3.125/6.25GHz spacing";
             }
             enum "1603.73" {
               description "1603.73 nm/186.934375 THz 3.125GHz spacing";
             }
             enum "1603.70" {
               description "1603.70 nm/186.937500 THz 3.125/6.25/12.5GHz spacing";
             }
             enum "1603.68" {
               description "1603.68 nm/186.940625 THz 3.125GHz spacing";
             }
             enum "1603.65" {
               description "1603.65 nm/186.943750 THz 3.125/6.25GHz spacing";
             }
             enum "1603.62" {
               description "1603.62 nm/186.946875 THz 3.125GHz spacing";
             }
             enum "1603.60" {
               description "1603.60 nm/186.950000 THz 3.125/6.25/12.5/50/75GHz spacing";
             }
             enum "1603.57" {
               description "1603.57 nm/186.953125 THz 3.125GHz spacing";
             }
             enum "1603.54" {
               description "1603.54 nm/186.956250 THz 3.125/6.25GHz spacing";
             }
             enum "1603.52" {
               description "1603.52 nm/186.959375 THz 3.125GHz spacing";
             }
             enum "1603.49" {
               description "1603.49 nm/186.962500 THz 3.125/6.25/12.5GHz spacing";
             }
             enum "1603.46" {
               description "1603.46 nm/186.965625 THz 3.125GHz spacing";
             }
             enum "1603.44" {
               description "1603.44 nm/186.968750 THz 3.125/6.25GHz spacing";
             }
             enum "1603.41" {
               description "1603.41 nm/186.971875 THz 3.125GHz spacing";
             }
             enum "1603.38" {
               description "1603.38 nm/186.975000 THz 3.125/6.25/12.5GHz spacing";
             }
             enum "1603.36" {
               description "1603.36 nm/186.978125 THz 3.125GHz spacing";
             }
             enum "1603.33" {
               description "1603.33 nm/186.981250 THz 3.125/6.25GHz spacing";
             }
             enum "1603.30" {
               description "1603.30 nm/186.984375 THz 3.125GHz spacing";
             }
             enum "1603.28" {
               description "1603.28 nm/186.987500 THz 3.125/6.25/12.5GHz spacing";
             }
             enum "1603.25" {
               description "1603.25 nm/186.990625 THz 3.125GHz spacing";
             }
             enum "1603.22" {
               description "1603.22 nm/186.993750 THz 3.125/6.25GHz spacing";
             }
             enum "1603.20" {
               description "1603.20 nm/186.996875 THz 3.125GHz spacing";
             }
             enum "1603.17" {
               description "1603.17 nm/187.000000 THz 3.125/6.25/12.5/100GHz spacing";
             }
             enum "1603.14" {
               description "1603.14 nm/187.003125 THz 3.125GHz spacing";
             }
             enum "1603.11" {
               description "1603.11 nm/187.006250 THz 3.125/6.25GHz spacing";
             }
             enum "1603.09" {
               description "1603.09 nm/187.009375 THz 3.125GHz spacing";
             }
             enum "1603.06" {
               description "1603.06 nm/187.012500 THz 3.125/6.25/12.5GHz spacing";
             }
             enum "1603.03" {
               description "1603.03 nm/187.015625 THz 3.125GHz spacing";
             }
             enum "1603.01" {
               description "1603.01 nm/187.018750 THz 3.125/6.25GHz spacing";
             }
             enum "1602.98" {
               description "1602.98 nm/187.021875 THz 3.125GHz spacing";
             }
             enum "1602.95" {
               description "1602.95 nm/187.025000 THz 3.125/6.25/12.5/75GHz spacing";
             }
             enum "1602.93" {
               description "1602.93 nm/187.028125 THz 3.125GHz spacing";
             }
             enum "1602.90" {
               description "1602.90 nm/187.031250 THz 3.125/6.25GHz spacing";
             }
             enum "1602.87" {
               description "1602.87 nm/187.034375 THz 3.125GHz spacing";
             }
             enum "1602.85" {
               description "1602.85 nm/187.037500 THz 3.125/6.25/12.5GHz spacing";
             }
             enum "1602.82" {
               description "1602.82 nm/187.040625 THz 3.125GHz spacing";
             }
             enum "1602.79" {
               description "1602.79 nm/187.043750 THz 3.125/6.25GHz spacing";
             }
             enum "1602.77" {
               description "1602.77 nm/187.046875 THz 3.125GHz spacing";
             }
             enum "1602.74" {
               description "1602.74 nm/187.050000 THz 3.125/6.25/12.5/50GHz spacing";
             }
             enum "1602.71" {
               description "1602.71 nm/187.053125 THz 3.125GHz spacing";
             }
             enum "1602.69" {
               description "1602.69 nm/187.056250 THz 3.125/6.25GHz spacing";
             }
             enum "1602.66" {
               description "1602.66 nm/187.059375 THz 3.125GHz spacing";
             }
             enum "1602.63" {
               description "1602.63 nm/187.062500 THz 3.125/6.25/12.5GHz spacing";
             }
             enum "1602.61" {
               description "1602.61 nm/187.065625 THz 3.125GHz spacing";
             }
             enum "1602.58" {
               description "1602.58 nm/187.068750 THz 3.125/6.25GHz spacing";
             }
             enum "1602.55" {
               description "1602.55 nm/187.071875 THz 3.125GHz spacing";
             }
             enum "1602.53" {
               description "1602.53 nm/187.075000 THz 3.125/6.25/12.5GHz spacing";
             }
             enum "1602.50" {
               description "1602.50 nm/187.078125 THz 3.125GHz spacing";
             }
             enum "1602.47" {
               description "1602.47 nm/187.081250 THz 3.125/6.25GHz spacing";
             }
             enum "1602.45" {
               description "1602.45 nm/187.084375 THz 3.125GHz spacing";
             }
             enum "1602.42" {
               description "1602.42 nm/187.087500 THz 3.125/6.25/12.5GHz spacing";
             }
             enum "1602.39" {
               description "1602.39 nm/187.090625 THz 3.125GHz spacing";
             }
             enum "1602.36" {
               description "1602.36 nm/187.093750 THz 3.125/6.25GHz spacing";
             }
             enum "1602.34" {
               description "1602.34 nm/187.096875 THz 3.125GHz spacing";
             }
             enum "1602.31" {
               description "1602.31 nm/187.100000 THz 3.125/6.25/12.5/100GHz spacing";
             }
             enum "1602.28" {
               description "1602.28 nm/187.103125 THz 3.125GHz spacing";
             }
             enum "1602.26" {
               description "1602.26 nm/187.106250 THz 3.125/6.25GHz spacing";
             }
             enum "1602.23" {
               description "1602.23 nm/187.109375 THz 3.125GHz spacing";
             }
             enum "1602.20" {
               description "1602.20 nm/187.112500 THz 3.125/6.25/12.5GHz spacing";
             }
             enum "1602.18" {
               description "1602.18 nm/187.115625 THz 3.125GHz spacing";
             }
             enum "1602.15" {
               description "1602.15 nm/187.118750 THz 3.125/6.25GHz spacing";
             }
             enum "1602.12" {
               description "1602.12 nm/187.121875 THz 3.125GHz spacing";
             }
             enum "1602.10" {
               description "1602.10 nm/187.125000 THz 3.125/6.25/12.5GHz spacing";
             }
             enum "1602.07" {
               description "1602.07 nm/187.128125 THz 3.125GHz spacing";
             }
             enum "1602.04" {
               description "1602.04 nm/187.131250 THz 3.125/6.25GHz spacing";
             }
             enum "1602.02" {
               description "1602.02 nm/187.134375 THz 3.125GHz spacing";
             }
             enum "1601.99" {
               description "1601.99 nm/187.137500 THz 3.125/6.25/12.5GHz spacing";
             }
             enum "1601.96" {
               description "1601.96 nm/187.140625 THz 3.125GHz spacing";
             }
             enum "1601.94" {
               description "1601.94 nm/187.143750 THz 3.125/6.25GHz spacing";
             }
             enum "1601.91" {
               description "1601.91 nm/187.146875 THz 3.125GHz spacing";
             }
             enum "1601.88" {
               description "1601.88 nm/187.150000 THz 3.125/6.25/12.5/50GHz spacing";
             }
             enum "1601.86" {
               description "1601.86 nm/187.153125 THz 3.125GHz spacing";
             }
             enum "1601.83" {
               description "1601.83 nm/187.156250 THz 3.125/6.25GHz spacing";
             }
             enum "1601.80" {
               description "1601.80 nm/187.159375 THz 3.125GHz spacing";
             }
             enum "1601.78" {
               description "1601.78 nm/187.162500 THz 3.125/6.25/12.5GHz spacing";
             }
             enum "1601.75" {
               description "1601.75 nm/187.165625 THz 3.125GHz spacing";
             }
             enum "1601.72" {
               description "1601.72 nm/187.168750 THz 3.125/6.25GHz spacing";
             }
             enum "1601.70" {
               description "1601.70 nm/187.171875 THz 3.125GHz spacing";
             }
             enum "1601.67" {
               description "1601.67 nm/187.175000 THz 3.125/6.25/12.5/75GHz spacing";
             }
             enum "1601.64" {
               description "1601.64 nm/187.178125 THz 3.125GHz spacing";
             }
             enum "1601.62" {
               description "1601.62 nm/187.181250 THz 3.125/6.25GHz spacing";
             }
             enum "1601.59" {
               description "1601.59 nm/187.184375 THz 3.125GHz spacing";
             }
             enum "1601.56" {
               description "1601.56 nm/187.187500 THz 3.125/6.25/12.5GHz spacing";
             }
             enum "1601.54" {
               description "1601.54 nm/187.190625 THz 3.125GHz spacing";
             }
             enum "1601.51" {
               description "1601.51 nm/187.193750 THz 3.125/6.25GHz spacing";
             }
             enum "1601.48" {
               description "1601.48 nm/187.196875 THz 3.125GHz spacing";
             }
             enum "1601.46" {
               description "1601.46 nm/187.200000 THz 3.125/6.25/12.5/50/75/100GHz spacing";
             }
             enum "1601.43" {
               description "1601.43 nm/187.203125 THz 3.125GHz spacing";
             }
             enum "1601.40" {
               description "1601.40 nm/187.206250 THz 3.125/6.25GHz spacing";
             }
             enum "1601.38" {
               description "1601.38 nm/187.209375 THz 3.125GHz spacing";
             }
             enum "1601.35" {
               description "1601.35 nm/187.212500 THz 3.125/6.25/12.5GHz spacing";
             }
             enum "1601.32" {
               description "1601.32 nm/187.215625 THz 3.125GHz spacing";
             }
             enum "1601.30" {
               description "1601.30 nm/187.218750 THz 3.125/6.25GHz spacing";
             }
             enum "1601.27" {
               description "1601.27 nm/187.221875 THz 3.125GHz spacing";
             }
             enum "1601.24" {
               description "1601.24 nm/187.225000 THz 3.125/6.25/12.5GHz spacing";
             }
             enum "1601.21" {
               description "1601.21 nm/187.228125 THz 3.125GHz spacing";
             }
             enum "1601.19" {
               description "1601.19 nm/187.231250 THz 3.125/6.25GHz spacing";
             }
             enum "1601.16" {
               description "1601.16 nm/187.234375 THz 3.125GHz spacing";
             }
             enum "1601.13" {
               description "1601.13 nm/187.237500 THz 3.125/6.25/12.5GHz spacing";
             }
             enum "1601.11" {
               description "1601.11 nm/187.240625 THz 3.125GHz spacing";
             }
             enum "1601.08" {
               description "1601.08 nm/187.243750 THz 3.125/6.25GHz spacing";
             }
             enum "1601.05" {
               description "1601.05 nm/187.246875 THz 3.125GHz spacing";
             }
             enum "1601.03" {
               description "1601.03 nm/187.250000 THz 3.125/6.25/12.5/50/75GHz spacing";
             }
             enum "1601.00" {
               description "1601.00 nm/187.253125 THz 3.125GHz spacing";
             }
             enum "1600.97" {
               description "1600.97 nm/187.256250 THz 3.125/6.25GHz spacing";
             }
             enum "1600.95" {
               description "1600.95 nm/187.259375 THz 3.125GHz spacing";
             }
             enum "1600.92" {
               description "1600.92 nm/187.262500 THz 3.125/6.25/12.5GHz spacing";
             }
             enum "1600.89" {
               description "1600.89 nm/187.265625 THz 3.125GHz spacing";
             }
             enum "1600.87" {
               description "1600.87 nm/187.268750 THz 3.125/6.25GHz spacing";
             }
             enum "1600.84" {
               description "1600.84 nm/187.271875 THz 3.125GHz spacing";
             }
             enum "1600.81" {
               description "1600.81 nm/187.275000 THz 3.125/6.25/12.5GHz spacing";
             }
             enum "1600.79" {
               description "1600.79 nm/187.278125 THz 3.125GHz spacing";
             }
             enum "1600.76" {
               description "1600.76 nm/187.281250 THz 3.125/6.25GHz spacing";
             }
             enum "1600.73" {
               description "1600.73 nm/187.284375 THz 3.125GHz spacing";
             }
             enum "1600.71" {
               description "1600.71 nm/187.287500 THz 3.125/6.25/12.5GHz spacing";
             }
             enum "1600.68" {
               description "1600.68 nm/187.290625 THz 3.125GHz spacing";
             }
             enum "1600.65" {
               description "1600.65 nm/187.293750 THz 3.125/6.25GHz spacing";
             }
             enum "1600.63" {
               description "1600.63 nm/187.296875 THz 3.125GHz spacing";
             }
             enum "1600.60" {
               description "1600.60 nm/187.300000 THz 3.125/6.25/12.5/100GHz spacing";
             }
             enum "1600.57" {
               description "1600.57 nm/187.303125 THz 3.125GHz spacing";
             }
             enum "1600.55" {
               description "1600.55 nm/187.306250 THz 3.125/6.25GHz spacing";
             }
             enum "1600.52" {
               description "1600.52 nm/187.309375 THz 3.125GHz spacing";
             }
             enum "1600.49" {
               description "1600.49 nm/187.312500 THz 3.125/6.25/12.5GHz spacing";
             }
             enum "1600.47" {
               description "1600.47 nm/187.315625 THz 3.125GHz spacing";
             }
             enum "1600.44" {
               description "1600.44 nm/187.318750 THz 3.125/6.25GHz spacing";
             }
             enum "1600.41" {
               description "1600.41 nm/187.321875 THz 3.125GHz spacing";
             }
             enum "1600.39" {
               description "1600.39 nm/187.325000 THz 3.125/6.25/12.5/75GHz spacing";
             }
             enum "1600.36" {
               description "1600.36 nm/187.328125 THz 3.125GHz spacing";
             }
             enum "1600.33" {
               description "1600.33 nm/187.331250 THz 3.125/6.25GHz spacing";
             }
             enum "1600.31" {
               description "1600.31 nm/187.334375 THz 3.125GHz spacing";
             }
             enum "1600.28" {
               description "1600.28 nm/187.337500 THz 3.125/6.25/12.5GHz spacing";
             }
             enum "1600.25" {
               description "1600.25 nm/187.340625 THz 3.125GHz spacing";
             }
             enum "1600.23" {
               description "1600.23 nm/187.343750 THz 3.125/6.25GHz spacing";
             }
             enum "1600.20" {
               description "1600.20 nm/187.346875 THz 3.125GHz spacing";
             }
             enum "1600.17" {
               description "1600.17 nm/187.350000 THz 3.125/6.25/12.5/50GHz spacing";
             }
             enum "1600.15" {
               description "1600.15 nm/187.353125 THz 3.125GHz spacing";
             }
             enum "1600.12" {
               description "1600.12 nm/187.356250 THz 3.125/6.25GHz spacing";
             }
             enum "1600.09" {
               description "1600.09 nm/187.359375 THz 3.125GHz spacing";
             }
             enum "1600.07" {
               description "1600.07 nm/187.362500 THz 3.125/6.25/12.5GHz spacing";
             }
             enum "1600.04" {
               description "1600.04 nm/187.365625 THz 3.125GHz spacing";
             }
             enum "1600.01" {
               description "1600.01 nm/187.368750 THz 3.125/6.25GHz spacing";
             }
             enum "1599.99" {
               description "1599.99 nm/187.371875 THz 3.125GHz spacing";
             }
             enum "1599.96" {
               description "1599.96 nm/187.375000 THz 3.125/6.25/12.5GHz spacing";
             }
             enum "1599.93" {
               description "1599.93 nm/187.378125 THz 3.125GHz spacing";
             }
             enum "1599.91" {
               description "1599.91 nm/187.381250 THz 3.125/6.25GHz spacing";
             }
             enum "1599.88" {
               description "1599.88 nm/187.384375 THz 3.125GHz spacing";
             }
             enum "1599.85" {
               description "1599.85 nm/187.387500 THz 3.125/6.25/12.5GHz spacing";
             }
             enum "1599.83" {
               description "1599.83 nm/187.390625 THz 3.125GHz spacing";
             }
             enum "1599.80" {
               description "1599.80 nm/187.393750 THz 3.125/6.25GHz spacing";
             }
             enum "1599.77" {
               description "1599.77 nm/187.396875 THz 3.125GHz spacing";
             }
             enum "1599.75" {
               description "1599.75 nm/187.400000 THz 3.125/6.25/12.5/100GHz spacing";
             }
             enum "1599.72" {
               description "1599.72 nm/187.403125 THz 3.125GHz spacing";
             }
             enum "1599.69" {
               description "1599.69 nm/187.406250 THz 3.125/6.25GHz spacing";
             }
             enum "1599.67" {
               description "1599.67 nm/187.409375 THz 3.125GHz spacing";
             }
             enum "1599.64" {
               description "1599.64 nm/187.412500 THz 3.125/6.25/12.5GHz spacing";
             }
             enum "1599.61" {
               description "1599.61 nm/187.415625 THz 3.125GHz spacing";
             }
             enum "1599.59" {
               description "1599.59 nm/187.418750 THz 3.125/6.25GHz spacing";
             }
             enum "1599.56" {
               description "1599.56 nm/187.421875 THz 3.125GHz spacing";
             }
             enum "1599.53" {
               description "1599.53 nm/187.425000 THz 3.125/6.25/12.5GHz spacing";
             }
             enum "1599.51" {
               description "1599.51 nm/187.428125 THz 3.125GHz spacing";
             }
             enum "1599.48" {
               description "1599.48 nm/187.431250 THz 3.125/6.25GHz spacing";
             }
             enum "1599.45" {
               description "1599.45 nm/187.434375 THz 3.125GHz spacing";
             }
             enum "1599.43" {
               description "1599.43 nm/187.437500 THz 3.125/6.25/12.5GHz spacing";
             }
             enum "1599.40" {
               description "1599.40 nm/187.440625 THz 3.125GHz spacing";
             }
             enum "1599.37" {
               description "1599.37 nm/187.443750 THz 3.125/6.25GHz spacing";
             }
             enum "1599.35" {
               description "1599.35 nm/187.446875 THz 3.125GHz spacing";
             }
             enum "1599.32" {
               description "1599.32 nm/187.450000 THz 3.125/6.25/12.5/50GHz spacing";
             }
             enum "1599.29" {
               description "1599.29 nm/187.453125 THz 3.125GHz spacing";
             }
             enum "1599.27" {
               description "1599.27 nm/187.456250 THz 3.125/6.25GHz spacing";
             }
             enum "1599.24" {
               description "1599.24 nm/187.459375 THz 3.125GHz spacing";
             }
             enum "1599.21" {
               description "1599.21 nm/187.462500 THz 3.125/6.25/12.5GHz spacing";
             }
             enum "1599.19" {
               description "1599.19 nm/187.465625 THz 3.125GHz spacing";
             }
             enum "1599.16" {
               description "1599.16 nm/187.468750 THz 3.125/6.25GHz spacing";
             }
             enum "1599.13" {
               description "1599.13 nm/187.471875 THz 3.125GHz spacing";
             }
             enum "1599.11" {
               description "1599.11 nm/187.475000 THz 3.125/6.25/12.5/75GHz spacing";
             }
             enum "1599.08" {
               description "1599.08 nm/187.478125 THz 3.125GHz spacing";
             }
             enum "1599.05" {
               description "1599.05 nm/187.481250 THz 3.125/6.25GHz spacing";
             }
             enum "1599.03" {
               description "1599.03 nm/187.484375 THz 3.125GHz spacing";
             }
             enum "1599.00" {
               description "1599.00 nm/187.487500 THz 3.125/6.25/12.5GHz spacing";
             }
             enum "1598.97" {
               description "1598.97 nm/187.490625 THz 3.125GHz spacing";
             }
             enum "1598.95" {
               description "1598.95 nm/187.493750 THz 3.125/6.25GHz spacing";
             }
             enum "1598.92" {
               description "1598.92 nm/187.496875 THz 3.125GHz spacing";
             }
             enum "1598.89" {
               description "1598.89 nm/187.500000 THz 3.125/6.25/12.5/50/75/100GHz spacing";
             }
             enum "1598.87" {
               description "1598.87 nm/187.503125 THz 3.125GHz spacing";
             }
             enum "1598.84" {
               description "1598.84 nm/187.506250 THz 3.125/6.25GHz spacing";
             }
             enum "1598.81" {
               description "1598.81 nm/187.509375 THz 3.125GHz spacing";
             }
             enum "1598.79" {
               description "1598.79 nm/187.512500 THz 3.125/6.25/12.5GHz spacing";
             }
             enum "1598.76" {
               description "1598.76 nm/187.515625 THz 3.125GHz spacing";
             }
             enum "1598.73" {
               description "1598.73 nm/187.518750 THz 3.125/6.25GHz spacing";
             }
             enum "1598.71" {
               description "1598.71 nm/187.521875 THz 3.125GHz spacing";
             }
             enum "1598.68" {
               description "1598.68 nm/187.525000 THz 3.125/6.25/12.5GHz spacing";
             }
             enum "1598.65" {
               description "1598.65 nm/187.528125 THz 3.125GHz spacing";
             }
             enum "1598.63" {
               description "1598.63 nm/187.531250 THz 3.125/6.25GHz spacing";
             }
             enum "1598.60" {
               description "1598.60 nm/187.534375 THz 3.125GHz spacing";
             }
             enum "1598.57" {
               description "1598.57 nm/187.537500 THz 3.125/6.25/12.5GHz spacing";
             }
             enum "1598.55" {
               description "1598.55 nm/187.540625 THz 3.125GHz spacing";
             }
             enum "1598.52" {
               description "1598.52 nm/187.543750 THz 3.125/6.25GHz spacing";
             }
             enum "1598.49" {
               description "1598.49 nm/187.546875 THz 3.125GHz spacing";
             }
             enum "1598.47" {
               description "1598.47 nm/187.550000 THz 3.125/6.25/12.5/50/75GHz spacing";
             }
             enum "1598.44" {
               description "1598.44 nm/187.553125 THz 3.125GHz spacing";
             }
             enum "1598.41" {
               description "1598.41 nm/187.556250 THz 3.125/6.25GHz spacing";
             }
             enum "1598.39" {
               description "1598.39 nm/187.559375 THz 3.125GHz spacing";
             }
             enum "1598.36" {
               description "1598.36 nm/187.562500 THz 3.125/6.25/12.5GHz spacing";
             }
             enum "1598.33" {
               description "1598.33 nm/187.565625 THz 3.125GHz spacing";
             }
             enum "1598.31" {
               description "1598.31 nm/187.568750 THz 3.125/6.25GHz spacing";
             }
             enum "1598.28" {
               description "1598.28 nm/187.571875 THz 3.125GHz spacing";
             }
             enum "1598.25" {
               description "1598.25 nm/187.575000 THz 3.125/6.25/12.5GHz spacing";
             }
             enum "1598.23" {
               description "1598.23 nm/187.578125 THz 3.125GHz spacing";
             }
             enum "1598.20" {
               description "1598.20 nm/187.581250 THz 3.125/6.25GHz spacing";
             }
             enum "1598.17" {
               description "1598.17 nm/187.584375 THz 3.125GHz spacing";
             }
             enum "1598.15" {
               description "1598.15 nm/187.587500 THz 3.125/6.25/12.5GHz spacing";
             }
             enum "1598.12" {
               description "1598.12 nm/187.590625 THz 3.125GHz spacing";
             }
             enum "1598.09" {
               description "1598.09 nm/187.593750 THz 3.125/6.25GHz spacing";
             }
             enum "1598.07" {
               description "1598.07 nm/187.596875 THz 3.125GHz spacing";
             }
             enum "1598.04" {
               description "1598.04 nm/187.600000 THz 3.125/6.25/12.5/100GHz spacing";
             }
             enum "1598.01" {
               description "1598.01 nm/187.603125 THz 3.125GHz spacing";
             }
             enum "1597.99" {
               description "1597.99 nm/187.606250 THz 3.125/6.25GHz spacing";
             }
             enum "1597.96" {
               description "1597.96 nm/187.609375 THz 3.125GHz spacing";
             }
             enum "1597.93" {
               description "1597.93 nm/187.612500 THz 3.125/6.25/12.5GHz spacing";
             }
             enum "1597.91" {
               description "1597.91 nm/187.615625 THz 3.125GHz spacing";
             }
             enum "1597.88" {
               description "1597.88 nm/187.618750 THz 3.125/6.25GHz spacing";
             }
             enum "1597.85" {
               description "1597.85 nm/187.621875 THz 3.125GHz spacing";
             }
             enum "1597.83" {
               description "1597.83 nm/187.625000 THz 3.125/6.25/12.5/75GHz spacing";
             }
             enum "1597.80" {
               description "1597.80 nm/187.628125 THz 3.125GHz spacing";
             }
             enum "1597.77" {
               description "1597.77 nm/187.631250 THz 3.125/6.25GHz spacing";
             }
             enum "1597.75" {
               description "1597.75 nm/187.634375 THz 3.125GHz spacing";
             }
             enum "1597.72" {
               description "1597.72 nm/187.637500 THz 3.125/6.25/12.5GHz spacing";
             }
             enum "1597.69" {
               description "1597.69 nm/187.640625 THz 3.125GHz spacing";
             }
             enum "1597.67" {
               description "1597.67 nm/187.643750 THz 3.125/6.25GHz spacing";
             }
             enum "1597.64" {
               description "1597.64 nm/187.646875 THz 3.125GHz spacing";
             }
             enum "1597.62" {
               description "1597.62 nm/187.650000 THz 3.125/6.25/12.5/50GHz spacing";
             }
             enum "1597.59" {
               description "1597.59 nm/187.653125 THz 3.125GHz spacing";
             }
             enum "1597.56" {
               description "1597.56 nm/187.656250 THz 3.125/6.25GHz spacing";
             }
             enum "1597.54" {
               description "1597.54 nm/187.659375 THz 3.125GHz spacing";
             }
             enum "1597.51" {
               description "1597.51 nm/187.662500 THz 3.125/6.25/12.5GHz spacing";
             }
             enum "1597.48" {
               description "1597.48 nm/187.665625 THz 3.125GHz spacing";
             }
             enum "1597.46" {
               description "1597.46 nm/187.668750 THz 3.125/6.25GHz spacing";
             }
             enum "1597.43" {
               description "1597.43 nm/187.671875 THz 3.125GHz spacing";
             }
             enum "1597.40" {
               description "1597.40 nm/187.675000 THz 3.125/6.25/12.5GHz spacing";
             }
             enum "1597.38" {
               description "1597.38 nm/187.678125 THz 3.125GHz spacing";
             }
             enum "1597.35" {
               description "1597.35 nm/187.681250 THz 3.125/6.25GHz spacing";
             }
             enum "1597.32" {
               description "1597.32 nm/187.684375 THz 3.125GHz spacing";
             }
             enum "1597.30" {
               description "1597.30 nm/187.687500 THz 3.125/6.25/12.5GHz spacing";
             }
             enum "1597.27" {
               description "1597.27 nm/187.690625 THz 3.125GHz spacing";
             }
             enum "1597.24" {
               description "1597.24 nm/187.693750 THz 3.125/6.25GHz spacing";
             }
             enum "1597.22" {
               description "1597.22 nm/187.696875 THz 3.125GHz spacing";
             }
             enum "1597.19" {
               description "1597.19 nm/187.700000 THz 3.125/6.25/12.5/100GHz spacing";
             }
             enum "1597.16" {
               description "1597.16 nm/187.703125 THz 3.125GHz spacing";
             }
             enum "1597.14" {
               description "1597.14 nm/187.706250 THz 3.125/6.25GHz spacing";
             }
             enum "1597.11" {
               description "1597.11 nm/187.709375 THz 3.125GHz spacing";
             }
             enum "1597.08" {
               description "1597.08 nm/187.712500 THz 3.125/6.25/12.5GHz spacing";
             }
             enum "1597.06" {
               description "1597.06 nm/187.715625 THz 3.125GHz spacing";
             }
             enum "1597.03" {
               description "1597.03 nm/187.718750 THz 3.125/6.25GHz spacing";
             }
             enum "1597.00" {
               description "1597.00 nm/187.721875 THz 3.125GHz spacing";
             }
             enum "1596.98" {
               description "1596.98 nm/187.725000 THz 3.125/6.25/12.5GHz spacing";
             }
             enum "1596.95" {
               description "1596.95 nm/187.728125 THz 3.125GHz spacing";
             }
             enum "1596.92" {
               description "1596.92 nm/187.731250 THz 3.125/6.25GHz spacing";
             }
             enum "1596.90" {
               description "1596.90 nm/187.734375 THz 3.125GHz spacing";
             }
             enum "1596.87" {
               description "1596.87 nm/187.737500 THz 3.125/6.25/12.5GHz spacing";
             }
             enum "1596.84" {
               description "1596.84 nm/187.740625 THz 3.125GHz spacing";
             }
             enum "1596.82" {
               description "1596.82 nm/187.743750 THz 3.125/6.25GHz spacing";
             }
             enum "1596.79" {
               description "1596.79 nm/187.746875 THz 3.125GHz spacing";
             }
             enum "1596.76" {
               description "1596.76 nm/187.750000 THz 3.125/6.25/12.5/50GHz spacing";
             }
             enum "1596.74" {
               description "1596.74 nm/187.753125 THz 3.125GHz spacing";
             }
             enum "1596.71" {
               description "1596.71 nm/187.756250 THz 3.125/6.25GHz spacing";
             }
             enum "1596.68" {
               description "1596.68 nm/187.759375 THz 3.125GHz spacing";
             }
             enum "1596.66" {
               description "1596.66 nm/187.762500 THz 3.125/6.25/12.5GHz spacing";
             }
             enum "1596.63" {
               description "1596.63 nm/187.765625 THz 3.125GHz spacing";
             }
             enum "1596.60" {
               description "1596.60 nm/187.768750 THz 3.125/6.25GHz spacing";
             }
             enum "1596.58" {
               description "1596.58 nm/187.771875 THz 3.125GHz spacing";
             }
             enum "1596.55" {
               description "1596.55 nm/187.775000 THz 3.125/6.25/12.5/75GHz spacing";
             }
             enum "1596.52" {
               description "1596.52 nm/187.778125 THz 3.125GHz spacing";
             }
             enum "1596.50" {
               description "1596.50 nm/187.781250 THz 3.125/6.25GHz spacing";
             }
             enum "1596.47" {
               description "1596.47 nm/187.784375 THz 3.125GHz spacing";
             }
             enum "1596.45" {
               description "1596.45 nm/187.787500 THz 3.125/6.25/12.5GHz spacing";
             }
             enum "1596.42" {
               description "1596.42 nm/187.790625 THz 3.125GHz spacing";
             }
             enum "1596.39" {
               description "1596.39 nm/187.793750 THz 3.125/6.25GHz spacing";
             }
             enum "1596.37" {
               description "1596.37 nm/187.796875 THz 3.125GHz spacing";
             }
             enum "1596.34" {
               description "1596.34 nm/187.800000 THz 3.125/6.25/12.5/50/75/100GHz spacing";
             }
             enum "1596.31" {
               description "1596.31 nm/187.803125 THz 3.125GHz spacing";
             }
             enum "1596.29" {
               description "1596.29 nm/187.806250 THz 3.125/6.25GHz spacing";
             }
             enum "1596.26" {
               description "1596.26 nm/187.809375 THz 3.125GHz spacing";
             }
             enum "1596.23" {
               description "1596.23 nm/187.812500 THz 3.125/6.25/12.5GHz spacing";
             }
             enum "1596.21" {
               description "1596.21 nm/187.815625 THz 3.125GHz spacing";
             }
             enum "1596.18" {
               description "1596.18 nm/187.818750 THz 3.125/6.25GHz spacing";
             }
             enum "1596.15" {
               description "1596.15 nm/187.821875 THz 3.125GHz spacing";
             }
             enum "1596.13" {
               description "1596.13 nm/187.825000 THz 3.125/6.25/12.5GHz spacing";
             }
             enum "1596.10" {
               description "1596.10 nm/187.828125 THz 3.125GHz spacing";
             }
             enum "1596.07" {
               description "1596.07 nm/187.831250 THz 3.125/6.25GHz spacing";
             }
             enum "1596.05" {
               description "1596.05 nm/187.834375 THz 3.125GHz spacing";
             }
             enum "1596.02" {
               description "1596.02 nm/187.837500 THz 3.125/6.25/12.5GHz spacing";
             }
             enum "1595.99" {
               description "1595.99 nm/187.840625 THz 3.125GHz spacing";
             }
             enum "1595.97" {
               description "1595.97 nm/187.843750 THz 3.125/6.25GHz spacing";
             }
             enum "1595.94" {
               description "1595.94 nm/187.846875 THz 3.125GHz spacing";
             }
             enum "1595.91" {
               description "1595.91 nm/187.850000 THz 3.125/6.25/12.5/50/75GHz spacing";
             }
             enum "1595.89" {
               description "1595.89 nm/187.853125 THz 3.125GHz spacing";
             }
             enum "1595.86" {
               description "1595.86 nm/187.856250 THz 3.125/6.25GHz spacing";
             }
             enum "1595.83" {
               description "1595.83 nm/187.859375 THz 3.125GHz spacing";
             }
             enum "1595.81" {
               description "1595.81 nm/187.862500 THz 3.125/6.25/12.5GHz spacing";
             }
             enum "1595.78" {
               description "1595.78 nm/187.865625 THz 3.125GHz spacing";
             }
             enum "1595.75" {
               description "1595.75 nm/187.868750 THz 3.125/6.25GHz spacing";
             }
             enum "1595.73" {
               description "1595.73 nm/187.871875 THz 3.125GHz spacing";
             }
             enum "1595.70" {
               description "1595.70 nm/187.875000 THz 3.125/6.25/12.5GHz spacing";
             }
             enum "1595.68" {
               description "1595.68 nm/187.878125 THz 3.125GHz spacing";
             }
             enum "1595.65" {
               description "1595.65 nm/187.881250 THz 3.125/6.25GHz spacing";
             }
             enum "1595.62" {
               description "1595.62 nm/187.884375 THz 3.125GHz spacing";
             }
             enum "1595.60" {
               description "1595.60 nm/187.887500 THz 3.125/6.25/12.5GHz spacing";
             }
             enum "1595.57" {
               description "1595.57 nm/187.890625 THz 3.125GHz spacing";
             }
             enum "1595.54" {
               description "1595.54 nm/187.893750 THz 3.125/6.25GHz spacing";
             }
             enum "1595.52" {
               description "1595.52 nm/187.896875 THz 3.125GHz spacing";
             }
             enum "1595.49" {
               description "1595.49 nm/187.900000 THz 3.125/6.25/12.5/100GHz spacing";
             }
             enum "1595.46" {
               description "1595.46 nm/187.903125 THz 3.125GHz spacing";
             }
             enum "1595.44" {
               description "1595.44 nm/187.906250 THz 3.125/6.25GHz spacing";
             }
             enum "1595.41" {
               description "1595.41 nm/187.909375 THz 3.125GHz spacing";
             }
             enum "1595.38" {
               description "1595.38 nm/187.912500 THz 3.125/6.25/12.5GHz spacing";
             }
             enum "1595.36" {
               description "1595.36 nm/187.915625 THz 3.125GHz spacing";
             }
             enum "1595.33" {
               description "1595.33 nm/187.918750 THz 3.125/6.25GHz spacing";
             }
             enum "1595.30" {
               description "1595.30 nm/187.921875 THz 3.125GHz spacing";
             }
             enum "1595.28" {
               description "1595.28 nm/187.925000 THz 3.125/6.25/12.5/75GHz spacing";
             }
             enum "1595.25" {
               description "1595.25 nm/187.928125 THz 3.125GHz spacing";
             }
             enum "1595.22" {
               description "1595.22 nm/187.931250 THz 3.125/6.25GHz spacing";
             }
             enum "1595.20" {
               description "1595.20 nm/187.934375 THz 3.125GHz spacing";
             }
             enum "1595.17" {
               description "1595.17 nm/187.937500 THz 3.125/6.25/12.5GHz spacing";
             }
             enum "1595.14" {
               description "1595.14 nm/187.940625 THz 3.125GHz spacing";
             }
             enum "1595.12" {
               description "1595.12 nm/187.943750 THz 3.125/6.25GHz spacing";
             }
             enum "1595.09" {
               description "1595.09 nm/187.946875 THz 3.125GHz spacing";
             }
             enum "1595.06" {
               description "1595.06 nm/187.950000 THz 3.125/6.25/12.5/50GHz spacing";
             }
             enum "1595.04" {
               description "1595.04 nm/187.953125 THz 3.125GHz spacing";
             }
             enum "1595.01" {
               description "1595.01 nm/187.956250 THz 3.125/6.25GHz spacing";
             }
             enum "1594.99" {
               description "1594.99 nm/187.959375 THz 3.125GHz spacing";
             }
             enum "1594.96" {
               description "1594.96 nm/187.962500 THz 3.125/6.25/12.5GHz spacing";
             }
             enum "1594.93" {
               description "1594.93 nm/187.965625 THz 3.125GHz spacing";
             }
             enum "1594.91" {
               description "1594.91 nm/187.968750 THz 3.125/6.25GHz spacing";
             }
             enum "1594.88" {
               description "1594.88 nm/187.971875 THz 3.125GHz spacing";
             }
             enum "1594.85" {
               description "1594.85 nm/187.975000 THz 3.125/6.25/12.5GHz spacing";
             }
             enum "1594.83" {
               description "1594.83 nm/187.978125 THz 3.125GHz spacing";
             }
             enum "1594.80" {
               description "1594.80 nm/187.981250 THz 3.125/6.25GHz spacing";
             }
             enum "1594.77" {
               description "1594.77 nm/187.984375 THz 3.125GHz spacing";
             }
             enum "1594.75" {
               description "1594.75 nm/187.987500 THz 3.125/6.25/12.5GHz spacing";
             }
             enum "1594.72" {
               description "1594.72 nm/187.990625 THz 3.125GHz spacing";
             }
             enum "1594.69" {
               description "1594.69 nm/187.993750 THz 3.125/6.25GHz spacing";
             }
             enum "1594.67" {
               description "1594.67 nm/187.996875 THz 3.125GHz spacing";
             }
             enum "1594.64" {
               description "1594.64 nm/188.000000 THz 3.125/6.25/12.5/100GHz spacing";
             }
             enum "1594.61" {
               description "1594.61 nm/188.003125 THz 3.125GHz spacing";
             }
             enum "1594.59" {
               description "1594.59 nm/188.006250 THz 3.125/6.25GHz spacing";
             }
             enum "1594.56" {
               description "1594.56 nm/188.009375 THz 3.125GHz spacing";
             }
             enum "1594.53" {
               description "1594.53 nm/188.012500 THz 3.125/6.25/12.5GHz spacing";
             }
             enum "1594.51" {
               description "1594.51 nm/188.015625 THz 3.125GHz spacing";
             }
             enum "1594.48" {
               description "1594.48 nm/188.018750 THz 3.125/6.25GHz spacing";
             }
             enum "1594.46" {
               description "1594.46 nm/188.021875 THz 3.125GHz spacing";
             }
             enum "1594.43" {
               description "1594.43 nm/188.025000 THz 3.125/6.25/12.5GHz spacing";
             }
             enum "1594.40" {
               description "1594.40 nm/188.028125 THz 3.125GHz spacing";
             }
             enum "1594.38" {
               description "1594.38 nm/188.031250 THz 3.125/6.25GHz spacing";
             }
             enum "1594.35" {
               description "1594.35 nm/188.034375 THz 3.125GHz spacing";
             }
             enum "1594.32" {
               description "1594.32 nm/188.037500 THz 3.125/6.25/12.5GHz spacing";
             }
             enum "1594.30" {
               description "1594.30 nm/188.040625 THz 3.125GHz spacing";
             }
             enum "1594.27" {
               description "1594.27 nm/188.043750 THz 3.125/6.25GHz spacing";
             }
             enum "1594.24" {
               description "1594.24 nm/188.046875 THz 3.125GHz spacing";
             }
             enum "1594.22" {
               description "1594.22 nm/188.050000 THz 3.125/6.25/12.5/50GHz spacing";
             }
             enum "1594.19" {
               description "1594.19 nm/188.053125 THz 3.125GHz spacing";
             }
             enum "1594.16" {
               description "1594.16 nm/188.056250 THz 3.125/6.25GHz spacing";
             }
             enum "1594.14" {
               description "1594.14 nm/188.059375 THz 3.125GHz spacing";
             }
             enum "1594.11" {
               description "1594.11 nm/188.062500 THz 3.125/6.25/12.5GHz spacing";
             }
             enum "1594.08" {
               description "1594.08 nm/188.065625 THz 3.125GHz spacing";
             }
             enum "1594.06" {
               description "1594.06 nm/188.068750 THz 3.125/6.25GHz spacing";
             }
             enum "1594.03" {
               description "1594.03 nm/188.071875 THz 3.125GHz spacing";
             }
             enum "1594.00" {
               description "1594.00 nm/188.075000 THz 3.125/6.25/12.5/75GHz spacing";
             }
             enum "1593.98" {
               description "1593.98 nm/188.078125 THz 3.125GHz spacing";
             }
             enum "1593.95" {
               description "1593.95 nm/188.081250 THz 3.125/6.25GHz spacing";
             }
             enum "1593.93" {
               description "1593.93 nm/188.084375 THz 3.125GHz spacing";
             }
             enum "1593.90" {
               description "1593.90 nm/188.087500 THz 3.125/6.25/12.5GHz spacing";
             }
             enum "1593.87" {
               description "1593.87 nm/188.090625 THz 3.125GHz spacing";
             }
             enum "1593.85" {
               description "1593.85 nm/188.093750 THz 3.125/6.25GHz spacing";
             }
             enum "1593.82" {
               description "1593.82 nm/188.096875 THz 3.125GHz spacing";
             }
             enum "1593.79" {
               description "1593.79 nm/188.100000 THz 3.125/6.25/12.5/50/75/100GHz spacing";
             }
             enum "1593.77" {
               description "1593.77 nm/188.103125 THz 3.125GHz spacing";
             }
             enum "1593.74" {
               description "1593.74 nm/188.106250 THz 3.125/6.25GHz spacing";
             }
             enum "1593.71" {
               description "1593.71 nm/188.109375 THz 3.125GHz spacing";
             }
             enum "1593.69" {
               description "1593.69 nm/188.112500 THz 3.125/6.25/12.5GHz spacing";
             }
             enum "1593.66" {
               description "1593.66 nm/188.115625 THz 3.125GHz spacing";
             }
             enum "1593.63" {
               description "1593.63 nm/188.118750 THz 3.125/6.25GHz spacing";
             }
             enum "1593.61" {
               description "1593.61 nm/188.121875 THz 3.125GHz spacing";
             }
             enum "1593.58" {
               description "1593.58 nm/188.125000 THz 3.125/6.25/12.5GHz spacing";
             }
             enum "1593.55" {
               description "1593.55 nm/188.128125 THz 3.125GHz spacing";
             }
             enum "1593.53" {
               description "1593.53 nm/188.131250 THz 3.125/6.25GHz spacing";
             }
             enum "1593.50" {
               description "1593.50 nm/188.134375 THz 3.125GHz spacing";
             }
             enum "1593.48" {
               description "1593.48 nm/188.137500 THz 3.125/6.25/12.5GHz spacing";
             }
             enum "1593.45" {
               description "1593.45 nm/188.140625 THz 3.125GHz spacing";
             }
             enum "1593.42" {
               description "1593.42 nm/188.143750 THz 3.125/6.25GHz spacing";
             }
             enum "1593.40" {
               description "1593.40 nm/188.146875 THz 3.125GHz spacing";
             }
             enum "1593.37" {
               description "1593.37 nm/188.150000 THz 3.125/6.25/12.5/50/75GHz spacing";
             }
             enum "1593.34" {
               description "1593.34 nm/188.153125 THz 3.125GHz spacing";
             }
             enum "1593.32" {
               description "1593.32 nm/188.156250 THz 3.125/6.25GHz spacing";
             }
             enum "1593.29" {
               description "1593.29 nm/188.159375 THz 3.125GHz spacing";
             }
             enum "1593.26" {
               description "1593.26 nm/188.162500 THz 3.125/6.25/12.5GHz spacing";
             }
             enum "1593.24" {
               description "1593.24 nm/188.165625 THz 3.125GHz spacing";
             }
             enum "1593.21" {
               description "1593.21 nm/188.168750 THz 3.125/6.25GHz spacing";
             }
             enum "1593.18" {
               description "1593.18 nm/188.171875 THz 3.125GHz spacing";
             }
             enum "1593.16" {
               description "1593.16 nm/188.175000 THz 3.125/6.25/12.5GHz spacing";
             }
             enum "1593.13" {
               description "1593.13 nm/188.178125 THz 3.125GHz spacing";
             }
             enum "1593.10" {
               description "1593.10 nm/188.181250 THz 3.125/6.25GHz spacing";
             }
             enum "1593.08" {
               description "1593.08 nm/188.184375 THz 3.125GHz spacing";
             }
             enum "1593.05" {
               description "1593.05 nm/188.187500 THz 3.125/6.25/12.5GHz spacing";
             }
             enum "1593.03" {
               description "1593.03 nm/188.190625 THz 3.125GHz spacing";
             }
             enum "1593.00" {
               description "1593.00 nm/188.193750 THz 3.125/6.25GHz spacing";
             }
             enum "1592.97" {
               description "1592.97 nm/188.196875 THz 3.125GHz spacing";
             }
             enum "1592.95" {
               description "1592.95 nm/188.200000 THz 3.125/6.25/12.5/100GHz spacing";
             }
             enum "1592.92" {
               description "1592.92 nm/188.203125 THz 3.125GHz spacing";
             }
             enum "1592.89" {
               description "1592.89 nm/188.206250 THz 3.125/6.25GHz spacing";
             }
             enum "1592.87" {
               description "1592.87 nm/188.209375 THz 3.125GHz spacing";
             }
             enum "1592.84" {
               description "1592.84 nm/188.212500 THz 3.125/6.25/12.5GHz spacing";
             }
             enum "1592.81" {
               description "1592.81 nm/188.215625 THz 3.125GHz spacing";
             }
             enum "1592.79" {
               description "1592.79 nm/188.218750 THz 3.125/6.25GHz spacing";
             }
             enum "1592.76" {
               description "1592.76 nm/188.221875 THz 3.125GHz spacing";
             }
             enum "1592.73" {
               description "1592.73 nm/188.225000 THz 3.125/6.25/12.5/75GHz spacing";
             }
             enum "1592.71" {
               description "1592.71 nm/188.228125 THz 3.125GHz spacing";
             }
             enum "1592.68" {
               description "1592.68 nm/188.231250 THz 3.125/6.25GHz spacing";
             }
             enum "1592.66" {
               description "1592.66 nm/188.234375 THz 3.125GHz spacing";
             }
             enum "1592.63" {
               description "1592.63 nm/188.237500 THz 3.125/6.25/12.5GHz spacing";
             }
             enum "1592.60" {
               description "1592.60 nm/188.240625 THz 3.125GHz spacing";
             }
             enum "1592.58" {
               description "1592.58 nm/188.243750 THz 3.125/6.25GHz spacing";
             }
             enum "1592.55" {
               description "1592.55 nm/188.246875 THz 3.125GHz spacing";
             }
             enum "1592.52" {
               description "1592.52 nm/188.250000 THz 3.125/6.25/12.5/50GHz spacing";
             }
             enum "1592.50" {
               description "1592.50 nm/188.253125 THz 3.125GHz spacing";
             }
             enum "1592.47" {
               description "1592.47 nm/188.256250 THz 3.125/6.25GHz spacing";
             }
             enum "1592.44" {
               description "1592.44 nm/188.259375 THz 3.125GHz spacing";
             }
             enum "1592.42" {
               description "1592.42 nm/188.262500 THz 3.125/6.25/12.5GHz spacing";
             }
             enum "1592.39" {
               description "1592.39 nm/188.265625 THz 3.125GHz spacing";
             }
             enum "1592.36" {
               description "1592.36 nm/188.268750 THz 3.125/6.25GHz spacing";
             }
             enum "1592.34" {
               description "1592.34 nm/188.271875 THz 3.125GHz spacing";
             }
             enum "1592.31" {
               description "1592.31 nm/188.275000 THz 3.125/6.25/12.5GHz spacing";
             }
             enum "1592.29" {
               description "1592.29 nm/188.278125 THz 3.125GHz spacing";
             }
             enum "1592.26" {
               description "1592.26 nm/188.281250 THz 3.125/6.25GHz spacing";
             }
             enum "1592.23" {
               description "1592.23 nm/188.284375 THz 3.125GHz spacing";
             }
             enum "1592.21" {
               description "1592.21 nm/188.287500 THz 3.125/6.25/12.5GHz spacing";
             }
             enum "1592.18" {
               description "1592.18 nm/188.290625 THz 3.125GHz spacing";
             }
             enum "1592.15" {
               description "1592.15 nm/188.293750 THz 3.125/6.25GHz spacing";
             }
             enum "1592.13" {
               description "1592.13 nm/188.296875 THz 3.125GHz spacing";
             }
             enum "1592.10" {
               description "1592.10 nm/188.300000 THz 3.125/6.25/12.5/100GHz spacing";
             }
             enum "1592.07" {
               description "1592.07 nm/188.303125 THz 3.125GHz spacing";
             }
             enum "1592.05" {
               description "1592.05 nm/188.306250 THz 3.125/6.25GHz spacing";
             }
             enum "1592.02" {
               description "1592.02 nm/188.309375 THz 3.125GHz spacing";
             }
             enum "1591.99" {
               description "1591.99 nm/188.312500 THz 3.125/6.25/12.5GHz spacing";
             }
             enum "1591.97" {
               description "1591.97 nm/188.315625 THz 3.125GHz spacing";
             }
             enum "1591.94" {
               description "1591.94 nm/188.318750 THz 3.125/6.25GHz spacing";
             }
             enum "1591.92" {
               description "1591.92 nm/188.321875 THz 3.125GHz spacing";
             }
             enum "1591.89" {
               description "1591.89 nm/188.325000 THz 3.125/6.25/12.5GHz spacing";
             }
             enum "1591.86" {
               description "1591.86 nm/188.328125 THz 3.125GHz spacing";
             }
             enum "1591.84" {
               description "1591.84 nm/188.331250 THz 3.125/6.25GHz spacing";
             }
             enum "1591.81" {
               description "1591.81 nm/188.334375 THz 3.125GHz spacing";
             }
             enum "1591.78" {
               description "1591.78 nm/188.337500 THz 3.125/6.25/12.5GHz spacing";
             }
             enum "1591.76" {
               description "1591.76 nm/188.340625 THz 3.125GHz spacing";
             }
             enum "1591.73" {
               description "1591.73 nm/188.343750 THz 3.125/6.25GHz spacing";
             }
             enum "1591.70" {
               description "1591.70 nm/188.346875 THz 3.125GHz spacing";
             }
             enum "1591.68" {
               description "1591.68 nm/188.350000 THz 3.125/6.25/12.5/50GHz spacing";
             }
             enum "1591.65" {
               description "1591.65 nm/188.353125 THz 3.125GHz spacing";
             }
             enum "1591.62" {
               description "1591.62 nm/188.356250 THz 3.125/6.25GHz spacing";
             }
             enum "1591.60" {
               description "1591.60 nm/188.359375 THz 3.125GHz spacing";
             }
             enum "1591.57" {
               description "1591.57 nm/188.362500 THz 3.125/6.25/12.5GHz spacing";
             }
             enum "1591.55" {
               description "1591.55 nm/188.365625 THz 3.125GHz spacing";
             }
             enum "1591.52" {
               description "1591.52 nm/188.368750 THz 3.125/6.25GHz spacing";
             }
             enum "1591.49" {
               description "1591.49 nm/188.371875 THz 3.125GHz spacing";
             }
             enum "1591.47" {
               description "1591.47 nm/188.375000 THz 3.125/6.25/12.5/75GHz spacing";
             }
             enum "1591.44" {
               description "1591.44 nm/188.378125 THz 3.125GHz spacing";
             }
             enum "1591.41" {
               description "1591.41 nm/188.381250 THz 3.125/6.25GHz spacing";
             }
             enum "1591.39" {
               description "1591.39 nm/188.384375 THz 3.125GHz spacing";
             }
             enum "1591.36" {
               description "1591.36 nm/188.387500 THz 3.125/6.25/12.5GHz spacing";
             }
             enum "1591.33" {
               description "1591.33 nm/188.390625 THz 3.125GHz spacing";
             }
             enum "1591.31" {
               description "1591.31 nm/188.393750 THz 3.125/6.25GHz spacing";
             }
             enum "1591.28" {
               description "1591.28 nm/188.396875 THz 3.125GHz spacing";
             }
             enum "1591.26" {
               description "1591.26 nm/188.400000 THz 3.125/6.25/12.5/50/75/100GHz spacing";
             }
             enum "1591.23" {
               description "1591.23 nm/188.403125 THz 3.125GHz spacing";
             }
             enum "1591.20" {
               description "1591.20 nm/188.406250 THz 3.125/6.25GHz spacing";
             }
             enum "1591.18" {
               description "1591.18 nm/188.409375 THz 3.125GHz spacing";
             }
             enum "1591.15" {
               description "1591.15 nm/188.412500 THz 3.125/6.25/12.5GHz spacing";
             }
             enum "1591.12" {
               description "1591.12 nm/188.415625 THz 3.125GHz spacing";
             }
             enum "1591.10" {
               description "1591.10 nm/188.418750 THz 3.125/6.25GHz spacing";
             }
             enum "1591.07" {
               description "1591.07 nm/188.421875 THz 3.125GHz spacing";
             }
             enum "1591.04" {
               description "1591.04 nm/188.425000 THz 3.125/6.25/12.5GHz spacing";
             }
             enum "1591.02" {
               description "1591.02 nm/188.428125 THz 3.125GHz spacing";
             }
             enum "1590.99" {
               description "1590.99 nm/188.431250 THz 3.125/6.25GHz spacing";
             }
             enum "1590.96" {
               description "1590.96 nm/188.434375 THz 3.125GHz spacing";
             }
             enum "1590.94" {
               description "1590.94 nm/188.437500 THz 3.125/6.25/12.5GHz spacing";
             }
             enum "1590.91" {
               description "1590.91 nm/188.440625 THz 3.125GHz spacing";
             }
             enum "1590.89" {
               description "1590.89 nm/188.443750 THz 3.125/6.25GHz spacing";
             }
             enum "1590.86" {
               description "1590.86 nm/188.446875 THz 3.125GHz spacing";
             }
             enum "1590.83" {
               description "1590.83 nm/188.450000 THz 3.125/6.25/12.5/50/75GHz spacing";
             }
             enum "1590.81" {
               description "1590.81 nm/188.453125 THz 3.125GHz spacing";
             }
             enum "1590.78" {
               description "1590.78 nm/188.456250 THz 3.125/6.25GHz spacing";
             }
             enum "1590.75" {
               description "1590.75 nm/188.459375 THz 3.125GHz spacing";
             }
             enum "1590.73" {
               description "1590.73 nm/188.462500 THz 3.125/6.25/12.5GHz spacing";
             }
             enum "1590.70" {
               description "1590.70 nm/188.465625 THz 3.125GHz spacing";
             }
             enum "1590.67" {
               description "1590.67 nm/188.468750 THz 3.125/6.25GHz spacing";
             }
             enum "1590.65" {
               description "1590.65 nm/188.471875 THz 3.125GHz spacing";
             }
             enum "1590.62" {
               description "1590.62 nm/188.475000 THz 3.125/6.25/12.5GHz spacing";
             }
             enum "1590.60" {
               description "1590.60 nm/188.478125 THz 3.125GHz spacing";
             }
             enum "1590.57" {
               description "1590.57 nm/188.481250 THz 3.125/6.25GHz spacing";
             }
             enum "1590.54" {
               description "1590.54 nm/188.484375 THz 3.125GHz spacing";
             }
             enum "1590.52" {
               description "1590.52 nm/188.487500 THz 3.125/6.25/12.5GHz spacing";
             }
             enum "1590.49" {
               description "1590.49 nm/188.490625 THz 3.125GHz spacing";
             }
             enum "1590.46" {
               description "1590.46 nm/188.493750 THz 3.125/6.25GHz spacing";
             }
             enum "1590.44" {
               description "1590.44 nm/188.496875 THz 3.125GHz spacing";
             }
             enum "1590.41" {
               description "1590.41 nm/188.500000 THz 3.125/6.25/12.5/100GHz spacing";
             }
             enum "1590.38" {
               description "1590.38 nm/188.503125 THz 3.125GHz spacing";
             }
             enum "1590.36" {
               description "1590.36 nm/188.506250 THz 3.125/6.25GHz spacing";
             }
             enum "1590.33" {
               description "1590.33 nm/188.509375 THz 3.125GHz spacing";
             }
             enum "1590.31" {
               description "1590.31 nm/188.512500 THz 3.125/6.25/12.5GHz spacing";
             }
             enum "1590.28" {
               description "1590.28 nm/188.515625 THz 3.125GHz spacing";
             }
             enum "1590.25" {
               description "1590.25 nm/188.518750 THz 3.125/6.25GHz spacing";
             }
             enum "1590.23" {
               description "1590.23 nm/188.521875 THz 3.125GHz spacing";
             }
             enum "1590.20" {
               description "1590.20 nm/188.525000 THz 3.125/6.25/12.5/75GHz spacing";
             }
             enum "1590.17" {
               description "1590.17 nm/188.528125 THz 3.125GHz spacing";
             }
             enum "1590.15" {
               description "1590.15 nm/188.531250 THz 3.125/6.25GHz spacing";
             }
             enum "1590.12" {
               description "1590.12 nm/188.534375 THz 3.125GHz spacing";
             }
             enum "1590.09" {
               description "1590.09 nm/188.537500 THz 3.125/6.25/12.5GHz spacing";
             }
             enum "1590.07" {
               description "1590.07 nm/188.540625 THz 3.125GHz spacing";
             }
             enum "1590.04" {
               description "1590.04 nm/188.543750 THz 3.125/6.25GHz spacing";
             }
             enum "1590.02" {
               description "1590.02 nm/188.546875 THz 3.125GHz spacing";
             }
             enum "1589.99" {
               description "1589.99 nm/188.550000 THz 3.125/6.25/12.5/50GHz spacing";
             }
             enum "1589.96" {
               description "1589.96 nm/188.553125 THz 3.125GHz spacing";
             }
             enum "1589.94" {
               description "1589.94 nm/188.556250 THz 3.125/6.25GHz spacing";
             }
             enum "1589.91" {
               description "1589.91 nm/188.559375 THz 3.125GHz spacing";
             }
             enum "1589.88" {
               description "1589.88 nm/188.562500 THz 3.125/6.25/12.5GHz spacing";
             }
             enum "1589.86" {
               description "1589.86 nm/188.565625 THz 3.125GHz spacing";
             }
             enum "1589.83" {
               description "1589.83 nm/188.568750 THz 3.125/6.25GHz spacing";
             }
             enum "1589.80" {
               description "1589.80 nm/188.571875 THz 3.125GHz spacing";
             }
             enum "1589.78" {
               description "1589.78 nm/188.575000 THz 3.125/6.25/12.5GHz spacing";
             }
             enum "1589.75" {
               description "1589.75 nm/188.578125 THz 3.125GHz spacing";
             }
             enum "1589.73" {
               description "1589.73 nm/188.581250 THz 3.125/6.25GHz spacing";
             }
             enum "1589.70" {
               description "1589.70 nm/188.584375 THz 3.125GHz spacing";
             }
             enum "1589.67" {
               description "1589.67 nm/188.587500 THz 3.125/6.25/12.5GHz spacing";
             }
             enum "1589.65" {
               description "1589.65 nm/188.590625 THz 3.125GHz spacing";
             }
             enum "1589.62" {
               description "1589.62 nm/188.593750 THz 3.125/6.25GHz spacing";
             }
             enum "1589.59" {
               description "1589.59 nm/188.596875 THz 3.125GHz spacing";
             }
             enum "1589.57" {
               description "1589.57 nm/188.600000 THz 3.125/6.25/12.5/100GHz spacing";
             }
             enum "1589.54" {
               description "1589.54 nm/188.603125 THz 3.125GHz spacing";
             }
             enum "1589.51" {
               description "1589.51 nm/188.606250 THz 3.125/6.25GHz spacing";
             }
             enum "1589.49" {
               description "1589.49 nm/188.609375 THz 3.125GHz spacing";
             }
             enum "1589.46" {
               description "1589.46 nm/188.612500 THz 3.125/6.25/12.5GHz spacing";
             }
             enum "1589.44" {
               description "1589.44 nm/188.615625 THz 3.125GHz spacing";
             }
             enum "1589.41" {
               description "1589.41 nm/188.618750 THz 3.125/6.25GHz spacing";
             }
             enum "1589.38" {
               description "1589.38 nm/188.621875 THz 3.125GHz spacing";
             }
             enum "1589.36" {
               description "1589.36 nm/188.625000 THz 3.125/6.25/12.5GHz spacing";
             }
             enum "1589.33" {
               description "1589.33 nm/188.628125 THz 3.125GHz spacing";
             }
             enum "1589.30" {
               description "1589.30 nm/188.631250 THz 3.125/6.25GHz spacing";
             }
             enum "1589.28" {
               description "1589.28 nm/188.634375 THz 3.125GHz spacing";
             }
             enum "1589.25" {
               description "1589.25 nm/188.637500 THz 3.125/6.25/12.5GHz spacing";
             }
             enum "1589.23" {
               description "1589.23 nm/188.640625 THz 3.125GHz spacing";
             }
             enum "1589.20" {
               description "1589.20 nm/188.643750 THz 3.125/6.25GHz spacing";
             }
             enum "1589.17" {
               description "1589.17 nm/188.646875 THz 3.125GHz spacing";
             }
             enum "1589.15" {
               description "1589.15 nm/188.650000 THz 3.125/6.25/12.5/50GHz spacing";
             }
             enum "1589.12" {
               description "1589.12 nm/188.653125 THz 3.125GHz spacing";
             }
             enum "1589.09" {
               description "1589.09 nm/188.656250 THz 3.125/6.25GHz spacing";
             }
             enum "1589.07" {
               description "1589.07 nm/188.659375 THz 3.125GHz spacing";
             }
             enum "1589.04" {
               description "1589.04 nm/188.662500 THz 3.125/6.25/12.5GHz spacing";
             }
             enum "1589.01" {
               description "1589.01 nm/188.665625 THz 3.125GHz spacing";
             }
             enum "1588.99" {
               description "1588.99 nm/188.668750 THz 3.125/6.25GHz spacing";
             }
             enum "1588.96" {
               description "1588.96 nm/188.671875 THz 3.125GHz spacing";
             }
             enum "1588.94" {
               description "1588.94 nm/188.675000 THz 3.125/6.25/12.5/75GHz spacing";
             }
             enum "1588.91" {
               description "1588.91 nm/188.678125 THz 3.125GHz spacing";
             }
             enum "1588.88" {
               description "1588.88 nm/188.681250 THz 3.125/6.25GHz spacing";
             }
             enum "1588.86" {
               description "1588.86 nm/188.684375 THz 3.125GHz spacing";
             }
             enum "1588.83" {
               description "1588.83 nm/188.687500 THz 3.125/6.25/12.5GHz spacing";
             }
             enum "1588.80" {
               description "1588.80 nm/188.690625 THz 3.125GHz spacing";
             }
             enum "1588.78" {
               description "1588.78 nm/188.693750 THz 3.125/6.25GHz spacing";
             }
             enum "1588.75" {
               description "1588.75 nm/188.696875 THz 3.125GHz spacing";
             }
             enum "1588.73" {
               description "1588.73 nm/188.700000 THz 3.125/6.25/12.5/50/75/100GHz spacing";
             }
             enum "1588.70" {
               description "1588.70 nm/188.703125 THz 3.125GHz spacing";
             }
             enum "1588.67" {
               description "1588.67 nm/188.706250 THz 3.125/6.25GHz spacing";
             }
             enum "1588.65" {
               description "1588.65 nm/188.709375 THz 3.125GHz spacing";
             }
             enum "1588.62" {
               description "1588.62 nm/188.712500 THz 3.125/6.25/12.5GHz spacing";
             }
             enum "1588.59" {
               description "1588.59 nm/188.715625 THz 3.125GHz spacing";
             }
             enum "1588.57" {
               description "1588.57 nm/188.718750 THz 3.125/6.25GHz spacing";
             }
             enum "1588.54" {
               description "1588.54 nm/188.721875 THz 3.125GHz spacing";
             }
             enum "1588.51" {
               description "1588.51 nm/188.725000 THz 3.125/6.25/12.5GHz spacing";
             }
             enum "1588.49" {
               description "1588.49 nm/188.728125 THz 3.125GHz spacing";
             }
             enum "1588.46" {
               description "1588.46 nm/188.731250 THz 3.125/6.25GHz spacing";
             }
             enum "1588.44" {
               description "1588.44 nm/188.734375 THz 3.125GHz spacing";
             }
             enum "1588.41" {
               description "1588.41 nm/188.737500 THz 3.125/6.25/12.5GHz spacing";
             }
             enum "1588.38" {
               description "1588.38 nm/188.740625 THz 3.125GHz spacing";
             }
             enum "1588.36" {
               description "1588.36 nm/188.743750 THz 3.125/6.25GHz spacing";
             }
             enum "1588.33" {
               description "1588.33 nm/188.746875 THz 3.125GHz spacing";
             }
             enum "1588.30" {
               description "1588.30 nm/188.750000 THz 3.125/6.25/12.5/50/75GHz spacing";
             }
             enum "1588.28" {
               description "1588.28 nm/188.753125 THz 3.125GHz spacing";
             }
             enum "1588.25" {
               description "1588.25 nm/188.756250 THz 3.125/6.25GHz spacing";
             }
             enum "1588.23" {
               description "1588.23 nm/188.759375 THz 3.125GHz spacing";
             }
             enum "1588.20" {
               description "1588.20 nm/188.762500 THz 3.125/6.25/12.5GHz spacing";
             }
             enum "1588.17" {
               description "1588.17 nm/188.765625 THz 3.125GHz spacing";
             }
             enum "1588.15" {
               description "1588.15 nm/188.768750 THz 3.125/6.25GHz spacing";
             }
             enum "1588.12" {
               description "1588.12 nm/188.771875 THz 3.125GHz spacing";
             }
             enum "1588.09" {
               description "1588.09 nm/188.775000 THz 3.125/6.25/12.5GHz spacing";
             }
             enum "1588.07" {
               description "1588.07 nm/188.778125 THz 3.125GHz spacing";
             }
             enum "1588.04" {
               description "1588.04 nm/188.781250 THz 3.125/6.25GHz spacing";
             }
             enum "1588.02" {
               description "1588.02 nm/188.784375 THz 3.125GHz spacing";
             }
             enum "1587.99" {
               description "1587.99 nm/188.787500 THz 3.125/6.25/12.5GHz spacing";
             }
             enum "1587.96" {
               description "1587.96 nm/188.790625 THz 3.125GHz spacing";
             }
             enum "1587.94" {
               description "1587.94 nm/188.793750 THz 3.125/6.25GHz spacing";
             }
             enum "1587.91" {
               description "1587.91 nm/188.796875 THz 3.125GHz spacing";
             }
             enum "1587.88" {
               description "1587.88 nm/188.800000 THz 3.125/6.25/12.5/100GHz spacing";
             }
             enum "1587.86" {
               description "1587.86 nm/188.803125 THz 3.125GHz spacing";
             }
             enum "1587.83" {
               description "1587.83 nm/188.806250 THz 3.125/6.25GHz spacing";
             }
             enum "1587.80" {
               description "1587.80 nm/188.809375 THz 3.125GHz spacing";
             }
             enum "1587.78" {
               description "1587.78 nm/188.812500 THz 3.125/6.25/12.5GHz spacing";
             }
             enum "1587.75" {
               description "1587.75 nm/188.815625 THz 3.125GHz spacing";
             }
             enum "1587.73" {
               description "1587.73 nm/188.818750 THz 3.125/6.25GHz spacing";
             }
             enum "1587.70" {
               description "1587.70 nm/188.821875 THz 3.125GHz spacing";
             }
             enum "1587.67" {
               description "1587.67 nm/188.825000 THz 3.125/6.25/12.5/75GHz spacing";
             }
             enum "1587.65" {
               description "1587.65 nm/188.828125 THz 3.125GHz spacing";
             }
             enum "1587.62" {
               description "1587.62 nm/188.831250 THz 3.125/6.25GHz spacing";
             }
             enum "1587.59" {
               description "1587.59 nm/188.834375 THz 3.125GHz spacing";
             }
             enum "1587.57" {
               description "1587.57 nm/188.837500 THz 3.125/6.25/12.5GHz spacing";
             }
             enum "1587.54" {
               description "1587.54 nm/188.840625 THz 3.125GHz spacing";
             }
             enum "1587.52" {
               description "1587.52 nm/188.843750 THz 3.125/6.25GHz spacing";
             }
             enum "1587.49" {
               description "1587.49 nm/188.846875 THz 3.125GHz spacing";
             }
             enum "1587.46" {
               description "1587.46 nm/188.850000 THz 3.125/6.25/12.5/50GHz spacing";
             }
             enum "1587.44" {
               description "1587.44 nm/188.853125 THz 3.125GHz spacing";
             }
             enum "1587.41" {
               description "1587.41 nm/188.856250 THz 3.125/6.25GHz spacing";
             }
             enum "1587.38" {
               description "1587.38 nm/188.859375 THz 3.125GHz spacing";
             }
             enum "1587.36" {
               description "1587.36 nm/188.862500 THz 3.125/6.25/12.5GHz spacing";
             }
             enum "1587.33" {
               description "1587.33 nm/188.865625 THz 3.125GHz spacing";
             }
             enum "1587.31" {
               description "1587.31 nm/188.868750 THz 3.125/6.25GHz spacing";
             }
             enum "1587.28" {
               description "1587.28 nm/188.871875 THz 3.125GHz spacing";
             }
             enum "1587.25" {
               description "1587.25 nm/188.875000 THz 3.125/6.25/12.5GHz spacing";
             }
             enum "1587.23" {
               description "1587.23 nm/188.878125 THz 3.125GHz spacing";
             }
             enum "1587.20" {
               description "1587.20 nm/188.881250 THz 3.125/6.25GHz spacing";
             }
             enum "1587.17" {
               description "1587.17 nm/188.884375 THz 3.125GHz spacing";
             }
             enum "1587.15" {
               description "1587.15 nm/188.887500 THz 3.125/6.25/12.5GHz spacing";
             }
             enum "1587.12" {
               description "1587.12 nm/188.890625 THz 3.125GHz spacing";
             }
             enum "1587.10" {
               description "1587.10 nm/188.893750 THz 3.125/6.25GHz spacing";
             }
             enum "1587.07" {
               description "1587.07 nm/188.896875 THz 3.125GHz spacing";
             }
             enum "1587.04" {
               description "1587.04 nm/188.900000 THz 3.125/6.25/12.5/100GHz spacing";
             }
             enum "1587.02" {
               description "1587.02 nm/188.903125 THz 3.125GHz spacing";
             }
             enum "1586.99" {
               description "1586.99 nm/188.906250 THz 3.125/6.25GHz spacing";
             }
             enum "1586.96" {
               description "1586.96 nm/188.909375 THz 3.125GHz spacing";
             }
             enum "1586.94" {
               description "1586.94 nm/188.912500 THz 3.125/6.25/12.5GHz spacing";
             }
             enum "1586.91" {
               description "1586.91 nm/188.915625 THz 3.125GHz spacing";
             }
             enum "1586.89" {
               description "1586.89 nm/188.918750 THz 3.125/6.25GHz spacing";
             }
             enum "1586.86" {
               description "1586.86 nm/188.921875 THz 3.125GHz spacing";
             }
             enum "1586.83" {
               description "1586.83 nm/188.925000 THz 3.125/6.25/12.5GHz spacing";
             }
             enum "1586.81" {
               description "1586.81 nm/188.928125 THz 3.125GHz spacing";
             }
             enum "1586.78" {
               description "1586.78 nm/188.931250 THz 3.125/6.25GHz spacing";
             }
             enum "1586.75" {
               description "1586.75 nm/188.934375 THz 3.125GHz spacing";
             }
             enum "1586.73" {
               description "1586.73 nm/188.937500 THz 3.125/6.25/12.5GHz spacing";
             }
             enum "1586.70" {
               description "1586.70 nm/188.940625 THz 3.125GHz spacing";
             }
             enum "1586.68" {
               description "1586.68 nm/188.943750 THz 3.125/6.25GHz spacing";
             }
             enum "1586.65" {
               description "1586.65 nm/188.946875 THz 3.125GHz spacing";
             }
             enum "1586.62" {
               description "1586.62 nm/188.950000 THz 3.125/6.25/12.5/50GHz spacing";
             }
             enum "1586.60" {
               description "1586.60 nm/188.953125 THz 3.125GHz spacing";
             }
             enum "1586.57" {
               description "1586.57 nm/188.956250 THz 3.125/6.25GHz spacing";
             }
             enum "1586.54" {
               description "1586.54 nm/188.959375 THz 3.125GHz spacing";
             }
             enum "1586.52" {
               description "1586.52 nm/188.962500 THz 3.125/6.25/12.5GHz spacing";
             }
             enum "1586.49" {
               description "1586.49 nm/188.965625 THz 3.125GHz spacing";
             }
             enum "1586.47" {
               description "1586.47 nm/188.968750 THz 3.125/6.25GHz spacing";
             }
             enum "1586.44" {
               description "1586.44 nm/188.971875 THz 3.125GHz spacing";
             }
             enum "1586.41" {
               description "1586.41 nm/188.975000 THz 3.125/6.25/12.5/75GHz spacing";
             }
             enum "1586.39" {
               description "1586.39 nm/188.978125 THz 3.125GHz spacing";
             }
             enum "1586.36" {
               description "1586.36 nm/188.981250 THz 3.125/6.25GHz spacing";
             }
             enum "1586.33" {
               description "1586.33 nm/188.984375 THz 3.125GHz spacing";
             }
             enum "1586.31" {
               description "1586.31 nm/188.987500 THz 3.125/6.25/12.5GHz spacing";
             }
             enum "1586.28" {
               description "1586.28 nm/188.990625 THz 3.125GHz spacing";
             }
             enum "1586.26" {
               description "1586.26 nm/188.993750 THz 3.125/6.25GHz spacing";
             }
             enum "1586.23" {
               description "1586.23 nm/188.996875 THz 3.125GHz spacing";
             }
             enum "1586.20" {
               description "1586.20 nm/189.000000 THz 3.125/6.25/12.5/50/75/100GHz spacing";
             }
             enum "1586.18" {
               description "1586.18 nm/189.003125 THz 3.125GHz spacing";
             }
             enum "1586.15" {
               description "1586.15 nm/189.006250 THz 3.125/6.25GHz spacing";
             }
             enum "1586.12" {
               description "1586.12 nm/189.009375 THz 3.125GHz spacing";
             }
             enum "1586.10" {
               description "1586.10 nm/189.012500 THz 3.125/6.25/12.5GHz spacing";
             }
             enum "1586.07" {
               description "1586.07 nm/189.015625 THz 3.125GHz spacing";
             }
             enum "1586.05" {
               description "1586.05 nm/189.018750 THz 3.125/6.25GHz spacing";
             }
             enum "1586.02" {
               description "1586.02 nm/189.021875 THz 3.125GHz spacing";
             }
             enum "1585.99" {
               description "1585.99 nm/189.025000 THz 3.125/6.25/12.5GHz spacing";
             }
             enum "1585.97" {
               description "1585.97 nm/189.028125 THz 3.125GHz spacing";
             }
             enum "1585.94" {
               description "1585.94 nm/189.031250 THz 3.125/6.25GHz spacing";
             }
             enum "1585.92" {
               description "1585.92 nm/189.034375 THz 3.125GHz spacing";
             }
             enum "1585.89" {
               description "1585.89 nm/189.037500 THz 3.125/6.25/12.5GHz spacing";
             }
             enum "1585.86" {
               description "1585.86 nm/189.040625 THz 3.125GHz spacing";
             }
             enum "1585.84" {
               description "1585.84 nm/189.043750 THz 3.125/6.25GHz spacing";
             }
             enum "1585.81" {
               description "1585.81 nm/189.046875 THz 3.125GHz spacing";
             }
             enum "1585.78" {
               description "1585.78 nm/189.050000 THz 3.125/6.25/12.5/50/75GHz spacing";
             }
             enum "1585.76" {
               description "1585.76 nm/189.053125 THz 3.125GHz spacing";
             }
             enum "1585.73" {
               description "1585.73 nm/189.056250 THz 3.125/6.25GHz spacing";
             }
             enum "1585.71" {
               description "1585.71 nm/189.059375 THz 3.125GHz spacing";
             }
             enum "1585.68" {
               description "1585.68 nm/189.062500 THz 3.125/6.25/12.5GHz spacing";
             }
             enum "1585.65" {
               description "1585.65 nm/189.065625 THz 3.125GHz spacing";
             }
             enum "1585.63" {
               description "1585.63 nm/189.068750 THz 3.125/6.25GHz spacing";
             }
             enum "1585.60" {
               description "1585.60 nm/189.071875 THz 3.125GHz spacing";
             }
             enum "1585.57" {
               description "1585.57 nm/189.075000 THz 3.125/6.25/12.5GHz spacing";
             }
             enum "1585.55" {
               description "1585.55 nm/189.078125 THz 3.125GHz spacing";
             }
             enum "1585.52" {
               description "1585.52 nm/189.081250 THz 3.125/6.25GHz spacing";
             }
             enum "1585.50" {
               description "1585.50 nm/189.084375 THz 3.125GHz spacing";
             }
             enum "1585.47" {
               description "1585.47 nm/189.087500 THz 3.125/6.25/12.5GHz spacing";
             }
             enum "1585.44" {
               description "1585.44 nm/189.090625 THz 3.125GHz spacing";
             }
             enum "1585.42" {
               description "1585.42 nm/189.093750 THz 3.125/6.25GHz spacing";
             }
             enum "1585.39" {
               description "1585.39 nm/189.096875 THz 3.125GHz spacing";
             }
             enum "1585.36" {
               description "1585.36 nm/189.100000 THz 3.125/6.25/12.5/100GHz spacing";
             }
             enum "1585.34" {
               description "1585.34 nm/189.103125 THz 3.125GHz spacing";
             }
             enum "1585.31" {
               description "1585.31 nm/189.106250 THz 3.125/6.25GHz spacing";
             }
             enum "1585.29" {
               description "1585.29 nm/189.109375 THz 3.125GHz spacing";
             }
             enum "1585.26" {
               description "1585.26 nm/189.112500 THz 3.125/6.25/12.5GHz spacing";
             }
             enum "1585.23" {
               description "1585.23 nm/189.115625 THz 3.125GHz spacing";
             }
             enum "1585.21" {
               description "1585.21 nm/189.118750 THz 3.125/6.25GHz spacing";
             }
             enum "1585.18" {
               description "1585.18 nm/189.121875 THz 3.125GHz spacing";
             }
             enum "1585.16" {
               description "1585.16 nm/189.125000 THz 3.125/6.25/12.5/75GHz spacing";
             }
             enum "1585.13" {
               description "1585.13 nm/189.128125 THz 3.125GHz spacing";
             }
             enum "1585.10" {
               description "1585.10 nm/189.131250 THz 3.125/6.25GHz spacing";
             }
             enum "1585.08" {
               description "1585.08 nm/189.134375 THz 3.125GHz spacing";
             }
             enum "1585.05" {
               description "1585.05 nm/189.137500 THz 3.125/6.25/12.5GHz spacing";
             }
             enum "1585.02" {
               description "1585.02 nm/189.140625 THz 3.125GHz spacing";
             }
             enum "1585.00" {
               description "1585.00 nm/189.143750 THz 3.125/6.25GHz spacing";
             }
             enum "1584.97" {
               description "1584.97 nm/189.146875 THz 3.125GHz spacing";
             }
             enum "1584.95" {
               description "1584.95 nm/189.150000 THz 3.125/6.25/12.5/50GHz spacing";
             }
             enum "1584.92" {
               description "1584.92 nm/189.153125 THz 3.125GHz spacing";
             }
             enum "1584.89" {
               description "1584.89 nm/189.156250 THz 3.125/6.25GHz spacing";
             }
             enum "1584.87" {
               description "1584.87 nm/189.159375 THz 3.125GHz spacing";
             }
             enum "1584.84" {
               description "1584.84 nm/189.162500 THz 3.125/6.25/12.5GHz spacing";
             }
             enum "1584.81" {
               description "1584.81 nm/189.165625 THz 3.125GHz spacing";
             }
             enum "1584.79" {
               description "1584.79 nm/189.168750 THz 3.125/6.25GHz spacing";
             }
             enum "1584.76" {
               description "1584.76 nm/189.171875 THz 3.125GHz spacing";
             }
             enum "1584.74" {
               description "1584.74 nm/189.175000 THz 3.125/6.25/12.5GHz spacing";
             }
             enum "1584.71" {
               description "1584.71 nm/189.178125 THz 3.125GHz spacing";
             }
             enum "1584.68" {
               description "1584.68 nm/189.181250 THz 3.125/6.25GHz spacing";
             }
             enum "1584.66" {
               description "1584.66 nm/189.184375 THz 3.125GHz spacing";
             }
             enum "1584.63" {
               description "1584.63 nm/189.187500 THz 3.125/6.25/12.5GHz spacing";
             }
             enum "1584.61" {
               description "1584.61 nm/189.190625 THz 3.125GHz spacing";
             }
             enum "1584.58" {
               description "1584.58 nm/189.193750 THz 3.125/6.25GHz spacing";
             }
             enum "1584.55" {
               description "1584.55 nm/189.196875 THz 3.125GHz spacing";
             }
             enum "1584.53" {
               description "1584.53 nm/189.200000 THz 3.125/6.25/12.5/100GHz spacing";
             }
             enum "1584.50" {
               description "1584.50 nm/189.203125 THz 3.125GHz spacing";
             }
             enum "1584.47" {
               description "1584.47 nm/189.206250 THz 3.125/6.25GHz spacing";
             }
             enum "1584.45" {
               description "1584.45 nm/189.209375 THz 3.125GHz spacing";
             }
             enum "1584.42" {
               description "1584.42 nm/189.212500 THz 3.125/6.25/12.5GHz spacing";
             }
             enum "1584.40" {
               description "1584.40 nm/189.215625 THz 3.125GHz spacing";
             }
             enum "1584.37" {
               description "1584.37 nm/189.218750 THz 3.125/6.25GHz spacing";
             }
             enum "1584.34" {
               description "1584.34 nm/189.221875 THz 3.125GHz spacing";
             }
             enum "1584.32" {
               description "1584.32 nm/189.225000 THz 3.125/6.25/12.5GHz spacing";
             }
             enum "1584.29" {
               description "1584.29 nm/189.228125 THz 3.125GHz spacing";
             }
             enum "1584.27" {
               description "1584.27 nm/189.231250 THz 3.125/6.25GHz spacing";
             }
             enum "1584.24" {
               description "1584.24 nm/189.234375 THz 3.125GHz spacing";
             }
             enum "1584.21" {
               description "1584.21 nm/189.237500 THz 3.125/6.25/12.5GHz spacing";
             }
             enum "1584.19" {
               description "1584.19 nm/189.240625 THz 3.125GHz spacing";
             }
             enum "1584.16" {
               description "1584.16 nm/189.243750 THz 3.125/6.25GHz spacing";
             }
             enum "1584.13" {
               description "1584.13 nm/189.246875 THz 3.125GHz spacing";
             }
             enum "1584.11" {
               description "1584.11 nm/189.250000 THz 3.125/6.25/12.5/50GHz spacing";
             }
             enum "1584.08" {
               description "1584.08 nm/189.253125 THz 3.125GHz spacing";
             }
             enum "1584.06" {
               description "1584.06 nm/189.256250 THz 3.125/6.25GHz spacing";
             }
             enum "1584.03" {
               description "1584.03 nm/189.259375 THz 3.125GHz spacing";
             }
             enum "1584.00" {
               description "1584.00 nm/189.262500 THz 3.125/6.25/12.5GHz spacing";
             }
             enum "1583.98" {
               description "1583.98 nm/189.265625 THz 3.125GHz spacing";
             }
             enum "1583.95" {
               description "1583.95 nm/189.268750 THz 3.125/6.25GHz spacing";
             }
             enum "1583.93" {
               description "1583.93 nm/189.271875 THz 3.125GHz spacing";
             }
             enum "1583.90" {
               description "1583.90 nm/189.275000 THz 3.125/6.25/12.5/75GHz spacing";
             }
             enum "1583.87" {
               description "1583.87 nm/189.278125 THz 3.125GHz spacing";
             }
             enum "1583.85" {
               description "1583.85 nm/189.281250 THz 3.125/6.25GHz spacing";
             }
             enum "1583.82" {
               description "1583.82 nm/189.284375 THz 3.125GHz spacing";
             }
             enum "1583.79" {
               description "1583.79 nm/189.287500 THz 3.125/6.25/12.5GHz spacing";
             }
             enum "1583.77" {
               description "1583.77 nm/189.290625 THz 3.125GHz spacing";
             }
             enum "1583.74" {
               description "1583.74 nm/189.293750 THz 3.125/6.25GHz spacing";
             }
             enum "1583.72" {
               description "1583.72 nm/189.296875 THz 3.125GHz spacing";
             }
             enum "1583.69" {
               description "1583.69 nm/189.300000 THz 3.125/6.25/12.5/50/75/100GHz spacing";
             }
             enum "1583.66" {
               description "1583.66 nm/189.303125 THz 3.125GHz spacing";
             }
             enum "1583.64" {
               description "1583.64 nm/189.306250 THz 3.125/6.25GHz spacing";
             }
             enum "1583.61" {
               description "1583.61 nm/189.309375 THz 3.125GHz spacing";
             }
             enum "1583.59" {
               description "1583.59 nm/189.312500 THz 3.125/6.25/12.5GHz spacing";
             }
             enum "1583.56" {
               description "1583.56 nm/189.315625 THz 3.125GHz spacing";
             }
             enum "1583.53" {
               description "1583.53 nm/189.318750 THz 3.125/6.25GHz spacing";
             }
             enum "1583.51" {
               description "1583.51 nm/189.321875 THz 3.125GHz spacing";
             }
             enum "1583.48" {
               description "1583.48 nm/189.325000 THz 3.125/6.25/12.5GHz spacing";
             }
             enum "1583.45" {
               description "1583.45 nm/189.328125 THz 3.125GHz spacing";
             }
             enum "1583.43" {
               description "1583.43 nm/189.331250 THz 3.125/6.25GHz spacing";
             }
             enum "1583.40" {
               description "1583.40 nm/189.334375 THz 3.125GHz spacing";
             }
             enum "1583.38" {
               description "1583.38 nm/189.337500 THz 3.125/6.25/12.5GHz spacing";
             }
             enum "1583.35" {
               description "1583.35 nm/189.340625 THz 3.125GHz spacing";
             }
             enum "1583.32" {
               description "1583.32 nm/189.343750 THz 3.125/6.25GHz spacing";
             }
             enum "1583.30" {
               description "1583.30 nm/189.346875 THz 3.125GHz spacing";
             }
             enum "1583.27" {
               description "1583.27 nm/189.350000 THz 3.125/6.25/12.5/50/75GHz spacing";
             }
             enum "1583.25" {
               description "1583.25 nm/189.353125 THz 3.125GHz spacing";
             }
             enum "1583.22" {
               description "1583.22 nm/189.356250 THz 3.125/6.25GHz spacing";
             }
             enum "1583.19" {
               description "1583.19 nm/189.359375 THz 3.125GHz spacing";
             }
             enum "1583.17" {
               description "1583.17 nm/189.362500 THz 3.125/6.25/12.5GHz spacing";
             }
             enum "1583.14" {
               description "1583.14 nm/189.365625 THz 3.125GHz spacing";
             }
             enum "1583.11" {
               description "1583.11 nm/189.368750 THz 3.125/6.25GHz spacing";
             }
             enum "1583.09" {
               description "1583.09 nm/189.371875 THz 3.125GHz spacing";
             }
             enum "1583.06" {
               description "1583.06 nm/189.375000 THz 3.125/6.25/12.5GHz spacing";
             }
             enum "1583.04" {
               description "1583.04 nm/189.378125 THz 3.125GHz spacing";
             }
             enum "1583.01" {
               description "1583.01 nm/189.381250 THz 3.125/6.25GHz spacing";
             }
             enum "1582.98" {
               description "1582.98 nm/189.384375 THz 3.125GHz spacing";
             }
             enum "1582.96" {
               description "1582.96 nm/189.387500 THz 3.125/6.25/12.5GHz spacing";
             }
             enum "1582.93" {
               description "1582.93 nm/189.390625 THz 3.125GHz spacing";
             }
             enum "1582.91" {
               description "1582.91 nm/189.393750 THz 3.125/6.25GHz spacing";
             }
             enum "1582.88" {
               description "1582.88 nm/189.396875 THz 3.125GHz spacing";
             }
             enum "1582.85" {
               description "1582.85 nm/189.400000 THz 3.125/6.25/12.5/100GHz spacing";
             }
             enum "1582.83" {
               description "1582.83 nm/189.403125 THz 3.125GHz spacing";
             }
             enum "1582.80" {
               description "1582.80 nm/189.406250 THz 3.125/6.25GHz spacing";
             }
             enum "1582.78" {
               description "1582.78 nm/189.409375 THz 3.125GHz spacing";
             }
             enum "1582.75" {
               description "1582.75 nm/189.412500 THz 3.125/6.25/12.5GHz spacing";
             }
             enum "1582.72" {
               description "1582.72 nm/189.415625 THz 3.125GHz spacing";
             }
             enum "1582.70" {
               description "1582.70 nm/189.418750 THz 3.125/6.25GHz spacing";
             }
             enum "1582.67" {
               description "1582.67 nm/189.421875 THz 3.125GHz spacing";
             }
             enum "1582.64" {
               description "1582.64 nm/189.425000 THz 3.125/6.25/12.5/75GHz spacing";
             }
             enum "1582.62" {
               description "1582.62 nm/189.428125 THz 3.125GHz spacing";
             }
             enum "1582.59" {
               description "1582.59 nm/189.431250 THz 3.125/6.25GHz spacing";
             }
             enum "1582.57" {
               description "1582.57 nm/189.434375 THz 3.125GHz spacing";
             }
             enum "1582.54" {
               description "1582.54 nm/189.437500 THz 3.125/6.25/12.5GHz spacing";
             }
             enum "1582.51" {
               description "1582.51 nm/189.440625 THz 3.125GHz spacing";
             }
             enum "1582.49" {
               description "1582.49 nm/189.443750 THz 3.125/6.25GHz spacing";
             }
             enum "1582.46" {
               description "1582.46 nm/189.446875 THz 3.125GHz spacing";
             }
             enum "1582.44" {
               description "1582.44 nm/189.450000 THz 3.125/6.25/12.5/50GHz spacing";
             }
             enum "1582.41" {
               description "1582.41 nm/189.453125 THz 3.125GHz spacing";
             }
             enum "1582.38" {
               description "1582.38 nm/189.456250 THz 3.125/6.25GHz spacing";
             }
             enum "1582.36" {
               description "1582.36 nm/189.459375 THz 3.125GHz spacing";
             }
             enum "1582.33" {
               description "1582.33 nm/189.462500 THz 3.125/6.25/12.5GHz spacing";
             }
             enum "1582.31" {
               description "1582.31 nm/189.465625 THz 3.125GHz spacing";
             }
             enum "1582.28" {
               description "1582.28 nm/189.468750 THz 3.125/6.25GHz spacing";
             }
             enum "1582.25" {
               description "1582.25 nm/189.471875 THz 3.125GHz spacing";
             }
             enum "1582.23" {
               description "1582.23 nm/189.475000 THz 3.125/6.25/12.5GHz spacing";
             }
             enum "1582.20" {
               description "1582.20 nm/189.478125 THz 3.125GHz spacing";
             }
             enum "1582.17" {
               description "1582.17 nm/189.481250 THz 3.125/6.25GHz spacing";
             }
             enum "1582.15" {
               description "1582.15 nm/189.484375 THz 3.125GHz spacing";
             }
             enum "1582.12" {
               description "1582.12 nm/189.487500 THz 3.125/6.25/12.5GHz spacing";
             }
             enum "1582.10" {
               description "1582.10 nm/189.490625 THz 3.125GHz spacing";
             }
             enum "1582.07" {
               description "1582.07 nm/189.493750 THz 3.125/6.25GHz spacing";
             }
             enum "1582.04" {
               description "1582.04 nm/189.496875 THz 3.125GHz spacing";
             }
             enum "1582.02" {
               description "1582.02 nm/189.500000 THz 3.125/6.25/12.5/100GHz spacing";
             }
             enum "1581.99" {
               description "1581.99 nm/189.503125 THz 3.125GHz spacing";
             }
             enum "1581.97" {
               description "1581.97 nm/189.506250 THz 3.125/6.25GHz spacing";
             }
             enum "1581.94" {
               description "1581.94 nm/189.509375 THz 3.125GHz spacing";
             }
             enum "1581.91" {
               description "1581.91 nm/189.512500 THz 3.125/6.25/12.5GHz spacing";
             }
             enum "1581.89" {
               description "1581.89 nm/189.515625 THz 3.125GHz spacing";
             }
             enum "1581.86" {
               description "1581.86 nm/189.518750 THz 3.125/6.25GHz spacing";
             }
             enum "1581.84" {
               description "1581.84 nm/189.521875 THz 3.125GHz spacing";
             }
             enum "1581.81" {
               description "1581.81 nm/189.525000 THz 3.125/6.25/12.5GHz spacing";
             }
             enum "1581.78" {
               description "1581.78 nm/189.528125 THz 3.125GHz spacing";
             }
             enum "1581.76" {
               description "1581.76 nm/189.531250 THz 3.125/6.25GHz spacing";
             }
             enum "1581.73" {
               description "1581.73 nm/189.534375 THz 3.125GHz spacing";
             }
             enum "1581.71" {
               description "1581.71 nm/189.537500 THz 3.125/6.25/12.5GHz spacing";
             }
             enum "1581.68" {
               description "1581.68 nm/189.540625 THz 3.125GHz spacing";
             }
             enum "1581.65" {
               description "1581.65 nm/189.543750 THz 3.125/6.25GHz spacing";
             }
             enum "1581.63" {
               description "1581.63 nm/189.546875 THz 3.125GHz spacing";
             }
             enum "1581.60" {
               description "1581.60 nm/189.550000 THz 3.125/6.25/12.5/50GHz spacing";
             }
             enum "1581.57" {
               description "1581.57 nm/189.553125 THz 3.125GHz spacing";
             }
             enum "1581.55" {
               description "1581.55 nm/189.556250 THz 3.125/6.25GHz spacing";
             }
             enum "1581.52" {
               description "1581.52 nm/189.559375 THz 3.125GHz spacing";
             }
             enum "1581.50" {
               description "1581.50 nm/189.562500 THz 3.125/6.25/12.5GHz spacing";
             }
             enum "1581.47" {
               description "1581.47 nm/189.565625 THz 3.125GHz spacing";
             }
             enum "1581.44" {
               description "1581.44 nm/189.568750 THz 3.125/6.25GHz spacing";
             }
             enum "1581.42" {
               description "1581.42 nm/189.571875 THz 3.125GHz spacing";
             }
             enum "1581.39" {
               description "1581.39 nm/189.575000 THz 3.125/6.25/12.5/75GHz spacing";
             }
             enum "1581.37" {
               description "1581.37 nm/189.578125 THz 3.125GHz spacing";
             }
             enum "1581.34" {
               description "1581.34 nm/189.581250 THz 3.125/6.25GHz spacing";
             }
             enum "1581.31" {
               description "1581.31 nm/189.584375 THz 3.125GHz spacing";
             }
             enum "1581.29" {
               description "1581.29 nm/189.587500 THz 3.125/6.25/12.5GHz spacing";
             }
             enum "1581.26" {
               description "1581.26 nm/189.590625 THz 3.125GHz spacing";
             }
             enum "1581.24" {
               description "1581.24 nm/189.593750 THz 3.125/6.25GHz spacing";
             }
             enum "1581.21" {
               description "1581.21 nm/189.596875 THz 3.125GHz spacing";
             }
             enum "1581.18" {
               description "1581.18 nm/189.600000 THz 3.125/6.25/12.5/50/75/100GHz spacing";
             }
             enum "1581.16" {
               description "1581.16 nm/189.603125 THz 3.125GHz spacing";
             }
             enum "1581.13" {
               description "1581.13 nm/189.606250 THz 3.125/6.25GHz spacing";
             }
             enum "1581.11" {
               description "1581.11 nm/189.609375 THz 3.125GHz spacing";
             }
             enum "1581.08" {
               description "1581.08 nm/189.612500 THz 3.125/6.25/12.5GHz spacing";
             }
             enum "1581.05" {
               description "1581.05 nm/189.615625 THz 3.125GHz spacing";
             }
             enum "1581.03" {
               description "1581.03 nm/189.618750 THz 3.125/6.25GHz spacing";
             }
             enum "1581.00" {
               description "1581.00 nm/189.621875 THz 3.125GHz spacing";
             }
             enum "1580.98" {
               description "1580.98 nm/189.625000 THz 3.125/6.25/12.5GHz spacing";
             }
             enum "1580.95" {
               description "1580.95 nm/189.628125 THz 3.125GHz spacing";
             }
             enum "1580.92" {
               description "1580.92 nm/189.631250 THz 3.125/6.25GHz spacing";
             }
             enum "1580.90" {
               description "1580.90 nm/189.634375 THz 3.125GHz spacing";
             }
             enum "1580.87" {
               description "1580.87 nm/189.637500 THz 3.125/6.25/12.5GHz spacing";
             }
             enum "1580.85" {
               description "1580.85 nm/189.640625 THz 3.125GHz spacing";
             }
             enum "1580.82" {
               description "1580.82 nm/189.643750 THz 3.125/6.25GHz spacing";
             }
             enum "1580.79" {
               description "1580.79 nm/189.646875 THz 3.125GHz spacing";
             }
             enum "1580.77" {
               description "1580.77 nm/189.650000 THz 3.125/6.25/12.5/50/75GHz spacing";
             }
             enum "1580.74" {
               description "1580.74 nm/189.653125 THz 3.125GHz spacing";
             }
             enum "1580.71" {
               description "1580.71 nm/189.656250 THz 3.125/6.25GHz spacing";
             }
             enum "1580.69" {
               description "1580.69 nm/189.659375 THz 3.125GHz spacing";
             }
             enum "1580.66" {
               description "1580.66 nm/189.662500 THz 3.125/6.25/12.5GHz spacing";
             }
             enum "1580.64" {
               description "1580.64 nm/189.665625 THz 3.125GHz spacing";
             }
             enum "1580.61" {
               description "1580.61 nm/189.668750 THz 3.125/6.25GHz spacing";
             }
             enum "1580.58" {
               description "1580.58 nm/189.671875 THz 3.125GHz spacing";
             }
             enum "1580.56" {
               description "1580.56 nm/189.675000 THz 3.125/6.25/12.5GHz spacing";
             }
             enum "1580.53" {
               description "1580.53 nm/189.678125 THz 3.125GHz spacing";
             }
             enum "1580.51" {
               description "1580.51 nm/189.681250 THz 3.125/6.25GHz spacing";
             }
             enum "1580.48" {
               description "1580.48 nm/189.684375 THz 3.125GHz spacing";
             }
             enum "1580.45" {
               description "1580.45 nm/189.687500 THz 3.125/6.25/12.5GHz spacing";
             }
             enum "1580.43" {
               description "1580.43 nm/189.690625 THz 3.125GHz spacing";
             }
             enum "1580.40" {
               description "1580.40 nm/189.693750 THz 3.125/6.25GHz spacing";
             }
             enum "1580.38" {
               description "1580.38 nm/189.696875 THz 3.125GHz spacing";
             }
             enum "1580.35" {
               description "1580.35 nm/189.700000 THz 3.125/6.25/12.5/100GHz spacing";
             }
             enum "1580.32" {
               description "1580.32 nm/189.703125 THz 3.125GHz spacing";
             }
             enum "1580.30" {
               description "1580.30 nm/189.706250 THz 3.125/6.25GHz spacing";
             }
             enum "1580.27" {
               description "1580.27 nm/189.709375 THz 3.125GHz spacing";
             }
             enum "1580.25" {
               description "1580.25 nm/189.712500 THz 3.125/6.25/12.5GHz spacing";
             }
             enum "1580.22" {
               description "1580.22 nm/189.715625 THz 3.125GHz spacing";
             }
             enum "1580.19" {
               description "1580.19 nm/189.718750 THz 3.125/6.25GHz spacing";
             }
             enum "1580.17" {
               description "1580.17 nm/189.721875 THz 3.125GHz spacing";
             }
             enum "1580.14" {
               description "1580.14 nm/189.725000 THz 3.125/6.25/12.5/75GHz spacing";
             }
             enum "1580.12" {
               description "1580.12 nm/189.728125 THz 3.125GHz spacing";
             }
             enum "1580.09" {
               description "1580.09 nm/189.731250 THz 3.125/6.25GHz spacing";
             }
             enum "1580.06" {
               description "1580.06 nm/189.734375 THz 3.125GHz spacing";
             }
             enum "1580.04" {
               description "1580.04 nm/189.737500 THz 3.125/6.25/12.5GHz spacing";
             }
             enum "1580.01" {
               description "1580.01 nm/189.740625 THz 3.125GHz spacing";
             }
             enum "1579.99" {
               description "1579.99 nm/189.743750 THz 3.125/6.25GHz spacing";
             }
             enum "1579.96" {
               description "1579.96 nm/189.746875 THz 3.125GHz spacing";
             }
             enum "1579.93" {
               description "1579.93 nm/189.750000 THz 3.125/6.25/12.5/50GHz spacing";
             }
             enum "1579.91" {
               description "1579.91 nm/189.753125 THz 3.125GHz spacing";
             }
             enum "1579.88" {
               description "1579.88 nm/189.756250 THz 3.125/6.25GHz spacing";
             }
             enum "1579.86" {
               description "1579.86 nm/189.759375 THz 3.125GHz spacing";
             }
             enum "1579.83" {
               description "1579.83 nm/189.762500 THz 3.125/6.25/12.5GHz spacing";
             }
             enum "1579.80" {
               description "1579.80 nm/189.765625 THz 3.125GHz spacing";
             }
             enum "1579.78" {
               description "1579.78 nm/189.768750 THz 3.125/6.25GHz spacing";
             }
             enum "1579.75" {
               description "1579.75 nm/189.771875 THz 3.125GHz spacing";
             }
             enum "1579.73" {
               description "1579.73 nm/189.775000 THz 3.125/6.25/12.5GHz spacing";
             }
             enum "1579.70" {
               description "1579.70 nm/189.778125 THz 3.125GHz spacing";
             }
             enum "1579.67" {
               description "1579.67 nm/189.781250 THz 3.125/6.25GHz spacing";
             }
             enum "1579.65" {
               description "1579.65 nm/189.784375 THz 3.125GHz spacing";
             }
             enum "1579.62" {
               description "1579.62 nm/189.787500 THz 3.125/6.25/12.5GHz spacing";
             }
             enum "1579.60" {
               description "1579.60 nm/189.790625 THz 3.125GHz spacing";
             }
             enum "1579.57" {
               description "1579.57 nm/189.793750 THz 3.125/6.25GHz spacing";
             }
             enum "1579.54" {
               description "1579.54 nm/189.796875 THz 3.125GHz spacing";
             }
             enum "1579.52" {
               description "1579.52 nm/189.800000 THz 3.125/6.25/12.5/100GHz spacing";
             }
             enum "1579.49" {
               description "1579.49 nm/189.803125 THz 3.125GHz spacing";
             }
             enum "1579.47" {
               description "1579.47 nm/189.806250 THz 3.125/6.25GHz spacing";
             }
             enum "1579.44" {
               description "1579.44 nm/189.809375 THz 3.125GHz spacing";
             }
             enum "1579.41" {
               description "1579.41 nm/189.812500 THz 3.125/6.25/12.5GHz spacing";
             }
             enum "1579.39" {
               description "1579.39 nm/189.815625 THz 3.125GHz spacing";
             }
             enum "1579.36" {
               description "1579.36 nm/189.818750 THz 3.125/6.25GHz spacing";
             }
             enum "1579.34" {
               description "1579.34 nm/189.821875 THz 3.125GHz spacing";
             }
             enum "1579.31" {
               description "1579.31 nm/189.825000 THz 3.125/6.25/12.5GHz spacing";
             }
             enum "1579.28" {
               description "1579.28 nm/189.828125 THz 3.125GHz spacing";
             }
             enum "1579.26" {
               description "1579.26 nm/189.831250 THz 3.125/6.25GHz spacing";
             }
             enum "1579.23" {
               description "1579.23 nm/189.834375 THz 3.125GHz spacing";
             }
             enum "1579.21" {
               description "1579.21 nm/189.837500 THz 3.125/6.25/12.5GHz spacing";
             }
             enum "1579.18" {
               description "1579.18 nm/189.840625 THz 3.125GHz spacing";
             }
             enum "1579.15" {
               description "1579.15 nm/189.843750 THz 3.125/6.25GHz spacing";
             }
             enum "1579.13" {
               description "1579.13 nm/189.846875 THz 3.125GHz spacing";
             }
             enum "1579.10" {
               description "1579.10 nm/189.850000 THz 3.125/6.25/12.5/50GHz spacing";
             }
             enum "1579.08" {
               description "1579.08 nm/189.853125 THz 3.125GHz spacing";
             }
             enum "1579.05" {
               description "1579.05 nm/189.856250 THz 3.125/6.25GHz spacing";
             }
             enum "1579.02" {
               description "1579.02 nm/189.859375 THz 3.125GHz spacing";
             }
             enum "1579.00" {
               description "1579.00 nm/189.862500 THz 3.125/6.25/12.5GHz spacing";
             }
             enum "1578.97" {
               description "1578.97 nm/189.865625 THz 3.125GHz spacing";
             }
             enum "1578.95" {
               description "1578.95 nm/189.868750 THz 3.125/6.25GHz spacing";
             }
             enum "1578.92" {
               description "1578.92 nm/189.871875 THz 3.125GHz spacing";
             }
             enum "1578.89" {
               description "1578.89 nm/189.875000 THz 3.125/6.25/12.5/75GHz spacing";
             }
             enum "1578.87" {
               description "1578.87 nm/189.878125 THz 3.125GHz spacing";
             }
             enum "1578.84" {
               description "1578.84 nm/189.881250 THz 3.125/6.25GHz spacing";
             }
             enum "1578.82" {
               description "1578.82 nm/189.884375 THz 3.125GHz spacing";
             }
             enum "1578.79" {
               description "1578.79 nm/189.887500 THz 3.125/6.25/12.5GHz spacing";
             }
             enum "1578.76" {
               description "1578.76 nm/189.890625 THz 3.125GHz spacing";
             }
             enum "1578.74" {
               description "1578.74 nm/189.893750 THz 3.125/6.25GHz spacing";
             }
             enum "1578.71" {
               description "1578.71 nm/189.896875 THz 3.125GHz spacing";
             }
             enum "1578.69" {
               description "1578.69 nm/189.900000 THz 3.125/6.25/12.5/50/75/100GHz spacing";
             }
             enum "1578.66" {
               description "1578.66 nm/189.903125 THz 3.125GHz spacing";
             }
             enum "1578.63" {
               description "1578.63 nm/189.906250 THz 3.125/6.25GHz spacing";
             }
             enum "1578.61" {
               description "1578.61 nm/189.909375 THz 3.125GHz spacing";
             }
             enum "1578.58" {
               description "1578.58 nm/189.912500 THz 3.125/6.25/12.5GHz spacing";
             }
             enum "1578.56" {
               description "1578.56 nm/189.915625 THz 3.125GHz spacing";
             }
             enum "1578.53" {
               description "1578.53 nm/189.918750 THz 3.125/6.25GHz spacing";
             }
             enum "1578.50" {
               description "1578.50 nm/189.921875 THz 3.125GHz spacing";
             }
             enum "1578.48" {
               description "1578.48 nm/189.925000 THz 3.125/6.25/12.5GHz spacing";
             }
             enum "1578.45" {
               description "1578.45 nm/189.928125 THz 3.125GHz spacing";
             }
             enum "1578.43" {
               description "1578.43 nm/189.931250 THz 3.125/6.25GHz spacing";
             }
             enum "1578.40" {
               description "1578.40 nm/189.934375 THz 3.125GHz spacing";
             }
             enum "1578.37" {
               description "1578.37 nm/189.937500 THz 3.125/6.25/12.5GHz spacing";
             }
             enum "1578.35" {
               description "1578.35 nm/189.940625 THz 3.125GHz spacing";
             }
             enum "1578.32" {
               description "1578.32 nm/189.943750 THz 3.125/6.25GHz spacing";
             }
             enum "1578.30" {
               description "1578.30 nm/189.946875 THz 3.125GHz spacing";
             }
             enum "1578.27" {
               description "1578.27 nm/189.950000 THz 3.125/6.25/12.5/50/75GHz spacing";
             }
             enum "1578.24" {
               description "1578.24 nm/189.953125 THz 3.125GHz spacing";
             }
             enum "1578.22" {
               description "1578.22 nm/189.956250 THz 3.125/6.25GHz spacing";
             }
             enum "1578.19" {
               description "1578.19 nm/189.959375 THz 3.125GHz spacing";
             }
             enum "1578.17" {
               description "1578.17 nm/189.962500 THz 3.125/6.25/12.5GHz spacing";
             }
             enum "1578.14" {
               description "1578.14 nm/189.965625 THz 3.125GHz spacing";
             }
             enum "1578.11" {
               description "1578.11 nm/189.968750 THz 3.125/6.25GHz spacing";
             }
             enum "1578.09" {
               description "1578.09 nm/189.971875 THz 3.125GHz spacing";
             }
             enum "1578.06" {
               description "1578.06 nm/189.975000 THz 3.125/6.25/12.5GHz spacing";
             }
             enum "1578.04" {
               description "1578.04 nm/189.978125 THz 3.125GHz spacing";
             }
             enum "1578.01" {
               description "1578.01 nm/189.981250 THz 3.125/6.25GHz spacing";
             }
             enum "1577.98" {
               description "1577.98 nm/189.984375 THz 3.125GHz spacing";
             }
             enum "1577.96" {
               description "1577.96 nm/189.987500 THz 3.125/6.25/12.5GHz spacing";
             }
             enum "1577.93" {
               description "1577.93 nm/189.990625 THz 3.125GHz spacing";
             }
             enum "1577.91" {
               description "1577.91 nm/189.993750 THz 3.125/6.25GHz spacing";
             }
             enum "1577.88" {
               description "1577.88 nm/189.996875 THz 3.125GHz spacing";
             }
             enum "1577.86" {
               description "1577.86 nm/190.000000 THz 3.125/6.25/12.5/100GHz spacing";
             }
             enum "1577.83" {
               description "1577.83 nm/190.003125 THz 3.125GHz spacing";
             }
             enum "1577.80" {
               description "1577.80 nm/190.006250 THz 3.125/6.25GHz spacing";
             }
             enum "1577.78" {
               description "1577.78 nm/190.009375 THz 3.125GHz spacing";
             }
             enum "1577.75" {
               description "1577.75 nm/190.012500 THz 3.125/6.25/12.5GHz spacing";
             }
             enum "1577.73" {
               description "1577.73 nm/190.015625 THz 3.125GHz spacing";
             }
             enum "1577.70" {
               description "1577.70 nm/190.018750 THz 3.125/6.25GHz spacing";
             }
             enum "1577.67" {
               description "1577.67 nm/190.021875 THz 3.125GHz spacing";
             }
             enum "1577.65" {
               description "1577.65 nm/190.025000 THz 3.125/6.25/12.5/75GHz spacing";
             }
             enum "1577.62" {
               description "1577.62 nm/190.028125 THz 3.125GHz spacing";
             }
             enum "1577.60" {
               description "1577.60 nm/190.031250 THz 3.125/6.25GHz spacing";
             }
             enum "1577.57" {
               description "1577.57 nm/190.034375 THz 3.125GHz spacing";
             }
             enum "1577.54" {
               description "1577.54 nm/190.037500 THz 3.125/6.25/12.5GHz spacing";
             }
             enum "1577.52" {
               description "1577.52 nm/190.040625 THz 3.125GHz spacing";
             }
             enum "1577.49" {
               description "1577.49 nm/190.043750 THz 3.125/6.25GHz spacing";
             }
             enum "1577.47" {
               description "1577.47 nm/190.046875 THz 3.125GHz spacing";
             }
             enum "1577.44" {
               description "1577.44 nm/190.050000 THz 3.125/6.25/12.5/50GHz spacing";
             }
             enum "1577.41" {
               description "1577.41 nm/190.053125 THz 3.125GHz spacing";
             }
             enum "1577.39" {
               description "1577.39 nm/190.056250 THz 3.125/6.25GHz spacing";
             }
             enum "1577.36" {
               description "1577.36 nm/190.059375 THz 3.125GHz spacing";
             }
             enum "1577.34" {
               description "1577.34 nm/190.062500 THz 3.125/6.25/12.5GHz spacing";
             }
             enum "1577.31" {
               description "1577.31 nm/190.065625 THz 3.125GHz spacing";
             }
             enum "1577.28" {
               description "1577.28 nm/190.068750 THz 3.125/6.25GHz spacing";
             }
             enum "1577.26" {
               description "1577.26 nm/190.071875 THz 3.125GHz spacing";
             }
             enum "1577.23" {
               description "1577.23 nm/190.075000 THz 3.125/6.25/12.5GHz spacing";
             }
             enum "1577.21" {
               description "1577.21 nm/190.078125 THz 3.125GHz spacing";
             }
             enum "1577.18" {
               description "1577.18 nm/190.081250 THz 3.125/6.25GHz spacing";
             }
             enum "1577.15" {
               description "1577.15 nm/190.084375 THz 3.125GHz spacing";
             }
             enum "1577.13" {
               description "1577.13 nm/190.087500 THz 3.125/6.25/12.5GHz spacing";
             }
             enum "1577.10" {
               description "1577.10 nm/190.090625 THz 3.125GHz spacing";
             }
             enum "1577.08" {
               description "1577.08 nm/190.093750 THz 3.125/6.25GHz spacing";
             }
             enum "1577.05" {
               description "1577.05 nm/190.096875 THz 3.125GHz spacing";
             }
             enum "1577.03" {
               description "1577.03 nm/190.100000 THz 3.125/6.25/12.5/100GHz spacing";
             }
             enum "1577.00" {
               description "1577.00 nm/190.103125 THz 3.125GHz spacing";
             }
             enum "1576.97" {
               description "1576.97 nm/190.106250 THz 3.125/6.25GHz spacing";
             }
             enum "1576.95" {
               description "1576.95 nm/190.109375 THz 3.125GHz spacing";
             }
             enum "1576.92" {
               description "1576.92 nm/190.112500 THz 3.125/6.25/12.5GHz spacing";
             }
             enum "1576.90" {
               description "1576.90 nm/190.115625 THz 3.125GHz spacing";
             }
             enum "1576.87" {
               description "1576.87 nm/190.118750 THz 3.125/6.25GHz spacing";
             }
             enum "1576.84" {
               description "1576.84 nm/190.121875 THz 3.125GHz spacing";
             }
             enum "1576.82" {
               description "1576.82 nm/190.125000 THz 3.125/6.25/12.5GHz spacing";
             }
             enum "1576.79" {
               description "1576.79 nm/190.128125 THz 3.125GHz spacing";
             }
             enum "1576.77" {
               description "1576.77 nm/190.131250 THz 3.125/6.25GHz spacing";
             }
             enum "1576.74" {
               description "1576.74 nm/190.134375 THz 3.125GHz spacing";
             }
             enum "1576.71" {
               description "1576.71 nm/190.137500 THz 3.125/6.25/12.5GHz spacing";
             }
             enum "1576.69" {
               description "1576.69 nm/190.140625 THz 3.125GHz spacing";
             }
             enum "1576.66" {
               description "1576.66 nm/190.143750 THz 3.125/6.25GHz spacing";
             }
             enum "1576.64" {
               description "1576.64 nm/190.146875 THz 3.125GHz spacing";
             }
             enum "1576.61" {
               description "1576.61 nm/190.150000 THz 3.125/6.25/12.5/50GHz spacing";
             }
             enum "1576.58" {
               description "1576.58 nm/190.153125 THz 3.125GHz spacing";
             }
             enum "1576.56" {
               description "1576.56 nm/190.156250 THz 3.125/6.25GHz spacing";
             }
             enum "1576.53" {
               description "1576.53 nm/190.159375 THz 3.125GHz spacing";
             }
             enum "1576.51" {
               description "1576.51 nm/190.162500 THz 3.125/6.25/12.5GHz spacing";
             }
             enum "1576.48" {
               description "1576.48 nm/190.165625 THz 3.125GHz spacing";
             }
             enum "1576.45" {
               description "1576.45 nm/190.168750 THz 3.125/6.25GHz spacing";
             }
             enum "1576.43" {
               description "1576.43 nm/190.171875 THz 3.125GHz spacing";
             }
             enum "1576.40" {
               description "1576.40 nm/190.175000 THz 3.125/6.25/12.5/75GHz spacing";
             }
             enum "1576.38" {
               description "1576.38 nm/190.178125 THz 3.125GHz spacing";
             }
             enum "1576.35" {
               description "1576.35 nm/190.181250 THz 3.125/6.25GHz spacing";
             }
             enum "1576.33" {
               description "1576.33 nm/190.184375 THz 3.125GHz spacing";
             }
             enum "1576.30" {
               description "1576.30 nm/190.187500 THz 3.125/6.25/12.5GHz spacing";
             }
             enum "1576.27" {
               description "1576.27 nm/190.190625 THz 3.125GHz spacing";
             }
             enum "1576.25" {
               description "1576.25 nm/190.193750 THz 3.125/6.25GHz spacing";
             }
             enum "1576.22" {
               description "1576.22 nm/190.196875 THz 3.125GHz spacing";
             }
             enum "1576.20" {
               description "1576.20 nm/190.200000 THz 3.125/6.25/12.5/50/75/100GHz spacing";
             }
             enum "1576.17" {
               description "1576.17 nm/190.203125 THz 3.125GHz spacing";
             }
             enum "1576.14" {
               description "1576.14 nm/190.206250 THz 3.125/6.25GHz spacing";
             }
             enum "1576.12" {
               description "1576.12 nm/190.209375 THz 3.125GHz spacing";
             }
             enum "1576.09" {
               description "1576.09 nm/190.212500 THz 3.125/6.25/12.5GHz spacing";
             }
             enum "1576.07" {
               description "1576.07 nm/190.215625 THz 3.125GHz spacing";
             }
             enum "1576.04" {
               description "1576.04 nm/190.218750 THz 3.125/6.25GHz spacing";
             }
             enum "1576.01" {
               description "1576.01 nm/190.221875 THz 3.125GHz spacing";
             }
             enum "1575.99" {
               description "1575.99 nm/190.225000 THz 3.125/6.25/12.5GHz spacing";
             }
             enum "1575.96" {
               description "1575.96 nm/190.228125 THz 3.125GHz spacing";
             }
             enum "1575.94" {
               description "1575.94 nm/190.231250 THz 3.125/6.25GHz spacing";
             }
             enum "1575.91" {
               description "1575.91 nm/190.234375 THz 3.125GHz spacing";
             }
             enum "1575.89" {
               description "1575.89 nm/190.237500 THz 3.125/6.25/12.5GHz spacing";
             }
             enum "1575.86" {
               description "1575.86 nm/190.240625 THz 3.125GHz spacing";
             }
             enum "1575.83" {
               description "1575.83 nm/190.243750 THz 3.125/6.25GHz spacing";
             }
             enum "1575.81" {
               description "1575.81 nm/190.246875 THz 3.125GHz spacing";
             }
             enum "1575.78" {
               description "1575.78 nm/190.250000 THz 3.125/6.25/12.5/50/75GHz spacing";
             }
             enum "1575.76" {
               description "1575.76 nm/190.253125 THz 3.125GHz spacing";
             }
             enum "1575.73" {
               description "1575.73 nm/190.256250 THz 3.125/6.25GHz spacing";
             }
             enum "1575.70" {
               description "1575.70 nm/190.259375 THz 3.125GHz spacing";
             }
             enum "1575.68" {
               description "1575.68 nm/190.262500 THz 3.125/6.25/12.5GHz spacing";
             }
             enum "1575.65" {
               description "1575.65 nm/190.265625 THz 3.125GHz spacing";
             }
             enum "1575.63" {
               description "1575.63 nm/190.268750 THz 3.125/6.25GHz spacing";
             }
             enum "1575.60" {
               description "1575.60 nm/190.271875 THz 3.125GHz spacing";
             }
             enum "1575.57" {
               description "1575.57 nm/190.275000 THz 3.125/6.25/12.5GHz spacing";
             }
             enum "1575.55" {
               description "1575.55 nm/190.278125 THz 3.125GHz spacing";
             }
             enum "1575.52" {
               description "1575.52 nm/190.281250 THz 3.125/6.25GHz spacing";
             }
             enum "1575.50" {
               description "1575.50 nm/190.284375 THz 3.125GHz spacing";
             }
             enum "1575.47" {
               description "1575.47 nm/190.287500 THz 3.125/6.25/12.5GHz spacing";
             }
             enum "1575.45" {
               description "1575.45 nm/190.290625 THz 3.125GHz spacing";
             }
             enum "1575.42" {
               description "1575.42 nm/190.293750 THz 3.125/6.25GHz spacing";
             }
             enum "1575.39" {
               description "1575.39 nm/190.296875 THz 3.125GHz spacing";
             }
             enum "1575.37" {
               description "1575.37 nm/190.300000 THz 3.125/6.25/12.5/100GHz spacing";
             }
             enum "1575.34" {
               description "1575.34 nm/190.303125 THz 3.125GHz spacing";
             }
             enum "1575.32" {
               description "1575.32 nm/190.306250 THz 3.125/6.25GHz spacing";
             }
             enum "1575.29" {
               description "1575.29 nm/190.309375 THz 3.125GHz spacing";
             }
             enum "1575.26" {
               description "1575.26 nm/190.312500 THz 3.125/6.25/12.5GHz spacing";
             }
             enum "1575.24" {
               description "1575.24 nm/190.315625 THz 3.125GHz spacing";
             }
             enum "1575.21" {
               description "1575.21 nm/190.318750 THz 3.125/6.25GHz spacing";
             }
             enum "1575.19" {
               description "1575.19 nm/190.321875 THz 3.125GHz spacing";
             }
             enum "1575.16" {
               description "1575.16 nm/190.325000 THz 3.125/6.25/12.5/75GHz spacing";
             }
             enum "1575.13" {
               description "1575.13 nm/190.328125 THz 3.125GHz spacing";
             }
             enum "1575.11" {
               description "1575.11 nm/190.331250 THz 3.125/6.25GHz spacing";
             }
             enum "1575.08" {
               description "1575.08 nm/190.334375 THz 3.125GHz spacing";
             }
             enum "1575.06" {
               description "1575.06 nm/190.337500 THz 3.125/6.25/12.5GHz spacing";
             }
             enum "1575.03" {
               description "1575.03 nm/190.340625 THz 3.125GHz spacing";
             }
             enum "1575.01" {
               description "1575.01 nm/190.343750 THz 3.125/6.25GHz spacing";
             }
             enum "1574.98" {
               description "1574.98 nm/190.346875 THz 3.125GHz spacing";
             }
             enum "1574.95" {
               description "1574.95 nm/190.350000 THz 3.125/6.25/12.5/50GHz spacing";
             }
             enum "1574.93" {
               description "1574.93 nm/190.353125 THz 3.125GHz spacing";
             }
             enum "1574.90" {
               description "1574.90 nm/190.356250 THz 3.125/6.25GHz spacing";
             }
             enum "1574.88" {
               description "1574.88 nm/190.359375 THz 3.125GHz spacing";
             }
             enum "1574.85" {
               description "1574.85 nm/190.362500 THz 3.125/6.25/12.5GHz spacing";
             }
             enum "1574.82" {
               description "1574.82 nm/190.365625 THz 3.125GHz spacing";
             }
             enum "1574.80" {
               description "1574.80 nm/190.368750 THz 3.125/6.25GHz spacing";
             }
             enum "1574.77" {
               description "1574.77 nm/190.371875 THz 3.125GHz spacing";
             }
             enum "1574.75" {
               description "1574.75 nm/190.375000 THz 3.125/6.25/12.5GHz spacing";
             }
             enum "1574.72" {
               description "1574.72 nm/190.378125 THz 3.125GHz spacing";
             }
             enum "1574.70" {
               description "1574.70 nm/190.381250 THz 3.125/6.25GHz spacing";
             }
             enum "1574.67" {
               description "1574.67 nm/190.384375 THz 3.125GHz spacing";
             }
             enum "1574.64" {
               description "1574.64 nm/190.387500 THz 3.125/6.25/12.5GHz spacing";
             }
             enum "1574.62" {
               description "1574.62 nm/190.390625 THz 3.125GHz spacing";
             }
             enum "1574.59" {
               description "1574.59 nm/190.393750 THz 3.125/6.25GHz spacing";
             }
             enum "1574.57" {
               description "1574.57 nm/190.396875 THz 3.125GHz spacing";
             }
             enum "1574.54" {
               description "1574.54 nm/190.400000 THz 3.125/6.25/12.5/100GHz spacing";
             }
             enum "1574.51" {
               description "1574.51 nm/190.403125 THz 3.125GHz spacing";
             }
             enum "1574.49" {
               description "1574.49 nm/190.406250 THz 3.125/6.25GHz spacing";
             }
             enum "1574.46" {
               description "1574.46 nm/190.409375 THz 3.125GHz spacing";
             }
             enum "1574.44" {
               description "1574.44 nm/190.412500 THz 3.125/6.25/12.5GHz spacing";
             }
             enum "1574.41" {
               description "1574.41 nm/190.415625 THz 3.125GHz spacing";
             }
             enum "1574.39" {
               description "1574.39 nm/190.418750 THz 3.125/6.25GHz spacing";
             }
             enum "1574.36" {
               description "1574.36 nm/190.421875 THz 3.125GHz spacing";
             }
             enum "1574.33" {
               description "1574.33 nm/190.425000 THz 3.125/6.25/12.5GHz spacing";
             }
             enum "1574.31" {
               description "1574.31 nm/190.428125 THz 3.125GHz spacing";
             }
             enum "1574.28" {
               description "1574.28 nm/190.431250 THz 3.125/6.25GHz spacing";
             }
             enum "1574.26" {
               description "1574.26 nm/190.434375 THz 3.125GHz spacing";
             }
             enum "1574.23" {
               description "1574.23 nm/190.437500 THz 3.125/6.25/12.5GHz spacing";
             }
             enum "1574.20" {
               description "1574.20 nm/190.440625 THz 3.125GHz spacing";
             }
             enum "1574.18" {
               description "1574.18 nm/190.443750 THz 3.125/6.25GHz spacing";
             }
             enum "1574.15" {
               description "1574.15 nm/190.446875 THz 3.125GHz spacing";
             }
             enum "1574.13" {
               description "1574.13 nm/190.450000 THz 3.125/6.25/12.5/50GHz spacing";
             }
             enum "1574.10" {
               description "1574.10 nm/190.453125 THz 3.125GHz spacing";
             }
             enum "1574.08" {
               description "1574.08 nm/190.456250 THz 3.125/6.25GHz spacing";
             }
             enum "1574.05" {
               description "1574.05 nm/190.459375 THz 3.125GHz spacing";
             }
             enum "1574.02" {
               description "1574.02 nm/190.462500 THz 3.125/6.25/12.5GHz spacing";
             }
             enum "1574.00" {
               description "1574.00 nm/190.465625 THz 3.125GHz spacing";
             }
             enum "1573.97" {
               description "1573.97 nm/190.468750 THz 3.125/6.25GHz spacing";
             }
             enum "1573.95" {
               description "1573.95 nm/190.471875 THz 3.125GHz spacing";
             }
             enum "1573.92" {
               description "1573.92 nm/190.475000 THz 3.125/6.25/12.5/75GHz spacing";
             }
             enum "1573.89" {
               description "1573.89 nm/190.478125 THz 3.125GHz spacing";
             }
             enum "1573.87" {
               description "1573.87 nm/190.481250 THz 3.125/6.25GHz spacing";
             }
             enum "1573.84" {
               description "1573.84 nm/190.484375 THz 3.125GHz spacing";
             }
             enum "1573.82" {
               description "1573.82 nm/190.487500 THz 3.125/6.25/12.5GHz spacing";
             }
             enum "1573.79" {
               description "1573.79 nm/190.490625 THz 3.125GHz spacing";
             }
             enum "1573.77" {
               description "1573.77 nm/190.493750 THz 3.125/6.25GHz spacing";
             }
             enum "1573.74" {
               description "1573.74 nm/190.496875 THz 3.125GHz spacing";
             }
             enum "1573.71" {
               description "1573.71 nm/190.500000 THz 3.125/6.25/12.5/50/75/100GHz spacing";
             }
             enum "1573.69" {
               description "1573.69 nm/190.503125 THz 3.125GHz spacing";
             }
             enum "1573.66" {
               description "1573.66 nm/190.506250 THz 3.125/6.25GHz spacing";
             }
             enum "1573.64" {
               description "1573.64 nm/190.509375 THz 3.125GHz spacing";
             }
             enum "1573.61" {
               description "1573.61 nm/190.512500 THz 3.125/6.25/12.5GHz spacing";
             }
             enum "1573.58" {
               description "1573.58 nm/190.515625 THz 3.125GHz spacing";
             }
             enum "1573.56" {
               description "1573.56 nm/190.518750 THz 3.125/6.25GHz spacing";
             }
             enum "1573.53" {
               description "1573.53 nm/190.521875 THz 3.125GHz spacing";
             }
             enum "1573.51" {
               description "1573.51 nm/190.525000 THz 3.125/6.25/12.5GHz spacing";
             }
             enum "1573.48" {
               description "1573.48 nm/190.528125 THz 3.125GHz spacing";
             }
             enum "1573.46" {
               description "1573.46 nm/190.531250 THz 3.125/6.25GHz spacing";
             }
             enum "1573.43" {
               description "1573.43 nm/190.534375 THz 3.125GHz spacing";
             }
             enum "1573.40" {
               description "1573.40 nm/190.537500 THz 3.125/6.25/12.5GHz spacing";
             }
             enum "1573.38" {
               description "1573.38 nm/190.540625 THz 3.125GHz spacing";
             }
             enum "1573.35" {
               description "1573.35 nm/190.543750 THz 3.125/6.25GHz spacing";
             }
             enum "1573.33" {
               description "1573.33 nm/190.546875 THz 3.125GHz spacing";
             }
             enum "1573.30" {
               description "1573.30 nm/190.550000 THz 3.125/6.25/12.5/50/75GHz spacing";
             }
             enum "1573.27" {
               description "1573.27 nm/190.553125 THz 3.125GHz spacing";
             }
             enum "1573.25" {
               description "1573.25 nm/190.556250 THz 3.125/6.25GHz spacing";
             }
             enum "1573.22" {
               description "1573.22 nm/190.559375 THz 3.125GHz spacing";
             }
             enum "1573.20" {
               description "1573.20 nm/190.562500 THz 3.125/6.25/12.5GHz spacing";
             }
             enum "1573.17" {
               description "1573.17 nm/190.565625 THz 3.125GHz spacing";
             }
             enum "1573.15" {
               description "1573.15 nm/190.568750 THz 3.125/6.25GHz spacing";
             }
             enum "1573.12" {
               description "1573.12 nm/190.571875 THz 3.125GHz spacing";
             }
             enum "1573.09" {
               description "1573.09 nm/190.575000 THz 3.125/6.25/12.5GHz spacing";
             }
             enum "1573.07" {
               description "1573.07 nm/190.578125 THz 3.125GHz spacing";
             }
             enum "1573.04" {
               description "1573.04 nm/190.581250 THz 3.125/6.25GHz spacing";
             }
             enum "1573.02" {
               description "1573.02 nm/190.584375 THz 3.125GHz spacing";
             }
             enum "1572.99" {
               description "1572.99 nm/190.587500 THz 3.125/6.25/12.5GHz spacing";
             }
             enum "1572.97" {
               description "1572.97 nm/190.590625 THz 3.125GHz spacing";
             }
             enum "1572.94" {
               description "1572.94 nm/190.593750 THz 3.125/6.25GHz spacing";
             }
             enum "1572.91" {
               description "1572.91 nm/190.596875 THz 3.125GHz spacing";
             }
             enum "1572.89" {
               description "1572.89 nm/190.600000 THz 3.125/6.25/12.5/100GHz spacing";
             }
             enum "1572.86" {
               description "1572.86 nm/190.603125 THz 3.125GHz spacing";
             }
             enum "1572.84" {
               description "1572.84 nm/190.606250 THz 3.125/6.25GHz spacing";
             }
             enum "1572.81" {
               description "1572.81 nm/190.609375 THz 3.125GHz spacing";
             }
             enum "1572.78" {
               description "1572.78 nm/190.612500 THz 3.125/6.25/12.5GHz spacing";
             }
             enum "1572.76" {
               description "1572.76 nm/190.615625 THz 3.125GHz spacing";
             }
             enum "1572.73" {
               description "1572.73 nm/190.618750 THz 3.125/6.25GHz spacing";
             }
             enum "1572.71" {
               description "1572.71 nm/190.621875 THz 3.125GHz spacing";
             }
             enum "1572.68" {
               description "1572.68 nm/190.625000 THz 3.125/6.25/12.5/75GHz spacing";
             }
             enum "1572.66" {
               description "1572.66 nm/190.628125 THz 3.125GHz spacing";
             }
             enum "1572.63" {
               description "1572.63 nm/190.631250 THz 3.125/6.25GHz spacing";
             }
             enum "1572.60" {
               description "1572.60 nm/190.634375 THz 3.125GHz spacing";
             }
             enum "1572.58" {
               description "1572.58 nm/190.637500 THz 3.125/6.25/12.5GHz spacing";
             }
             enum "1572.55" {
               description "1572.55 nm/190.640625 THz 3.125GHz spacing";
             }
             enum "1572.53" {
               description "1572.53 nm/190.643750 THz 3.125/6.25GHz spacing";
             }
             enum "1572.50" {
               description "1572.50 nm/190.646875 THz 3.125GHz spacing";
             }
             enum "1572.48" {
               description "1572.48 nm/190.650000 THz 3.125/6.25/12.5/50GHz spacing";
             }
             enum "1572.45" {
               description "1572.45 nm/190.653125 THz 3.125GHz spacing";
             }
             enum "1572.42" {
               description "1572.42 nm/190.656250 THz 3.125/6.25GHz spacing";
             }
             enum "1572.40" {
               description "1572.40 nm/190.659375 THz 3.125GHz spacing";
             }
             enum "1572.37" {
               description "1572.37 nm/190.662500 THz 3.125/6.25/12.5GHz spacing";
             }
             enum "1572.35" {
               description "1572.35 nm/190.665625 THz 3.125GHz spacing";
             }
             enum "1572.32" {
               description "1572.32 nm/190.668750 THz 3.125/6.25GHz spacing";
             }
             enum "1572.30" {
               description "1572.30 nm/190.671875 THz 3.125GHz spacing";
             }
             enum "1572.27" {
               description "1572.27 nm/190.675000 THz 3.125/6.25/12.5GHz spacing";
             }
             enum "1572.24" {
               description "1572.24 nm/190.678125 THz 3.125GHz spacing";
             }
             enum "1572.22" {
               description "1572.22 nm/190.681250 THz 3.125/6.25GHz spacing";
             }
             enum "1572.19" {
               description "1572.19 nm/190.684375 THz 3.125GHz spacing";
             }
             enum "1572.17" {
               description "1572.17 nm/190.687500 THz 3.125/6.25/12.5GHz spacing";
             }
             enum "1572.14" {
               description "1572.14 nm/190.690625 THz 3.125GHz spacing";
             }
             enum "1572.11" {
               description "1572.11 nm/190.693750 THz 3.125/6.25GHz spacing";
             }
             enum "1572.09" {
               description "1572.09 nm/190.696875 THz 3.125GHz spacing";
             }
             enum "1572.06" {
               description "1572.06 nm/190.700000 THz 3.125/6.25/12.5/100GHz spacing";
             }
             enum "1572.04" {
               description "1572.04 nm/190.703125 THz 3.125GHz spacing";
             }
             enum "1572.01" {
               description "1572.01 nm/190.706250 THz 3.125/6.25GHz spacing";
             }
             enum "1571.99" {
               description "1571.99 nm/190.709375 THz 3.125GHz spacing";
             }
             enum "1571.96" {
               description "1571.96 nm/190.712500 THz 3.125/6.25/12.5GHz spacing";
             }
             enum "1571.93" {
               description "1571.93 nm/190.715625 THz 3.125GHz spacing";
             }
             enum "1571.91" {
               description "1571.91 nm/190.718750 THz 3.125/6.25GHz spacing";
             }
             enum "1571.88" {
               description "1571.88 nm/190.721875 THz 3.125GHz spacing";
             }
             enum "1571.86" {
               description "1571.86 nm/190.725000 THz 3.125/6.25/12.5GHz spacing";
             }
             enum "1571.83" {
               description "1571.83 nm/190.728125 THz 3.125GHz spacing";
             }
             enum "1571.81" {
               description "1571.81 nm/190.731250 THz 3.125/6.25GHz spacing";
             }
             enum "1571.78" {
               description "1571.78 nm/190.734375 THz 3.125GHz spacing";
             }
             enum "1571.75" {
               description "1571.75 nm/190.737500 THz 3.125/6.25/12.5GHz spacing";
             }
             enum "1571.73" {
               description "1571.73 nm/190.740625 THz 3.125GHz spacing";
             }
             enum "1571.70" {
               description "1571.70 nm/190.743750 THz 3.125/6.25GHz spacing";
             }
             enum "1571.68" {
               description "1571.68 nm/190.746875 THz 3.125GHz spacing";
             }
             enum "1571.65" {
               description "1571.65 nm/190.750000 THz 3.125/6.25/12.5/50GHz spacing";
             }
             enum "1571.63" {
               description "1571.63 nm/190.753125 THz 3.125GHz spacing";
             }
             enum "1571.60" {
               description "1571.60 nm/190.756250 THz 3.125/6.25GHz spacing";
             }
             enum "1571.57" {
               description "1571.57 nm/190.759375 THz 3.125GHz spacing";
             }
             enum "1571.55" {
               description "1571.55 nm/190.762500 THz 3.125/6.25/12.5GHz spacing";
             }
             enum "1571.52" {
               description "1571.52 nm/190.765625 THz 3.125GHz spacing";
             }
             enum "1571.50" {
               description "1571.50 nm/190.768750 THz 3.125/6.25GHz spacing";
             }
             enum "1571.47" {
               description "1571.47 nm/190.771875 THz 3.125GHz spacing";
             }
             enum "1571.45" {
               description "1571.45 nm/190.775000 THz 3.125/6.25/12.5/75GHz spacing";
             }
             enum "1571.42" {
               description "1571.42 nm/190.778125 THz 3.125GHz spacing";
             }
             enum "1571.39" {
               description "1571.39 nm/190.781250 THz 3.125/6.25GHz spacing";
             }
             enum "1571.37" {
               description "1571.37 nm/190.784375 THz 3.125GHz spacing";
             }
             enum "1571.34" {
               description "1571.34 nm/190.787500 THz 3.125/6.25/12.5GHz spacing";
             }
             enum "1571.32" {
               description "1571.32 nm/190.790625 THz 3.125GHz spacing";
             }
             enum "1571.29" {
               description "1571.29 nm/190.793750 THz 3.125/6.25GHz spacing";
             }
             enum "1571.27" {
               description "1571.27 nm/190.796875 THz 3.125GHz spacing";
             }
             enum "1571.24" {
               description "1571.24 nm/190.800000 THz 3.125/6.25/12.5/50/75/100GHz spacing";
             }
             enum "1571.21" {
               description "1571.21 nm/190.803125 THz 3.125GHz spacing";
             }
             enum "1571.19" {
               description "1571.19 nm/190.806250 THz 3.125/6.25GHz spacing";
             }
             enum "1571.16" {
               description "1571.16 nm/190.809375 THz 3.125GHz spacing";
             }
             enum "1571.14" {
               description "1571.14 nm/190.812500 THz 3.125/6.25/12.5GHz spacing";
             }
             enum "1571.11" {
               description "1571.11 nm/190.815625 THz 3.125GHz spacing";
             }
             enum "1571.08" {
               description "1571.08 nm/190.818750 THz 3.125/6.25GHz spacing";
             }
             enum "1571.06" {
               description "1571.06 nm/190.821875 THz 3.125GHz spacing";
             }
             enum "1571.03" {
               description "1571.03 nm/190.825000 THz 3.125/6.25/12.5GHz spacing";
             }
             enum "1571.01" {
               description "1571.01 nm/190.828125 THz 3.125GHz spacing";
             }
             enum "1570.98" {
               description "1570.98 nm/190.831250 THz 3.125/6.25GHz spacing";
             }
             enum "1570.96" {
               description "1570.96 nm/190.834375 THz 3.125GHz spacing";
             }
             enum "1570.93" {
               description "1570.93 nm/190.837500 THz 3.125/6.25/12.5GHz spacing";
             }
             enum "1570.90" {
               description "1570.90 nm/190.840625 THz 3.125GHz spacing";
             }
             enum "1570.88" {
               description "1570.88 nm/190.843750 THz 3.125/6.25GHz spacing";
             }
             enum "1570.85" {
               description "1570.85 nm/190.846875 THz 3.125GHz spacing";
             }
             enum "1570.83" {
               description "1570.83 nm/190.850000 THz 3.125/6.25/12.5/50/75GHz spacing";
             }
             enum "1570.80" {
               description "1570.80 nm/190.853125 THz 3.125GHz spacing";
             }
             enum "1570.78" {
               description "1570.78 nm/190.856250 THz 3.125/6.25GHz spacing";
             }
             enum "1570.75" {
               description "1570.75 nm/190.859375 THz 3.125GHz spacing";
             }
             enum "1570.72" {
               description "1570.72 nm/190.862500 THz 3.125/6.25/12.5GHz spacing";
             }
             enum "1570.70" {
               description "1570.70 nm/190.865625 THz 3.125GHz spacing";
             }
             enum "1570.67" {
               description "1570.67 nm/190.868750 THz 3.125/6.25GHz spacing";
             }
             enum "1570.65" {
               description "1570.65 nm/190.871875 THz 3.125GHz spacing";
             }
             enum "1570.62" {
               description "1570.62 nm/190.875000 THz 3.125/6.25/12.5GHz spacing";
             }
             enum "1570.60" {
               description "1570.60 nm/190.878125 THz 3.125GHz spacing";
             }
             enum "1570.57" {
               description "1570.57 nm/190.881250 THz 3.125/6.25GHz spacing";
             }
             enum "1570.54" {
               description "1570.54 nm/190.884375 THz 3.125GHz spacing";
             }
             enum "1570.52" {
               description "1570.52 nm/190.887500 THz 3.125/6.25/12.5GHz spacing";
             }
             enum "1570.49" {
               description "1570.49 nm/190.890625 THz 3.125GHz spacing";
             }
             enum "1570.47" {
               description "1570.47 nm/190.893750 THz 3.125/6.25GHz spacing";
             }
             enum "1570.44" {
               description "1570.44 nm/190.896875 THz 3.125GHz spacing";
             }
             enum "1570.42" {
               description "1570.42 nm/190.900000 THz 3.125/6.25/12.5/100GHz spacing";
             }
             enum "1570.39" {
               description "1570.39 nm/190.903125 THz 3.125GHz spacing";
             }
             enum "1570.36" {
               description "1570.36 nm/190.906250 THz 3.125/6.25GHz spacing";
             }
             enum "1570.34" {
               description "1570.34 nm/190.909375 THz 3.125GHz spacing";
             }
             enum "1570.31" {
               description "1570.31 nm/190.912500 THz 3.125/6.25/12.5GHz spacing";
             }
             enum "1570.29" {
               description "1570.29 nm/190.915625 THz 3.125GHz spacing";
             }
             enum "1570.26" {
               description "1570.26 nm/190.918750 THz 3.125/6.25GHz spacing";
             }
             enum "1570.24" {
               description "1570.24 nm/190.921875 THz 3.125GHz spacing";
             }
             enum "1570.21" {
               description "1570.21 nm/190.925000 THz 3.125/6.25/12.5/75GHz spacing";
             }
             enum "1570.18" {
               description "1570.18 nm/190.928125 THz 3.125GHz spacing";
             }
             enum "1570.16" {
               description "1570.16 nm/190.931250 THz 3.125/6.25GHz spacing";
             }
             enum "1570.13" {
               description "1570.13 nm/190.934375 THz 3.125GHz spacing";
             }
             enum "1570.11" {
               description "1570.11 nm/190.937500 THz 3.125/6.25/12.5GHz spacing";
             }
             enum "1570.08" {
               description "1570.08 nm/190.940625 THz 3.125GHz spacing";
             }
             enum "1570.06" {
               description "1570.06 nm/190.943750 THz 3.125/6.25GHz spacing";
             }
             enum "1570.03" {
               description "1570.03 nm/190.946875 THz 3.125GHz spacing";
             }
             enum "1570.01" {
               description "1570.01 nm/190.950000 THz 3.125/6.25/12.5/50GHz spacing";
             }
             enum "1569.98" {
               description "1569.98 nm/190.953125 THz 3.125GHz spacing";
             }
             enum "1569.95" {
               description "1569.95 nm/190.956250 THz 3.125/6.25GHz spacing";
             }
             enum "1569.93" {
               description "1569.93 nm/190.959375 THz 3.125GHz spacing";
             }
             enum "1569.90" {
               description "1569.90 nm/190.962500 THz 3.125/6.25/12.5GHz spacing";
             }
             enum "1569.88" {
               description "1569.88 nm/190.965625 THz 3.125GHz spacing";
             }
             enum "1569.85" {
               description "1569.85 nm/190.968750 THz 3.125/6.25GHz spacing";
             }
             enum "1569.83" {
               description "1569.83 nm/190.971875 THz 3.125GHz spacing";
             }
             enum "1569.80" {
               description "1569.80 nm/190.975000 THz 3.125/6.25/12.5GHz spacing";
             }
             enum "1569.77" {
               description "1569.77 nm/190.978125 THz 3.125GHz spacing";
             }
             enum "1569.75" {
               description "1569.75 nm/190.981250 THz 3.125/6.25GHz spacing";
             }
             enum "1569.72" {
               description "1569.72 nm/190.984375 THz 3.125GHz spacing";
             }
             enum "1569.70" {
               description "1569.70 nm/190.987500 THz 3.125/6.25/12.5GHz spacing";
             }
             enum "1569.67" {
               description "1569.67 nm/190.990625 THz 3.125GHz spacing";
             }
             enum "1569.65" {
               description "1569.65 nm/190.993750 THz 3.125/6.25GHz spacing";
             }
             enum "1569.62" {
               description "1569.62 nm/190.996875 THz 3.125GHz spacing";
             }
             enum "1569.59" {
               description "1569.59 nm/191.000000 THz 3.125/6.25/12.5/100GHz spacing";
             }
             enum "1568.77" {
               description "1568.77 nm/191.1003 THz 50/100Ghz spacing";
             }
             enum "1568.36" {
               description "1568.36 nm/191.150000 THz 3.125/6.25/12.5/50/75GHz spacing";
             }
             enum "1568.34" {
               description "1568.34 nm/191.153125 THz 3.125GHz spacing";
             }
             enum "1568.31" {
               description "1568.31 nm/191.156250 THz 3.125/6.25GHz spacing";
             }
             enum "1568.29" {
               description "1568.29 nm/191.159375 THz 3.125GHz spacing";
             }
             enum "1568.26" {
               description "1568.26 nm/191.162500 THz 3.125/6.25/12.5GHz spacing";
             }
             enum "1568.23" {
               description "1568.23 nm/191.165625 THz 3.125GHz spacing";
             }
             enum "1568.21" {
               description "1568.21 nm/191.168750 THz 3.125/6.25GHz spacing";
             }
             enum "1568.18" {
               description "1568.18 nm/191.171875 THz 3.125GHz spacing";
             }
             enum "1568.16" {
               description "1568.16 nm/191.175000 THz 3.125/6.25/12.5/75GHz spacing";
             }
             enum "1568.13" {
               description "1568.13 nm/191.178125 THz 3.125GHz spacing";
             }
             enum "1568.11" {
               description "1568.11 nm/191.181250 THz 3.125/6.25GHz spacing";
             }
             enum "1568.08" {
               description "1568.08 nm/191.184375 THz 3.125GHz spacing";
             }
             enum "1568.05" {
               description "1568.05 nm/191.187500 THz 3.125/6.25/12.5GHz spacing";
             }
             enum "1568.03" {
               description "1568.03 nm/191.190625 THz 3.125GHz spacing";
             }
             enum "1568.00" {
               description "1568.00 nm/191.193750 THz 3.125/6.25GHz spacing";
             }
             enum "1567.98" {
               description "1567.98 nm/191.196875 THz 3.125GHz spacing";
             }
             enum "1567.95" {
               description "1567.95 nm/191.200000 THz 3.125/6.25/12.5/100GHz spacing";
             }
             enum "1567.93" {
               description "1567.93 nm/191.203125 THz 3.125GHz spacing";
             }
             enum "1567.90" {
               description "1567.90 nm/191.206250 THz 3.125/6.25GHz spacing";
             }
             enum "1567.88" {
               description "1567.88 nm/191.209375 THz 3.125GHz spacing";
             }
             enum "1567.85" {
               description "1567.85 nm/191.212500 THz 3.125/6.25/12.5GHz spacing";
             }
             enum "1567.82" {
               description "1567.82 nm/191.215625 THz 3.125GHz spacing";
             }
             enum "1567.80" {
               description "1567.80 nm/191.218750 THz 3.125/6.25GHz spacing";
             }
             enum "1567.77" {
               description "1567.77 nm/191.221875 THz 3.125GHz spacing";
             }
             enum "1567.75" {
               description "1567.75 nm/191.225000 THz 3.125/6.25/12.5/75GHz spacing";
             }
             enum "1567.72" {
               description "1567.72 nm/191.228125 THz 3.125GHz spacing";
             }
             enum "1567.70" {
               description "1567.70 nm/191.231250 THz 3.125/6.25GHz spacing";
             }
             enum "1567.67" {
               description "1567.67 nm/191.234375 THz 3.125GHz spacing";
             }
             enum "1567.64" {
               description "1567.64 nm/191.237500 THz 3.125/6.25/12.5GHz spacing";
             }
             enum "1567.62" {
               description "1567.62 nm/191.240625 THz 3.125GHz spacing";
             }
             enum "1567.59" {
               description "1567.59 nm/191.243750 THz 3.125/6.25GHz spacing";
             }
             enum "1567.57" {
               description "1567.57 nm/191.246875 THz 3.125GHz spacing";
             }
             enum "1567.54" {
               description "1567.54 nm/191.250000 THz 3.125/6.25/12.5/50/75GHz spacing";
             }
             enum "1567.52" {
               description "1567.52 nm/191.253125 THz 3.125GHz spacing";
             }
             enum "1567.49" {
               description "1567.49 nm/191.256250 THz 3.125/6.25GHz spacing";
             }
             enum "1567.47" {
               description "1567.47 nm/191.259375 THz 3.125GHz spacing";
             }
             enum "1567.44" {
               description "1567.44 nm/191.262500 THz 3.125/6.25/12.5GHz spacing";
             }
             enum "1567.41" {
               description "1567.41 nm/191.265625 THz 3.125GHz spacing";
             }
             enum "1567.39" {
               description "1567.39 nm/191.268750 THz 3.125/6.25GHz spacing";
             }
             enum "1567.36" {
               description "1567.36 nm/191.271875 THz 3.125GHz spacing";
             }
             enum "1567.34" {
               description "1567.34 nm/191.275000 THz 3.125/6.25/12.5GHz spacing";
             }
             enum "1567.31" {
               description "1567.31 nm/191.278125 THz 3.125GHz spacing";
             }
             enum "1567.29" {
               description "1567.29 nm/191.281250 THz 3.125/6.25GHz spacing";
             }
             enum "1567.26" {
               description "1567.26 nm/191.284375 THz 3.125GHz spacing";
             }
             enum "1567.23" {
               description "1567.23 nm/191.287500 THz 3.125/6.25/12.5GHz spacing";
             }
             enum "1567.21" {
               description "1567.21 nm/191.290625 THz 3.125GHz spacing";
             }
             enum "1567.18" {
               description "1567.18 nm/191.293750 THz 3.125/6.25GHz spacing";
             }
             enum "1567.16" {
               description "1567.16 nm/191.296875 THz 3.125GHz spacing";
             }
             enum "1567.13" {
               description "1567.13 nm/191.300000 THz 3.125/6.25/12.5/100GHz spacing";
             }
             enum "1567.11" {
               description "1567.11 nm/191.303125 THz 3.125GHz spacing";
             }
             enum "1567.08" {
               description "1567.08 nm/191.306250 THz 3.125/6.25GHz spacing";
             }
             enum "1567.06" {
               description "1567.06 nm/191.309375 THz 3.125GHz spacing";
             }
             enum "1567.03" {
               description "1567.03 nm/191.312500 THz 3.125/6.25/12.5GHz spacing";
             }
             enum "1567.00" {
               description "1567.00 nm/191.315625 THz 3.125GHz spacing";
             }
             enum "1566.98" {
               description "1566.98 nm/191.318750 THz 3.125/6.25GHz spacing";
             }
             enum "1566.95" {
               description "1566.95 nm/191.321875 THz 3.125GHz spacing";
             }
             enum "1566.93" {
               description "1566.93 nm/191.325000 THz 3.125/6.25/12.5/75GHz spacing";
             }
             enum "1566.90" {
               description "1566.90 nm/191.328125 THz 3.125GHz spacing";
             }
             enum "1566.88" {
               description "1566.88 nm/191.331250 THz 3.125/6.25GHz spacing";
             }
             enum "1566.85" {
               description "1566.85 nm/191.334375 THz 3.125GHz spacing";
             }
             enum "1566.83" {
               description "1566.83 nm/191.337500 THz 3.125/6.25/12.5GHz spacing";
             }
             enum "1566.80" {
               description "1566.80 nm/191.340625 THz 3.125GHz spacing";
             }
             enum "1566.77" {
               description "1566.77 nm/191.343750 THz 3.125/6.25GHz spacing";
             }
             enum "1566.75" {
               description "1566.75 nm/191.346875 THz 3.125GHz spacing";
             }
             enum "1566.72" {
               description "1566.72 nm/191.350000 THz 3.125/6.25/12.5/50GHz spacing";
             }
             enum "1566.70" {
               description "1566.70 nm/191.353125 THz 3.125GHz spacing";
             }
             enum "1566.67" {
               description "1566.67 nm/191.356250 THz 3.125/6.25GHz spacing";
             }
             enum "1566.65" {
               description "1566.65 nm/191.359375 THz 3.125GHz spacing";
             }
             enum "1566.62" {
               description "1566.62 nm/191.362500 THz 3.125/6.25/12.5GHz spacing";
             }
             enum "1566.60" {
               description "1566.60 nm/191.365625 THz 3.125GHz spacing";
             }
             enum "1566.57" {
               description "1566.57 nm/191.368750 THz 3.125/6.25GHz spacing";
             }
             enum "1566.54" {
               description "1566.54 nm/191.371875 THz 3.125GHz spacing";
             }
             enum "1566.52" {
               description "1566.52 nm/191.375000 THz 3.125/6.25/12.5GHz spacing";
             }
             enum "1566.49" {
               description "1566.49 nm/191.378125 THz 3.125GHz spacing";
             }
             enum "1566.47" {
               description "1566.47 nm/191.381250 THz 3.125/6.25GHz spacing";
             }
             enum "1566.44" {
               description "1566.44 nm/191.384375 THz 3.125GHz spacing";
             }
             enum "1566.42" {
               description "1566.42 nm/191.387500 THz 3.125/6.25/12.5GHz spacing";
             }
             enum "1566.39" {
               description "1566.39 nm/191.390625 THz 3.125GHz spacing";
             }
             enum "1566.36" {
               description "1566.36 nm/191.393750 THz 3.125/6.25GHz spacing";
             }
             enum "1566.34" {
               description "1566.34 nm/191.396875 THz 3.125GHz spacing";
             }
             enum "1566.31" {
               description "1566.31 nm/191.400000 THz 3.125/6.25/12.5/50/75/100GHz spacing";
             }
             enum "1566.29" {
               description "1566.29 nm/191.403125 THz 3.125GHz spacing";
             }
             enum "1566.26" {
               description "1566.26 nm/191.406250 THz 3.125/6.25GHz spacing";
             }
             enum "1566.24" {
               description "1566.24 nm/191.409375 THz 3.125GHz spacing";
             }
             enum "1566.21" {
               description "1566.21 nm/191.412500 THz 3.125/6.25/12.5GHz spacing";
             }
             enum "1566.19" {
               description "1566.19 nm/191.415625 THz 3.125GHz spacing";
             }
             enum "1566.16" {
               description "1566.16 nm/191.418750 THz 3.125/6.25GHz spacing";
             }
             enum "1566.13" {
               description "1566.13 nm/191.421875 THz 3.125GHz spacing";
             }
             enum "1566.11" {
               description "1566.11 nm/191.425000 THz 3.125/6.25/12.5GHz spacing";
             }
             enum "1566.08" {
               description "1566.08 nm/191.428125 THz 3.125GHz spacing";
             }
             enum "1566.06" {
               description "1566.06 nm/191.431250 THz 3.125/6.25GHz spacing";
             }
             enum "1566.03" {
               description "1566.03 nm/191.434375 THz 3.125GHz spacing";
             }
             enum "1566.01" {
               description "1566.01 nm/191.437500 THz 3.125/6.25/12.5GHz spacing";
             }
             enum "1565.98" {
               description "1565.98 nm/191.440625 THz 3.125GHz spacing";
             }
             enum "1565.96" {
               description "1565.96 nm/191.443750 THz 3.125/6.25GHz spacing";
             }
             enum "1565.93" {
               description "1565.93 nm/191.446875 THz 3.125GHz spacing";
             }
             enum "1565.90" {
               description "1565.90 nm/191.450000 THz 3.125/6.25/12.5/50GHz spacing";
             }
             enum "1565.88" {
               description "1565.88 nm/191.453125 THz 3.125GHz spacing";
             }
             enum "1565.85" {
               description "1565.85 nm/191.456250 THz 3.125/6.25GHz spacing";
             }
             enum "1565.83" {
               description "1565.83 nm/191.459375 THz 3.125GHz spacing";
             }
             enum "1565.80" {
               description "1565.80 nm/191.462500 THz 3.125/6.25/12.5GHz spacing";
             }
             enum "1565.78" {
               description "1565.78 nm/191.465625 THz 3.125GHz spacing";
             }
             enum "1565.75" {
               description "1565.75 nm/191.468750 THz 3.125/6.25GHz spacing";
             }
             enum "1565.73" {
               description "1565.73 nm/191.471875 THz 3.125GHz spacing";
             }
             enum "1565.70" {
               description "1565.70 nm/191.475000 THz 3.125/6.25/12.5/75GHz spacing";
             }
             enum "1565.67" {
               description "1565.67 nm/191.478125 THz 3.125GHz spacing";
             }
             enum "1565.65" {
               description "1565.65 nm/191.481250 THz 3.125/6.25GHz spacing";
             }
             enum "1565.62" {
               description "1565.62 nm/191.484375 THz 3.125GHz spacing";
             }
             enum "1565.60" {
               description "1565.60 nm/191.487500 THz 3.125/6.25/12.5GHz spacing";
             }
             enum "1565.57" {
               description "1565.57 nm/191.490625 THz 3.125GHz spacing";
             }
             enum "1565.55" {
               description "1565.55 nm/191.493750 THz 3.125/6.25GHz spacing";
             }
             enum "1565.52" {
               description "1565.52 nm/191.496875 THz 3.125GHz spacing";
             }
             enum "1565.50" {
               description "1565.50 nm/191.500000 THz 3.125/6.25/12.5/100GHz spacing";
             }
             enum "1565.47" {
               description "1565.47 nm/191.503125 THz 3.125GHz spacing";
             }
             enum "1565.44" {
               description "1565.44 nm/191.506250 THz 3.125/6.25GHz spacing";
             }
             enum "1565.42" {
               description "1565.42 nm/191.509375 THz 3.125GHz spacing";
             }
             enum "1565.39" {
               description "1565.39 nm/191.512500 THz 3.125/6.25/12.5GHz spacing";
             }
             enum "1565.37" {
               description "1565.37 nm/191.515625 THz 3.125GHz spacing";
             }
             enum "1565.34" {
               description "1565.34 nm/191.518750 THz 3.125/6.25GHz spacing";
             }
             enum "1565.32" {
               description "1565.32 nm/191.521875 THz 3.125GHz spacing";
             }
             enum "1565.29" {
               description "1565.29 nm/191.525000 THz 3.125/6.25/12.5GHz spacing";
             }
             enum "1565.27" {
               description "1565.27 nm/191.528125 THz 3.125GHz spacing";
             }
             enum "1565.24" {
               description "1565.24 nm/191.531250 THz 3.125/6.25GHz spacing";
             }
             enum "1565.21" {
               description "1565.21 nm/191.534375 THz 3.125GHz spacing";
             }
             enum "1565.19" {
               description "1565.19 nm/191.537500 THz 3.125/6.25/12.5GHz spacing";
             }
             enum "1565.16" {
               description "1565.16 nm/191.540625 THz 3.125GHz spacing";
             }
             enum "1565.14" {
               description "1565.14 nm/191.543750 THz 3.125/6.25GHz spacing";
             }
             enum "1565.11" {
               description "1565.11 nm/191.546875 THz 3.125GHz spacing";
             }
             enum "1565.09" {
               description "1565.09 nm/191.550000 THz 3.125/6.25/12.5/50/75GHz spacing";
             }
             enum "1565.06" {
               description "1565.06 nm/191.553125 THz 3.125GHz spacing";
             }
             enum "1565.04" {
               description "1565.04 nm/191.556250 THz 3.125/6.25GHz spacing";
             }
             enum "1565.01" {
               description "1565.01 nm/191.559375 THz 3.125GHz spacing";
             }
             enum "1564.99" {
               description "1564.99 nm/191.562500 THz 3.125/6.25/12.5GHz spacing";
             }
             enum "1564.96" {
               description "1564.96 nm/191.565625 THz 3.125GHz spacing";
             }
             enum "1564.93" {
               description "1564.93 nm/191.568750 THz 3.125/6.25GHz spacing";
             }
             enum "1564.91" {
               description "1564.91 nm/191.571875 THz 3.125GHz spacing";
             }
             enum "1564.88" {
               description "1564.88 nm/191.575000 THz 3.125/6.25/12.5GHz spacing";
             }
             enum "1564.86" {
               description "1564.86 nm/191.578125 THz 3.125GHz spacing";
             }
             enum "1564.83" {
               description "1564.83 nm/191.581250 THz 3.125/6.25GHz spacing";
             }
             enum "1564.81" {
               description "1564.81 nm/191.584375 THz 3.125GHz spacing";
             }
             enum "1564.78" {
               description "1564.78 nm/191.587500 THz 3.125/6.25/12.5GHz spacing";
             }
             enum "1564.76" {
               description "1564.76 nm/191.590625 THz 3.125GHz spacing";
             }
             enum "1564.73" {
               description "1564.73 nm/191.593750 THz 3.125/6.25GHz spacing";
             }
             enum "1564.70" {
               description "1564.70 nm/191.596875 THz 3.125GHz spacing";
             }
             enum "1564.68" {
               description "1564.68 nm/191.600000 THz 3.125/6.25/12.5/100GHz spacing";
             }
             enum "1564.65" {
               description "1564.65 nm/191.603125 THz 3.125GHz spacing";
             }
             enum "1564.63" {
               description "1564.63 nm/191.606250 THz 3.125/6.25GHz spacing";
             }
             enum "1564.60" {
               description "1564.60 nm/191.609375 THz 3.125GHz spacing";
             }
             enum "1564.58" {
               description "1564.58 nm/191.612500 THz 3.125/6.25/12.5GHz spacing";
             }
             enum "1564.55" {
               description "1564.55 nm/191.615625 THz 3.125GHz spacing";
             }
             enum "1564.53" {
               description "1564.53 nm/191.618750 THz 3.125/6.25GHz spacing";
             }
             enum "1564.50" {
               description "1564.50 nm/191.621875 THz 3.125GHz spacing";
             }
             enum "1564.47" {
               description "1564.47 nm/191.625000 THz 3.125/6.25/12.5/75GHz spacing";
             }
             enum "1564.45" {
               description "1564.45 nm/191.628125 THz 3.125GHz spacing";
             }
             enum "1564.42" {
               description "1564.42 nm/191.631250 THz 3.125/6.25GHz spacing";
             }
             enum "1564.40" {
               description "1564.40 nm/191.634375 THz 3.125GHz spacing";
             }
             enum "1564.37" {
               description "1564.37 nm/191.637500 THz 3.125/6.25/12.5GHz spacing";
             }
             enum "1564.35" {
               description "1564.35 nm/191.640625 THz 3.125GHz spacing";
             }
             enum "1564.32" {
               description "1564.32 nm/191.643750 THz 3.125/6.25GHz spacing";
             }
             enum "1564.30" {
               description "1564.30 nm/191.646875 THz 3.125GHz spacing";
             }
             enum "1564.27" {
               description "1564.27 nm/191.650000 THz 3.125/6.25/12.5/50GHz spacing";
             }
             enum "1564.25" {
               description "1564.25 nm/191.653125 THz 3.125GHz spacing";
             }
             enum "1564.22" {
               description "1564.22 nm/191.656250 THz 3.125/6.25GHz spacing";
             }
             enum "1564.19" {
               description "1564.19 nm/191.659375 THz 3.125GHz spacing";
             }
             enum "1564.17" {
               description "1564.17 nm/191.662500 THz 3.125/6.25/12.5GHz spacing";
             }
             enum "1564.14" {
               description "1564.14 nm/191.665625 THz 3.125GHz spacing";
             }
             enum "1564.12" {
               description "1564.12 nm/191.668750 THz 3.125/6.25GHz spacing";
             }
             enum "1564.09" {
               description "1564.09 nm/191.671875 THz 3.125GHz spacing";
             }
             enum "1564.07" {
               description "1564.07 nm/191.675000 THz 3.125/6.25/12.5GHz spacing";
             }
             enum "1564.04" {
               description "1564.04 nm/191.678125 THz 3.125GHz spacing";
             }
             enum "1564.02" {
               description "1564.02 nm/191.681250 THz 3.125/6.25GHz spacing";
             }
             enum "1563.99" {
               description "1563.99 nm/191.684375 THz 3.125GHz spacing";
             }
             enum "1563.96" {
               description "1563.96 nm/191.687500 THz 3.125/6.25/12.5GHz spacing";
             }
             enum "1563.94" {
               description "1563.94 nm/191.690625 THz 3.125GHz spacing";
             }
             enum "1563.91" {
               description "1563.91 nm/191.693750 THz 3.125/6.25GHz spacing";
             }
             enum "1563.89" {
               description "1563.89 nm/191.696875 THz 3.125GHz spacing";
             }
             enum "1563.86" {
               description "1563.86 nm/191.700000 THz 3.125/6.25/12.5/50/75/100GHz spacing";
             }
             enum "1563.84" {
               description "1563.84 nm/191.703125 THz 3.125GHz spacing";
             }
             enum "1563.81" {
               description "1563.81 nm/191.706250 THz 3.125/6.25GHz spacing";
             }
             enum "1563.79" {
               description "1563.79 nm/191.709375 THz 3.125GHz spacing";
             }
             enum "1563.76" {
               description "1563.76 nm/191.712500 THz 3.125/6.25/12.5GHz spacing";
             }
             enum "1563.74" {
               description "1563.74 nm/191.715625 THz 3.125GHz spacing";
             }
             enum "1563.71" {
               description "1563.71 nm/191.718750 THz 3.125/6.25GHz spacing";
             }
             enum "1563.68" {
               description "1563.68 nm/191.721875 THz 3.125GHz spacing";
             }
             enum "1563.66" {
               description "1563.66 nm/191.725000 THz 3.125/6.25/12.5GHz spacing";
             }
             enum "1563.63" {
               description "1563.63 nm/191.728125 THz 3.125GHz spacing";
             }
             enum "1563.61" {
               description "1563.61 nm/191.731250 THz 3.125/6.25GHz spacing";
             }
             enum "1563.58" {
               description "1563.58 nm/191.734375 THz 3.125GHz spacing";
             }
             enum "1563.56" {
               description "1563.56 nm/191.737500 THz 3.125/6.25/12.5GHz spacing";
             }
             enum "1563.53" {
               description "1563.53 nm/191.740625 THz 3.125GHz spacing";
             }
             enum "1563.51" {
               description "1563.51 nm/191.743750 THz 3.125/6.25GHz spacing";
             }
             enum "1563.48" {
               description "1563.48 nm/191.746875 THz 3.125GHz spacing";
             }
             enum "1563.45" {
               description "1563.45 nm/191.750000 THz 3.125/6.25/12.5/50GHz spacing";
             }
             enum "1563.43" {
               description "1563.43 nm/191.753125 THz 3.125GHz spacing";
             }
             enum "1563.40" {
               description "1563.40 nm/191.756250 THz 3.125/6.25GHz spacing";
             }
             enum "1563.38" {
               description "1563.38 nm/191.759375 THz 3.125GHz spacing";
             }
             enum "1563.35" {
               description "1563.35 nm/191.762500 THz 3.125/6.25/12.5GHz spacing";
             }
             enum "1563.33" {
               description "1563.33 nm/191.765625 THz 3.125GHz spacing";
             }
             enum "1563.30" {
               description "1563.30 nm/191.768750 THz 3.125/6.25GHz spacing";
             }
             enum "1563.28" {
               description "1563.28 nm/191.771875 THz 3.125GHz spacing";
             }
             enum "1563.25" {
               description "1563.25 nm/191.775000 THz 3.125/6.25/12.5/75GHz spacing";
             }
             enum "1563.23" {
               description "1563.23 nm/191.778125 THz 3.125GHz spacing";
             }
             enum "1563.20" {
               description "1563.20 nm/191.781250 THz 3.125/6.25GHz spacing";
             }
             enum "1563.17" {
               description "1563.17 nm/191.784375 THz 3.125GHz spacing";
             }
             enum "1563.15" {
               description "1563.15 nm/191.787500 THz 3.125/6.25/12.5GHz spacing";
             }
             enum "1563.12" {
               description "1563.12 nm/191.790625 THz 3.125GHz spacing";
             }
             enum "1563.10" {
               description "1563.10 nm/191.793750 THz 3.125/6.25GHz spacing";
             }
             enum "1563.07" {
               description "1563.07 nm/191.796875 THz 3.125GHz spacing";
             }
             enum "1563.05" {
               description "1563.05 nm/191.800000 THz 3.125/6.25/12.5/100GHz spacing";
             }
             enum "1563.02" {
               description "1563.02 nm/191.803125 THz 3.125GHz spacing";
             }
             enum "1563.00" {
               description "1563.00 nm/191.806250 THz 3.125/6.25GHz spacing";
             }
             enum "1562.97" {
               description "1562.97 nm/191.809375 THz 3.125GHz spacing";
             }
             enum "1562.95" {
               description "1562.95 nm/191.812500 THz 3.125/6.25/12.5GHz spacing";
             }
             enum "1562.92" {
               description "1562.92 nm/191.815625 THz 3.125GHz spacing";
             }
             enum "1562.89" {
               description "1562.89 nm/191.818750 THz 3.125/6.25GHz spacing";
             }
             enum "1562.87" {
               description "1562.87 nm/191.821875 THz 3.125GHz spacing";
             }
             enum "1562.84" {
               description "1562.84 nm/191.825000 THz 3.125/6.25/12.5GHz spacing";
             }
             enum "1562.82" {
               description "1562.82 nm/191.828125 THz 3.125GHz spacing";
             }
             enum "1562.79" {
               description "1562.79 nm/191.831250 THz 3.125/6.25GHz spacing";
             }
             enum "1562.77" {
               description "1562.77 nm/191.834375 THz 3.125GHz spacing";
             }
             enum "1562.74" {
               description "1562.74 nm/191.837500 THz 3.125/6.25/12.5GHz spacing";
             }
             enum "1562.72" {
               description "1562.72 nm/191.840625 THz 3.125GHz spacing";
             }
             enum "1562.69" {
               description "1562.69 nm/191.843750 THz 3.125/6.25GHz spacing";
             }
             enum "1562.67" {
               description "1562.67 nm/191.846875 THz 3.125GHz spacing";
             }
             enum "1562.64" {
               description "1562.64 nm/191.850000 THz 3.125/6.25/12.5/50/75GHz spacing";
             }
             enum "1562.61" {
               description "1562.61 nm/191.853125 THz 3.125GHz spacing";
             }
             enum "1562.59" {
               description "1562.59 nm/191.856250 THz 3.125/6.25GHz spacing";
             }
             enum "1562.56" {
               description "1562.56 nm/191.859375 THz 3.125GHz spacing";
             }
             enum "1562.54" {
               description "1562.54 nm/191.862500 THz 3.125/6.25/12.5GHz spacing";
             }
             enum "1562.51" {
               description "1562.51 nm/191.865625 THz 3.125GHz spacing";
             }
             enum "1562.49" {
               description "1562.49 nm/191.868750 THz 3.125/6.25GHz spacing";
             }
             enum "1562.46" {
               description "1562.46 nm/191.871875 THz 3.125GHz spacing";
             }
             enum "1562.44" {
               description "1562.44 nm/191.875000 THz 3.125/6.25/12.5GHz spacing";
             }
             enum "1562.41" {
               description "1562.41 nm/191.878125 THz 3.125GHz spacing";
             }
             enum "1562.39" {
               description "1562.39 nm/191.881250 THz 3.125/6.25GHz spacing";
             }
             enum "1562.36" {
               description "1562.36 nm/191.884375 THz 3.125GHz spacing";
             }
             enum "1562.33" {
               description "1562.33 nm/191.887500 THz 3.125/6.25/12.5GHz spacing";
             }
             enum "1562.31" {
               description "1562.31 nm/191.890625 THz 3.125GHz spacing";
             }
             enum "1562.28" {
               description "1562.28 nm/191.893750 THz 3.125/6.25GHz spacing";
             }
             enum "1562.26" {
               description "1562.26 nm/191.896875 THz 3.125GHz spacing";
             }
             enum "1562.23" {
               description "1562.23 nm/191.900000 THz 3.125/6.25/12.5/100GHz spacing";
             }
             enum "1562.21" {
               description "1562.21 nm/191.903125 THz 3.125GHz spacing";
             }
             enum "1562.18" {
               description "1562.18 nm/191.906250 THz 3.125/6.25GHz spacing";
             }
             enum "1562.16" {
               description "1562.16 nm/191.909375 THz 3.125GHz spacing";
             }
             enum "1562.13" {
               description "1562.13 nm/191.912500 THz 3.125/6.25/12.5GHz spacing";
             }
             enum "1562.11" {
               description "1562.11 nm/191.915625 THz 3.125GHz spacing";
             }
             enum "1562.08" {
               description "1562.08 nm/191.918750 THz 3.125/6.25GHz spacing";
             }
             enum "1562.05" {
               description "1562.05 nm/191.921875 THz 3.125GHz spacing";
             }
             enum "1562.03" {
               description "1562.03 nm/191.925000 THz 3.125/6.25/12.5/75GHz spacing";
             }
             enum "1562.00" {
               description "1562.00 nm/191.928125 THz 3.125GHz spacing";
             }
             enum "1561.98" {
               description "1561.98 nm/191.931250 THz 3.125/6.25GHz spacing";
             }
             enum "1561.95" {
               description "1561.95 nm/191.934375 THz 3.125GHz spacing";
             }
             enum "1561.93" {
               description "1561.93 nm/191.937500 THz 3.125/6.25/12.5GHz spacing";
             }
             enum "1561.90" {
               description "1561.90 nm/191.940625 THz 3.125GHz spacing";
             }
             enum "1561.88" {
               description "1561.88 nm/191.943750 THz 3.125/6.25GHz spacing";
             }
             enum "1561.85" {
               description "1561.85 nm/191.946875 THz 3.125GHz spacing";
             }
             enum "1561.83" {
               description "1561.83 nm/191.950000 THz 3.125/6.25/12.5/50GHz spacing";
             }
             enum "1561.80" {
               description "1561.80 nm/191.953125 THz 3.125GHz spacing";
             }
             enum "1561.77" {
               description "1561.77 nm/191.956250 THz 3.125/6.25GHz spacing";
             }
             enum "1561.75" {
               description "1561.75 nm/191.959375 THz 3.125GHz spacing";
             }
             enum "1561.72" {
               description "1561.72 nm/191.962500 THz 3.125/6.25/12.5GHz spacing";
             }
             enum "1561.70" {
               description "1561.70 nm/191.965625 THz 3.125GHz spacing";
             }
             enum "1561.67" {
               description "1561.67 nm/191.968750 THz 3.125/6.25GHz spacing";
             }
             enum "1561.65" {
               description "1561.65 nm/191.971875 THz 3.125GHz spacing";
             }
             enum "1561.62" {
               description "1561.62 nm/191.975000 THz 3.125/6.25/12.5GHz spacing";
             }
             enum "1561.60" {
               description "1561.60 nm/191.978125 THz 3.125GHz spacing";
             }
             enum "1561.57" {
               description "1561.57 nm/191.981250 THz 3.125/6.25GHz spacing";
             }
             enum "1561.55" {
               description "1561.55 nm/191.984375 THz 3.125GHz spacing";
             }
             enum "1561.52" {
               description "1561.52 nm/191.987500 THz 3.125/6.25/12.5GHz spacing";
             }
             enum "1561.50" {
               description "1561.50 nm/191.990625 THz 3.125GHz spacing";
             }
             enum "1561.47" {
               description "1561.47 nm/191.993750 THz 3.125/6.25GHz spacing";
             }
             enum "1561.44" {
               description "1561.44 nm/191.996875 THz 3.125GHz spacing";
             }
             enum "1561.42" {
               description "1561.42 nm/192.000000 THz 3.125/6.25/12.5/50/75/100GHz spacing";
             }
             enum "1561.39" {
               description "1561.39 nm/192.003125 THz 3.125GHz spacing";
             }
             enum "1561.37" {
               description "1561.37 nm/192.006250 THz 3.125/6.25GHz spacing";
             }
             enum "1561.34" {
               description "1561.34 nm/192.009375 THz 3.125GHz spacing";
             }
             enum "1561.32" {
               description "1561.32 nm/192.012500 THz 3.125/6.25/12.5GHz spacing";
             }
             enum "1561.29" {
               description "1561.29 nm/192.015625 THz 3.125GHz spacing";
             }
             enum "1561.27" {
               description "1561.27 nm/192.018750 THz 3.125/6.25GHz spacing";
             }
             enum "1561.24" {
               description "1561.24 nm/192.021875 THz 3.125GHz spacing";
             }
             enum "1561.22" {
               description "1561.22 nm/192.025000 THz 3.125/6.25/12.5GHz spacing";
             }
             enum "1561.19" {
               description "1561.19 nm/192.028125 THz 3.125GHz spacing";
             }
             enum "1561.16" {
               description "1561.16 nm/192.031250 THz 3.125/6.25GHz spacing";
             }
             enum "1561.14" {
               description "1561.14 nm/192.034375 THz 3.125GHz spacing";
             }
             enum "1561.11" {
               description "1561.11 nm/192.037500 THz 3.125/6.25/12.5GHz spacing";
             }
             enum "1561.09" {
               description "1561.09 nm/192.040625 THz 3.125GHz spacing";
             }
             enum "1561.06" {
               description "1561.06 nm/192.043750 THz 3.125/6.25GHz spacing";
             }
             enum "1561.04" {
               description "1561.04 nm/192.046875 THz 3.125GHz spacing";
             }
             enum "1561.01" {
               description "1561.01 nm/192.050000 THz 3.125/6.25/12.5/50GHz spacing";
             }
             enum "1560.99" {
               description "1560.99 nm/192.053125 THz 3.125GHz spacing";
             }
             enum "1560.96" {
               description "1560.96 nm/192.056250 THz 3.125/6.25GHz spacing";
             }
             enum "1560.94" {
               description "1560.94 nm/192.059375 THz 3.125GHz spacing";
             }
             enum "1560.91" {
               description "1560.91 nm/192.062500 THz 3.125/6.25/12.5GHz spacing";
             }
             enum "1560.89" {
               description "1560.89 nm/192.065625 THz 3.125GHz spacing";
             }
             enum "1560.86" {
               description "1560.86 nm/192.068750 THz 3.125/6.25GHz spacing";
             }
             enum "1560.83" {
               description "1560.83 nm/192.071875 THz 3.125GHz spacing";
             }
             enum "1560.81" {
               description "1560.81 nm/192.075000 THz 3.125/6.25/12.5/75GHz spacing";
             }
             enum "1560.78" {
               description "1560.78 nm/192.078125 THz 3.125GHz spacing";
             }
             enum "1560.76" {
               description "1560.76 nm/192.081250 THz 3.125/6.25GHz spacing";
             }
             enum "1560.73" {
               description "1560.73 nm/192.084375 THz 3.125GHz spacing";
             }
             enum "1560.71" {
               description "1560.71 nm/192.087500 THz 3.125/6.25/12.5GHz spacing";
             }
             enum "1560.68" {
               description "1560.68 nm/192.090625 THz 3.125GHz spacing";
             }
             enum "1560.66" {
               description "1560.66 nm/192.093750 THz 3.125/6.25GHz spacing";
             }
             enum "1560.63" {
               description "1560.63 nm/192.096875 THz 3.125GHz spacing";
             }
             enum "1560.61" {
               description "1560.61 nm/192.100000 THz 3.125/6.25/12.5/100GHz spacing";
             }
             enum "1560.58" {
               description "1560.58 nm/192.103125 THz 3.125GHz spacing";
             }
             enum "1560.56" {
               description "1560.56 nm/192.106250 THz 3.125/6.25GHz spacing";
             }
             enum "1560.53" {
               description "1560.53 nm/192.109375 THz 3.125GHz spacing";
             }
             enum "1560.50" {
               description "1560.50 nm/192.112500 THz 3.125/6.25/12.5GHz spacing";
             }
             enum "1560.48" {
               description "1560.48 nm/192.115625 THz 3.125GHz spacing";
             }
             enum "1560.45" {
               description "1560.45 nm/192.118750 THz 3.125/6.25GHz spacing";
             }
             enum "1560.43" {
               description "1560.43 nm/192.121875 THz 3.125GHz spacing";
             }
             enum "1560.40" {
               description "1560.40 nm/192.125000 THz 3.125/6.25/12.5GHz spacing";
             }
             enum "1560.38" {
               description "1560.38 nm/192.128125 THz 3.125GHz spacing";
             }
             enum "1560.35" {
               description "1560.35 nm/192.131250 THz 3.125/6.25GHz spacing";
             }
             enum "1560.33" {
               description "1560.33 nm/192.134375 THz 3.125GHz spacing";
             }
             enum "1560.30" {
               description "1560.30 nm/192.137500 THz 3.125/6.25/12.5GHz spacing";
             }
             enum "1560.28" {
               description "1560.28 nm/192.140625 THz 3.125GHz spacing";
             }
             enum "1560.25" {
               description "1560.25 nm/192.143750 THz 3.125/6.25GHz spacing";
             }
             enum "1560.23" {
               description "1560.23 nm/192.146875 THz 3.125GHz spacing";
             }
             enum "1560.20" {
               description "1560.20 nm/192.150000 THz 3.125/6.25/12.5/50/75GHz spacing";
             }
             enum "1560.17" {
               description "1560.17 nm/192.153125 THz 3.125GHz spacing";
             }
             enum "1560.15" {
               description "1560.15 nm/192.156250 THz 3.125/6.25GHz spacing";
             }
             enum "1560.12" {
               description "1560.12 nm/192.159375 THz 3.125GHz spacing";
             }
             enum "1560.10" {
               description "1560.10 nm/192.162500 THz 3.125/6.25/12.5GHz spacing";
             }
             enum "1560.07" {
               description "1560.07 nm/192.165625 THz 3.125GHz spacing";
             }
             enum "1560.05" {
               description "1560.05 nm/192.168750 THz 3.125/6.25GHz spacing";
             }
             enum "1560.02" {
               description "1560.02 nm/192.171875 THz 3.125GHz spacing";
             }
             enum "1560.00" {
               description "1560.00 nm/192.175000 THz 3.125/6.25/12.5GHz spacing";
             }
             enum "1559.97" {
               description "1559.97 nm/192.178125 THz 3.125GHz spacing";
             }
             enum "1559.95" {
               description "1559.95 nm/192.181250 THz 3.125/6.25GHz spacing";
             }
             enum "1559.92" {
               description "1559.92 nm/192.184375 THz 3.125GHz spacing";
             }
             enum "1559.90" {
               description "1559.90 nm/192.187500 THz 3.125/6.25/12.5GHz spacing";
             }
             enum "1559.87" {
               description "1559.87 nm/192.190625 THz 3.125GHz spacing";
             }
             enum "1559.84" {
               description "1559.84 nm/192.193750 THz 3.125/6.25GHz spacing";
             }
             enum "1559.82" {
               description "1559.82 nm/192.196875 THz 3.125GHz spacing";
             }
             enum "1559.79" {
               description "1559.79 nm/192.200000 THz 3.125/6.25/12.5/100GHz spacing";
             }
             enum "1559.77" {
               description "1559.77 nm/192.203125 THz 3.125GHz spacing";
             }
             enum "1559.74" {
               description "1559.74 nm/192.206250 THz 3.125/6.25GHz spacing";
             }
             enum "1559.72" {
               description "1559.72 nm/192.209375 THz 3.125GHz spacing";
             }
             enum "1559.69" {
               description "1559.69 nm/192.212500 THz 3.125/6.25/12.5GHz spacing";
             }
             enum "1559.67" {
               description "1559.67 nm/192.215625 THz 3.125GHz spacing";
             }
             enum "1559.64" {
               description "1559.64 nm/192.218750 THz 3.125/6.25GHz spacing";
             }
             enum "1559.62" {
               description "1559.62 nm/192.221875 THz 3.125GHz spacing";
             }
             enum "1559.59" {
               description "1559.59 nm/192.225000 THz 3.125/6.25/12.5/75GHz spacing";
             }
             enum "1559.57" {
               description "1559.57 nm/192.228125 THz 3.125GHz spacing";
             }
             enum "1559.54" {
               description "1559.54 nm/192.231250 THz 3.125/6.25GHz spacing";
             }
             enum "1559.52" {
               description "1559.52 nm/192.234375 THz 3.125GHz spacing";
             }
             enum "1559.49" {
               description "1559.49 nm/192.237500 THz 3.125/6.25/12.5GHz spacing";
             }
             enum "1559.46" {
               description "1559.46 nm/192.240625 THz 3.125GHz spacing";
             }
             enum "1559.44" {
               description "1559.44 nm/192.243750 THz 3.125/6.25GHz spacing";
             }
             enum "1559.41" {
               description "1559.41 nm/192.246875 THz 3.125GHz spacing";
             }
             enum "1559.39" {
               description "1559.39 nm/192.250000 THz 3.125/6.25/12.5/50GHz spacing";
             }
             enum "1559.36" {
               description "1559.36 nm/192.253125 THz 3.125GHz spacing";
             }
             enum "1559.34" {
               description "1559.34 nm/192.256250 THz 3.125/6.25GHz spacing";
             }
             enum "1559.31" {
               description "1559.31 nm/192.259375 THz 3.125GHz spacing";
             }
             enum "1559.29" {
               description "1559.29 nm/192.262500 THz 3.125/6.25/12.5GHz spacing";
             }
             enum "1559.26" {
               description "1559.26 nm/192.265625 THz 3.125GHz spacing";
             }
             enum "1559.24" {
               description "1559.24 nm/192.268750 THz 3.125/6.25GHz spacing";
             }
             enum "1559.21" {
               description "1559.21 nm/192.271875 THz 3.125GHz spacing";
             }
             enum "1559.19" {
               description "1559.19 nm/192.275000 THz 3.125/6.25/12.5GHz spacing";
             }
             enum "1559.16" {
               description "1559.16 nm/192.278125 THz 3.125GHz spacing";
             }
             enum "1559.14" {
               description "1559.14 nm/192.281250 THz 3.125/6.25GHz spacing";
             }
             enum "1559.11" {
               description "1559.11 nm/192.284375 THz 3.125GHz spacing";
             }
             enum "1559.08" {
               description "1559.08 nm/192.287500 THz 3.125/6.25/12.5GHz spacing";
             }
             enum "1559.06" {
               description "1559.06 nm/192.290625 THz 3.125GHz spacing";
             }
             enum "1559.03" {
               description "1559.03 nm/192.293750 THz 3.125/6.25GHz spacing";
             }
             enum "1559.01" {
               description "1559.01 nm/192.296875 THz 3.125GHz spacing";
             }
             enum "1558.98" {
               description "1558.98 nm/192.300000 THz 3.125/6.25/12.5/50/75/100GHz spacing";
             }
             enum "1558.96" {
               description "1558.96 nm/192.303125 THz 3.125GHz spacing";
             }
             enum "1558.93" {
               description "1558.93 nm/192.306250 THz 3.125/6.25GHz spacing";
             }
             enum "1558.91" {
               description "1558.91 nm/192.309375 THz 3.125GHz spacing";
             }
             enum "1558.88" {
               description "1558.88 nm/192.312500 THz 3.125/6.25/12.5GHz spacing";
             }
             enum "1558.86" {
               description "1558.86 nm/192.315625 THz 3.125GHz spacing";
             }
             enum "1558.83" {
               description "1558.83 nm/192.318750 THz 3.125/6.25GHz spacing";
             }
             enum "1558.81" {
               description "1558.81 nm/192.321875 THz 3.125GHz spacing";
             }
             enum "1558.78" {
               description "1558.78 nm/192.325000 THz 3.125/6.25/12.5GHz spacing";
             }
             enum "1558.76" {
               description "1558.76 nm/192.328125 THz 3.125GHz spacing";
             }
             enum "1558.73" {
               description "1558.73 nm/192.331250 THz 3.125/6.25GHz spacing";
             }
             enum "1558.70" {
               description "1558.70 nm/192.334375 THz 3.125GHz spacing";
             }
             enum "1558.68" {
               description "1558.68 nm/192.337500 THz 3.125/6.25/12.5GHz spacing";
             }
             enum "1558.65" {
               description "1558.65 nm/192.340625 THz 3.125GHz spacing";
             }
             enum "1558.63" {
               description "1558.63 nm/192.343750 THz 3.125/6.25GHz spacing";
             }
             enum "1558.60" {
               description "1558.60 nm/192.346875 THz 3.125GHz spacing";
             }
             enum "1558.58" {
               description "1558.58 nm/192.350000 THz 3.125/6.25/12.5/50GHz spacing";
             }
             enum "1558.55" {
               description "1558.55 nm/192.353125 THz 3.125GHz spacing";
             }
             enum "1558.53" {
               description "1558.53 nm/192.356250 THz 3.125/6.25GHz spacing";
             }
             enum "1558.50" {
               description "1558.50 nm/192.359375 THz 3.125GHz spacing";
             }
             enum "1558.48" {
               description "1558.48 nm/192.362500 THz 3.125/6.25/12.5GHz spacing";
             }
             enum "1558.45" {
               description "1558.45 nm/192.365625 THz 3.125GHz spacing";
             }
             enum "1558.43" {
               description "1558.43 nm/192.368750 THz 3.125/6.25GHz spacing";
             }
             enum "1558.40" {
               description "1558.40 nm/192.371875 THz 3.125GHz spacing";
             }
             enum "1558.38" {
               description "1558.38 nm/192.375000 THz 3.125/6.25/12.5/75GHz spacing";
             }
             enum "1558.35" {
               description "1558.35 nm/192.378125 THz 3.125GHz spacing";
             }
             enum "1558.32" {
               description "1558.32 nm/192.381250 THz 3.125/6.25GHz spacing";
             }
             enum "1558.30" {
               description "1558.30 nm/192.384375 THz 3.125GHz spacing";
             }
             enum "1558.27" {
               description "1558.27 nm/192.387500 THz 3.125/6.25/12.5GHz spacing";
             }
             enum "1558.25" {
               description "1558.25 nm/192.390625 THz 3.125GHz spacing";
             }
             enum "1558.22" {
               description "1558.22 nm/192.393750 THz 3.125/6.25GHz spacing";
             }
             enum "1558.20" {
               description "1558.20 nm/192.396875 THz 3.125GHz spacing";
             }
             enum "1558.17" {
               description "1558.17 nm/192.400000 THz 3.125/6.25/12.5/100GHz spacing";
             }
             enum "1558.15" {
               description "1558.15 nm/192.403125 THz 3.125GHz spacing";
             }
             enum "1558.12" {
               description "1558.12 nm/192.406250 THz 3.125/6.25GHz spacing";
             }
             enum "1558.10" {
               description "1558.10 nm/192.409375 THz 3.125GHz spacing";
             }
             enum "1558.07" {
               description "1558.07 nm/192.412500 THz 3.125/6.25/12.5GHz spacing";
             }
             enum "1558.05" {
               description "1558.05 nm/192.415625 THz 3.125GHz spacing";
             }
             enum "1558.02" {
               description "1558.02 nm/192.418750 THz 3.125/6.25GHz spacing";
             }
             enum "1558.00" {
               description "1558.00 nm/192.421875 THz 3.125GHz spacing";
             }
             enum "1557.97" {
               description "1557.97 nm/192.425000 THz 3.125/6.25/12.5GHz spacing";
             }
             enum "1557.95" {
               description "1557.95 nm/192.428125 THz 3.125GHz spacing";
             }
             enum "1557.92" {
               description "1557.92 nm/192.431250 THz 3.125/6.25GHz spacing";
             }
             enum "1557.89" {
               description "1557.89 nm/192.434375 THz 3.125GHz spacing";
             }
             enum "1557.87" {
               description "1557.87 nm/192.437500 THz 3.125/6.25/12.5GHz spacing";
             }
             enum "1557.84" {
               description "1557.84 nm/192.440625 THz 3.125GHz spacing";
             }
             enum "1557.82" {
               description "1557.82 nm/192.443750 THz 3.125/6.25GHz spacing";
             }
             enum "1557.79" {
               description "1557.79 nm/192.446875 THz 3.125GHz spacing";
             }
             enum "1557.77" {
               description "1557.77 nm/192.450000 THz 3.125/6.25/12.5/50/75GHz spacing";
             }
             enum "1557.74" {
               description "1557.74 nm/192.453125 THz 3.125GHz spacing";
             }
             enum "1557.72" {
               description "1557.72 nm/192.456250 THz 3.125/6.25GHz spacing";
             }
             enum "1557.69" {
               description "1557.69 nm/192.459375 THz 3.125GHz spacing";
             }
             enum "1557.67" {
               description "1557.67 nm/192.462500 THz 3.125/6.25/12.5GHz spacing";
             }
             enum "1557.64" {
               description "1557.64 nm/192.465625 THz 3.125GHz spacing";
             }
             enum "1557.62" {
               description "1557.62 nm/192.468750 THz 3.125/6.25GHz spacing";
             }
             enum "1557.59" {
               description "1557.59 nm/192.471875 THz 3.125GHz spacing";
             }
             enum "1557.57" {
               description "1557.57 nm/192.475000 THz 3.125/6.25/12.5GHz spacing";
             }
             enum "1557.54" {
               description "1557.54 nm/192.478125 THz 3.125GHz spacing";
             }
             enum "1557.52" {
               description "1557.52 nm/192.481250 THz 3.125/6.25GHz spacing";
             }
             enum "1557.49" {
               description "1557.49 nm/192.484375 THz 3.125GHz spacing";
             }
             enum "1557.46" {
               description "1557.46 nm/192.487500 THz 3.125/6.25/12.5GHz spacing";
             }
             enum "1557.44" {
               description "1557.44 nm/192.490625 THz 3.125GHz spacing";
             }
             enum "1557.41" {
               description "1557.41 nm/192.493750 THz 3.125/6.25GHz spacing";
             }
             enum "1557.39" {
               description "1557.39 nm/192.496875 THz 3.125GHz spacing";
             }
             enum "1557.36" {
               description "1557.36 nm/192.500000 THz 3.125/6.25/12.5/100GHz spacing";
             }
             enum "1557.34" {
               description "1557.34 nm/192.503125 THz 3.125GHz spacing";
             }
             enum "1557.31" {
               description "1557.31 nm/192.506250 THz 3.125/6.25GHz spacing";
             }
             enum "1557.29" {
               description "1557.29 nm/192.509375 THz 3.125GHz spacing";
             }
             enum "1557.26" {
               description "1557.26 nm/192.512500 THz 3.125/6.25/12.5GHz spacing";
             }
             enum "1557.24" {
               description "1557.24 nm/192.515625 THz 3.125GHz spacing";
             }
             enum "1557.21" {
               description "1557.21 nm/192.518750 THz 3.125/6.25GHz spacing";
             }
             enum "1557.19" {
               description "1557.19 nm/192.521875 THz 3.125GHz spacing";
             }
             enum "1557.16" {
               description "1557.16 nm/192.525000 THz 3.125/6.25/12.5/75GHz spacing";
             }
             enum "1557.14" {
               description "1557.14 nm/192.528125 THz 3.125GHz spacing";
             }
             enum "1557.11" {
               description "1557.11 nm/192.531250 THz 3.125/6.25GHz spacing";
             }
             enum "1557.09" {
               description "1557.09 nm/192.534375 THz 3.125GHz spacing";
             }
             enum "1557.06" {
               description "1557.06 nm/192.537500 THz 3.125/6.25/12.5GHz spacing";
             }
             enum "1557.03" {
               description "1557.03 nm/192.540625 THz 3.125GHz spacing";
             }
             enum "1557.01" {
               description "1557.01 nm/192.543750 THz 3.125/6.25GHz spacing";
             }
             enum "1556.98" {
               description "1556.98 nm/192.546875 THz 3.125GHz spacing";
             }
             enum "1556.96" {
               description "1556.96 nm/192.550000 THz 3.125/6.25/12.5/50GHz spacing";
             }
             enum "1556.93" {
               description "1556.93 nm/192.553125 THz 3.125GHz spacing";
             }
             enum "1556.91" {
               description "1556.91 nm/192.556250 THz 3.125/6.25GHz spacing";
             }
             enum "1556.88" {
               description "1556.88 nm/192.559375 THz 3.125GHz spacing";
             }
             enum "1556.86" {
               description "1556.86 nm/192.562500 THz 3.125/6.25/12.5GHz spacing";
             }
             enum "1556.83" {
               description "1556.83 nm/192.565625 THz 3.125GHz spacing";
             }
             enum "1556.81" {
               description "1556.81 nm/192.568750 THz 3.125/6.25GHz spacing";
             }
             enum "1556.78" {
               description "1556.78 nm/192.571875 THz 3.125GHz spacing";
             }
             enum "1556.76" {
               description "1556.76 nm/192.575000 THz 3.125/6.25/12.5GHz spacing";
             }
             enum "1556.73" {
               description "1556.73 nm/192.578125 THz 3.125GHz spacing";
             }
             enum "1556.71" {
               description "1556.71 nm/192.581250 THz 3.125/6.25GHz spacing";
             }
             enum "1556.68" {
               description "1556.68 nm/192.584375 THz 3.125GHz spacing";
             }
             enum "1556.66" {
               description "1556.66 nm/192.587500 THz 3.125/6.25/12.5GHz spacing";
             }
             enum "1556.63" {
               description "1556.63 nm/192.590625 THz 3.125GHz spacing";
             }
             enum "1556.61" {
               description "1556.61 nm/192.593750 THz 3.125/6.25GHz spacing";
             }
             enum "1556.58" {
               description "1556.58 nm/192.596875 THz 3.125GHz spacing";
             }
             enum "1556.55" {
               description "1556.55 nm/192.600000 THz 3.125/6.25/12.5/50/75/100GHz spacing";
             }
             enum "1556.53" {
               description "1556.53 nm/192.603125 THz 3.125GHz spacing";
             }
             enum "1556.50" {
               description "1556.50 nm/192.606250 THz 3.125/6.25GHz spacing";
             }
             enum "1556.48" {
               description "1556.48 nm/192.609375 THz 3.125GHz spacing";
             }
             enum "1556.45" {
               description "1556.45 nm/192.612500 THz 3.125/6.25/12.5GHz spacing";
             }
             enum "1556.43" {
               description "1556.43 nm/192.615625 THz 3.125GHz spacing";
             }
             enum "1556.40" {
               description "1556.40 nm/192.618750 THz 3.125/6.25GHz spacing";
             }
             enum "1556.38" {
               description "1556.38 nm/192.621875 THz 3.125GHz spacing";
             }
             enum "1556.35" {
               description "1556.35 nm/192.625000 THz 3.125/6.25/12.5GHz spacing";
             }
             enum "1556.33" {
               description "1556.33 nm/192.628125 THz 3.125GHz spacing";
             }
             enum "1556.30" {
               description "1556.30 nm/192.631250 THz 3.125/6.25GHz spacing";
             }
             enum "1556.28" {
               description "1556.28 nm/192.634375 THz 3.125GHz spacing";
             }
             enum "1556.25" {
               description "1556.25 nm/192.637500 THz 3.125/6.25/12.5GHz spacing";
             }
             enum "1556.23" {
               description "1556.23 nm/192.640625 THz 3.125GHz spacing";
             }
             enum "1556.20" {
               description "1556.20 nm/192.643750 THz 3.125/6.25GHz spacing";
             }
             enum "1556.18" {
               description "1556.18 nm/192.646875 THz 3.125GHz spacing";
             }
             enum "1556.15" {
               description "1556.15 nm/192.650000 THz 3.125/6.25/12.5/50GHz spacing";
             }
             enum "1556.13" {
               description "1556.13 nm/192.653125 THz 3.125GHz spacing";
             }
             enum "1556.10" {
               description "1556.10 nm/192.656250 THz 3.125/6.25GHz spacing";
             }
             enum "1556.08" {
               description "1556.08 nm/192.659375 THz 3.125GHz spacing";
             }
             enum "1556.05" {
               description "1556.05 nm/192.662500 THz 3.125/6.25/12.5GHz spacing";
             }
             enum "1556.02" {
               description "1556.02 nm/192.665625 THz 3.125GHz spacing";
             }
             enum "1556.00" {
               description "1556.00 nm/192.668750 THz 3.125/6.25GHz spacing";
             }
             enum "1555.97" {
               description "1555.97 nm/192.671875 THz 3.125GHz spacing";
             }
             enum "1555.95" {
               description "1555.95 nm/192.675000 THz 3.125/6.25/12.5/75GHz spacing";
             }
             enum "1555.92" {
               description "1555.92 nm/192.678125 THz 3.125GHz spacing";
             }
             enum "1555.90" {
               description "1555.90 nm/192.681250 THz 3.125/6.25GHz spacing";
             }
             enum "1555.87" {
               description "1555.87 nm/192.684375 THz 3.125GHz spacing";
             }
             enum "1555.85" {
               description "1555.85 nm/192.687500 THz 3.125/6.25/12.5GHz spacing";
             }
             enum "1555.82" {
               description "1555.82 nm/192.690625 THz 3.125GHz spacing";
             }
             enum "1555.80" {
               description "1555.80 nm/192.693750 THz 3.125/6.25GHz spacing";
             }
             enum "1555.77" {
               description "1555.77 nm/192.696875 THz 3.125GHz spacing";
             }
             enum "1555.75" {
               description "1555.75 nm/192.700000 THz 3.125/6.25/12.5/100GHz spacing";
             }
             enum "1555.72" {
               description "1555.72 nm/192.703125 THz 3.125GHz spacing";
             }
             enum "1555.70" {
               description "1555.70 nm/192.706250 THz 3.125/6.25GHz spacing";
             }
             enum "1555.67" {
               description "1555.67 nm/192.709375 THz 3.125GHz spacing";
             }
             enum "1555.65" {
               description "1555.65 nm/192.712500 THz 3.125/6.25/12.5GHz spacing";
             }
             enum "1555.62" {
               description "1555.62 nm/192.715625 THz 3.125GHz spacing";
             }
             enum "1555.60" {
               description "1555.60 nm/192.718750 THz 3.125/6.25GHz spacing";
             }
             enum "1555.57" {
               description "1555.57 nm/192.721875 THz 3.125GHz spacing";
             }
             enum "1555.55" {
               description "1555.55 nm/192.725000 THz 3.125/6.25/12.5GHz spacing";
             }
             enum "1555.52" {
               description "1555.52 nm/192.728125 THz 3.125GHz spacing";
             }
             enum "1555.49" {
               description "1555.49 nm/192.731250 THz 3.125/6.25GHz spacing";
             }
             enum "1555.47" {
               description "1555.47 nm/192.734375 THz 3.125GHz spacing";
             }
             enum "1555.44" {
               description "1555.44 nm/192.737500 THz 3.125/6.25/12.5GHz spacing";
             }
             enum "1555.42" {
               description "1555.42 nm/192.740625 THz 3.125GHz spacing";
             }
             enum "1555.39" {
               description "1555.39 nm/192.743750 THz 3.125/6.25GHz spacing";
             }
             enum "1555.37" {
               description "1555.37 nm/192.746875 THz 3.125GHz spacing";
             }
             enum "1555.34" {
               description "1555.34 nm/192.750000 THz 3.125/6.25/12.5/50/75GHz spacing";
             }
             enum "1555.32" {
               description "1555.32 nm/192.753125 THz 3.125GHz spacing";
             }
             enum "1555.29" {
               description "1555.29 nm/192.756250 THz 3.125/6.25GHz spacing";
             }
             enum "1555.27" {
               description "1555.27 nm/192.759375 THz 3.125GHz spacing";
             }
             enum "1555.24" {
               description "1555.24 nm/192.762500 THz 3.125/6.25/12.5GHz spacing";
             }
             enum "1555.22" {
               description "1555.22 nm/192.765625 THz 3.125GHz spacing";
             }
             enum "1555.19" {
               description "1555.19 nm/192.768750 THz 3.125/6.25GHz spacing";
             }
             enum "1555.17" {
               description "1555.17 nm/192.771875 THz 3.125GHz spacing";
             }
             enum "1555.14" {
               description "1555.14 nm/192.775000 THz 3.125/6.25/12.5GHz spacing";
             }
             enum "1555.12" {
               description "1555.12 nm/192.778125 THz 3.125GHz spacing";
             }
             enum "1555.09" {
               description "1555.09 nm/192.781250 THz 3.125/6.25GHz spacing";
             }
             enum "1555.07" {
               description "1555.07 nm/192.784375 THz 3.125GHz spacing";
             }
             enum "1555.04" {
               description "1555.04 nm/192.787500 THz 3.125/6.25/12.5GHz spacing";
             }
             enum "1555.02" {
               description "1555.02 nm/192.790625 THz 3.125GHz spacing";
             }
             enum "1554.99" {
               description "1554.99 nm/192.793750 THz 3.125/6.25GHz spacing";
             }
             enum "1554.97" {
               description "1554.97 nm/192.796875 THz 3.125GHz spacing";
             }
             enum "1554.94" {
               description "1554.94 nm/192.800000 THz 3.125/6.25/12.5/100GHz spacing";
             }
             enum "1554.91" {
               description "1554.91 nm/192.803125 THz 3.125GHz spacing";
             }
             enum "1554.89" {
               description "1554.89 nm/192.806250 THz 3.125/6.25GHz spacing";
             }
             enum "1554.86" {
               description "1554.86 nm/192.809375 THz 3.125GHz spacing";
             }
             enum "1554.84" {
               description "1554.84 nm/192.812500 THz 3.125/6.25/12.5GHz spacing";
             }
             enum "1554.81" {
               description "1554.81 nm/192.815625 THz 3.125GHz spacing";
             }
             enum "1554.79" {
               description "1554.79 nm/192.818750 THz 3.125/6.25GHz spacing";
             }
             enum "1554.76" {
               description "1554.76 nm/192.821875 THz 3.125GHz spacing";
             }
             enum "1554.74" {
               description "1554.74 nm/192.825000 THz 3.125/6.25/12.5/75GHz spacing";
             }
             enum "1554.71" {
               description "1554.71 nm/192.828125 THz 3.125GHz spacing";
             }
             enum "1554.69" {
               description "1554.69 nm/192.831250 THz 3.125/6.25GHz spacing";
             }
             enum "1554.66" {
               description "1554.66 nm/192.834375 THz 3.125GHz spacing";
             }
             enum "1554.64" {
               description "1554.64 nm/192.837500 THz 3.125/6.25/12.5GHz spacing";
             }
             enum "1554.61" {
               description "1554.61 nm/192.840625 THz 3.125GHz spacing";
             }
             enum "1554.59" {
               description "1554.59 nm/192.843750 THz 3.125/6.25GHz spacing";
             }
             enum "1554.56" {
               description "1554.56 nm/192.846875 THz 3.125GHz spacing";
             }
             enum "1554.54" {
               description "1554.54 nm/192.850000 THz 3.125/6.25/12.5/50GHz spacing";
             }
             enum "1554.51" {
               description "1554.51 nm/192.853125 THz 3.125GHz spacing";
             }
             enum "1554.49" {
               description "1554.49 nm/192.856250 THz 3.125/6.25GHz spacing";
             }
             enum "1554.46" {
               description "1554.46 nm/192.859375 THz 3.125GHz spacing";
             }
             enum "1554.44" {
               description "1554.44 nm/192.862500 THz 3.125/6.25/12.5GHz spacing";
             }
             enum "1554.41" {
               description "1554.41 nm/192.865625 THz 3.125GHz spacing";
             }
             enum "1554.39" {
               description "1554.39 nm/192.868750 THz 3.125/6.25GHz spacing";
             }
             enum "1554.36" {
               description "1554.36 nm/192.871875 THz 3.125GHz spacing";
             }
             enum "1554.34" {
               description "1554.34 nm/192.875000 THz 3.125/6.25/12.5GHz spacing";
             }
             enum "1554.31" {
               description "1554.31 nm/192.878125 THz 3.125GHz spacing";
             }
             enum "1554.29" {
               description "1554.29 nm/192.881250 THz 3.125/6.25GHz spacing";
             }
             enum "1554.26" {
               description "1554.26 nm/192.884375 THz 3.125GHz spacing";
             }
             enum "1554.23" {
               description "1554.23 nm/192.887500 THz 3.125/6.25/12.5GHz spacing";
             }
             enum "1554.21" {
               description "1554.21 nm/192.890625 THz 3.125GHz spacing";
             }
             enum "1554.18" {
               description "1554.18 nm/192.893750 THz 3.125/6.25GHz spacing";
             }
             enum "1554.16" {
               description "1554.16 nm/192.896875 THz 3.125GHz spacing";
             }
             enum "1554.13" {
               description "1554.13 nm/192.900000 THz 3.125/6.25/12.5/50/75/100GHz spacing";
             }
             enum "1554.11" {
               description "1554.11 nm/192.903125 THz 3.125GHz spacing";
             }
             enum "1554.08" {
               description "1554.08 nm/192.906250 THz 3.125/6.25GHz spacing";
             }
             enum "1554.06" {
               description "1554.06 nm/192.909375 THz 3.125GHz spacing";
             }
             enum "1554.03" {
               description "1554.03 nm/192.912500 THz 3.125/6.25/12.5GHz spacing";
             }
             enum "1554.01" {
               description "1554.01 nm/192.915625 THz 3.125GHz spacing";
             }
             enum "1553.98" {
               description "1553.98 nm/192.918750 THz 3.125/6.25GHz spacing";
             }
             enum "1553.96" {
               description "1553.96 nm/192.921875 THz 3.125GHz spacing";
             }
             enum "1553.93" {
               description "1553.93 nm/192.925000 THz 3.125/6.25/12.5GHz spacing";
             }
             enum "1553.91" {
               description "1553.91 nm/192.928125 THz 3.125GHz spacing";
             }
             enum "1553.88" {
               description "1553.88 nm/192.931250 THz 3.125/6.25GHz spacing";
             }
             enum "1553.86" {
               description "1553.86 nm/192.934375 THz 3.125GHz spacing";
             }
             enum "1553.83" {
               description "1553.83 nm/192.937500 THz 3.125/6.25/12.5GHz spacing";
             }
             enum "1553.81" {
               description "1553.81 nm/192.940625 THz 3.125GHz spacing";
             }
             enum "1553.78" {
               description "1553.78 nm/192.943750 THz 3.125/6.25GHz spacing";
             }
             enum "1553.76" {
               description "1553.76 nm/192.946875 THz 3.125GHz spacing";
             }
             enum "1553.73" {
               description "1553.73 nm/192.950000 THz 3.125/6.25/12.5/50GHz spacing";
             }
             enum "1553.71" {
               description "1553.71 nm/192.953125 THz 3.125GHz spacing";
             }
             enum "1553.68" {
               description "1553.68 nm/192.956250 THz 3.125/6.25GHz spacing";
             }
             enum "1553.66" {
               description "1553.66 nm/192.959375 THz 3.125GHz spacing";
             }
             enum "1553.63" {
               description "1553.63 nm/192.962500 THz 3.125/6.25/12.5GHz spacing";
             }
             enum "1553.61" {
               description "1553.61 nm/192.965625 THz 3.125GHz spacing";
             }
             enum "1553.58" {
               description "1553.58 nm/192.968750 THz 3.125/6.25GHz spacing";
             }
             enum "1553.56" {
               description "1553.56 nm/192.971875 THz 3.125GHz spacing";
             }
             enum "1553.53" {
               description "1553.53 nm/192.975000 THz 3.125/6.25/12.5/75GHz spacing";
             }
             enum "1553.50" {
               description "1553.50 nm/192.978125 THz 3.125GHz spacing";
             }
             enum "1553.48" {
               description "1553.48 nm/192.981250 THz 3.125/6.25GHz spacing";
             }
             enum "1553.45" {
               description "1553.45 nm/192.984375 THz 3.125GHz spacing";
             }
             enum "1553.43" {
               description "1553.43 nm/192.987500 THz 3.125/6.25/12.5GHz spacing";
             }
             enum "1553.40" {
               description "1553.40 nm/192.990625 THz 3.125GHz spacing";
             }
             enum "1553.38" {
               description "1553.38 nm/192.993750 THz 3.125/6.25GHz spacing";
             }
             enum "1553.35" {
               description "1553.35 nm/192.996875 THz 3.125GHz spacing";
             }
             enum "1553.33" {
               description "1553.33 nm/193.000000 THz 3.125/6.25/12.5/100GHz spacing";
             }
             enum "1553.30" {
               description "1553.30 nm/193.003125 THz 3.125GHz spacing";
             }
             enum "1553.28" {
               description "1553.28 nm/193.006250 THz 3.125/6.25GHz spacing";
             }
             enum "1553.25" {
               description "1553.25 nm/193.009375 THz 3.125GHz spacing";
             }
             enum "1553.23" {
               description "1553.23 nm/193.012500 THz 3.125/6.25/12.5GHz spacing";
             }
             enum "1553.20" {
               description "1553.20 nm/193.015625 THz 3.125GHz spacing";
             }
             enum "1553.18" {
               description "1553.18 nm/193.018750 THz 3.125/6.25GHz spacing";
             }
             enum "1553.15" {
               description "1553.15 nm/193.021875 THz 3.125GHz spacing";
             }
             enum "1553.13" {
               description "1553.13 nm/193.025000 THz 3.125/6.25/12.5GHz spacing";
             }
             enum "1553.10" {
               description "1553.10 nm/193.028125 THz 3.125GHz spacing";
             }
             enum "1553.08" {
               description "1553.08 nm/193.031250 THz 3.125/6.25GHz spacing";
             }
             enum "1553.05" {
               description "1553.05 nm/193.034375 THz 3.125GHz spacing";
             }
             enum "1553.03" {
               description "1553.03 nm/193.037500 THz 3.125/6.25/12.5GHz spacing";
             }
             enum "1553.00" {
               description "1553.00 nm/193.040625 THz 3.125GHz spacing";
             }
             enum "1552.98" {
               description "1552.98 nm/193.043750 THz 3.125/6.25GHz spacing";
             }
             enum "1552.95" {
               description "1552.95 nm/193.046875 THz 3.125GHz spacing";
             }
             enum "1552.93" {
               description "1552.93 nm/193.050000 THz 3.125/6.25/12.5/50/75GHz spacing";
             }
             enum "1552.90" {
               description "1552.90 nm/193.053125 THz 3.125GHz spacing";
             }
             enum "1552.88" {
               description "1552.88 nm/193.056250 THz 3.125/6.25GHz spacing";
             }
             enum "1552.85" {
               description "1552.85 nm/193.059375 THz 3.125GHz spacing";
             }
             enum "1552.83" {
               description "1552.83 nm/193.062500 THz 3.125/6.25/12.5GHz spacing";
             }
             enum "1552.80" {
               description "1552.80 nm/193.065625 THz 3.125GHz spacing";
             }
             enum "1552.78" {
               description "1552.78 nm/193.068750 THz 3.125/6.25GHz spacing";
             }
             enum "1552.75" {
               description "1552.75 nm/193.071875 THz 3.125GHz spacing";
             }
             enum "1552.73" {
               description "1552.73 nm/193.075000 THz 3.125/6.25/12.5GHz spacing";
             }
             enum "1552.70" {
               description "1552.70 nm/193.078125 THz 3.125GHz spacing";
             }
             enum "1552.68" {
               description "1552.68 nm/193.081250 THz 3.125/6.25GHz spacing";
             }
             enum "1552.65" {
               description "1552.65 nm/193.084375 THz 3.125GHz spacing";
             }
             enum "1552.62" {
               description "1552.62 nm/193.087500 THz 3.125/6.25/12.5GHz spacing";
             }
             enum "1552.60" {
               description "1552.60 nm/193.090625 THz 3.125GHz spacing";
             }
             enum "1552.57" {
               description "1552.57 nm/193.093750 THz 3.125/6.25GHz spacing";
             }
             enum "1552.55" {
               description "1552.55 nm/193.096875 THz 3.125GHz spacing";
             }
             enum "1552.52" {
               description "1552.52 nm/193.100000 THz 3.125/6.25/12.5/100GHz spacing";
             }
             enum "1552.50" {
               description "1552.50 nm/193.103125 THz 3.125GHz spacing";
             }
             enum "1552.47" {
               description "1552.47 nm/193.106250 THz 3.125/6.25GHz spacing";
             }
             enum "1552.45" {
               description "1552.45 nm/193.109375 THz 3.125GHz spacing";
             }
             enum "1552.42" {
               description "1552.42 nm/193.112500 THz 3.125/6.25/12.5GHz spacing";
             }
             enum "1552.40" {
               description "1552.40 nm/193.115625 THz 3.125GHz spacing";
             }
             enum "1552.37" {
               description "1552.37 nm/193.118750 THz 3.125/6.25GHz spacing";
             }
             enum "1552.35" {
               description "1552.35 nm/193.121875 THz 3.125GHz spacing";
             }
             enum "1552.32" {
               description "1552.32 nm/193.125000 THz 3.125/6.25/12.5/75GHz spacing";
             }
             enum "1552.30" {
               description "1552.30 nm/193.128125 THz 3.125GHz spacing";
             }
             enum "1552.27" {
               description "1552.27 nm/193.131250 THz 3.125/6.25GHz spacing";
             }
             enum "1552.25" {
               description "1552.25 nm/193.134375 THz 3.125GHz spacing";
             }
             enum "1552.22" {
               description "1552.22 nm/193.137500 THz 3.125/6.25/12.5GHz spacing";
             }
             enum "1552.20" {
               description "1552.20 nm/193.140625 THz 3.125GHz spacing";
             }
             enum "1552.17" {
               description "1552.17 nm/193.143750 THz 3.125/6.25GHz spacing";
             }
             enum "1552.15" {
               description "1552.15 nm/193.146875 THz 3.125GHz spacing";
             }
             enum "1552.12" {
               description "1552.12 nm/193.150000 THz 3.125/6.25/12.5/50GHz spacing";
             }
             enum "1552.10" {
               description "1552.10 nm/193.153125 THz 3.125GHz spacing";
             }
             enum "1552.07" {
               description "1552.07 nm/193.156250 THz 3.125/6.25GHz spacing";
             }
             enum "1552.05" {
               description "1552.05 nm/193.159375 THz 3.125GHz spacing";
             }
             enum "1552.02" {
               description "1552.02 nm/193.162500 THz 3.125/6.25/12.5GHz spacing";
             }
             enum "1552.00" {
               description "1552.00 nm/193.165625 THz 3.125GHz spacing";
             }
             enum "1551.97" {
               description "1551.97 nm/193.168750 THz 3.125/6.25GHz spacing";
             }
             enum "1551.95" {
               description "1551.95 nm/193.171875 THz 3.125GHz spacing";
             }
             enum "1551.92" {
               description "1551.92 nm/193.175000 THz 3.125/6.25/12.5GHz spacing";
             }
             enum "1551.90" {
               description "1551.90 nm/193.178125 THz 3.125GHz spacing";
             }
             enum "1551.87" {
               description "1551.87 nm/193.181250 THz 3.125/6.25GHz spacing";
             }
             enum "1551.85" {
               description "1551.85 nm/193.184375 THz 3.125GHz spacing";
             }
             enum "1551.82" {
               description "1551.82 nm/193.187500 THz 3.125/6.25/12.5GHz spacing";
             }
             enum "1551.80" {
               description "1551.80 nm/193.190625 THz 3.125GHz spacing";
             }
             enum "1551.77" {
               description "1551.77 nm/193.193750 THz 3.125/6.25GHz spacing";
             }
             enum "1551.75" {
               description "1551.75 nm/193.196875 THz 3.125GHz spacing";
             }
             enum "1551.72" {
               description "1551.72 nm/193.200000 THz 3.125/6.25/12.5/50/75/100GHz spacing";
             }
             enum "1551.70" {
               description "1551.70 nm/193.203125 THz 3.125GHz spacing";
             }
             enum "1551.67" {
               description "1551.67 nm/193.206250 THz 3.125/6.25GHz spacing";
             }
             enum "1551.65" {
               description "1551.65 nm/193.209375 THz 3.125GHz spacing";
             }
             enum "1551.62" {
               description "1551.62 nm/193.212500 THz 3.125/6.25/12.5GHz spacing";
             }
             enum "1551.60" {
               description "1551.60 nm/193.215625 THz 3.125GHz spacing";
             }
             enum "1551.57" {
               description "1551.57 nm/193.218750 THz 3.125/6.25GHz spacing";
             }
             enum "1551.55" {
               description "1551.55 nm/193.221875 THz 3.125GHz spacing";
             }
             enum "1551.52" {
               description "1551.52 nm/193.225000 THz 3.125/6.25/12.5GHz spacing";
             }
             enum "1551.49" {
               description "1551.49 nm/193.228125 THz 3.125GHz spacing";
             }
             enum "1551.47" {
               description "1551.47 nm/193.231250 THz 3.125/6.25GHz spacing";
             }
             enum "1551.44" {
               description "1551.44 nm/193.234375 THz 3.125GHz spacing";
             }
             enum "1551.42" {
               description "1551.42 nm/193.237500 THz 3.125/6.25/12.5GHz spacing";
             }
             enum "1551.39" {
               description "1551.39 nm/193.240625 THz 3.125GHz spacing";
             }
             enum "1551.37" {
               description "1551.37 nm/193.243750 THz 3.125/6.25GHz spacing";
             }
             enum "1551.34" {
               description "1551.34 nm/193.246875 THz 3.125GHz spacing";
             }
             enum "1551.32" {
               description "1551.32 nm/193.250000 THz 3.125/6.25/12.5/50GHz spacing";
             }
             enum "1551.29" {
               description "1551.29 nm/193.253125 THz 3.125GHz spacing";
             }
             enum "1551.27" {
               description "1551.27 nm/193.256250 THz 3.125/6.25GHz spacing";
             }
             enum "1551.24" {
               description "1551.24 nm/193.259375 THz 3.125GHz spacing";
             }
             enum "1551.22" {
               description "1551.22 nm/193.262500 THz 3.125/6.25/12.5GHz spacing";
             }
             enum "1551.19" {
               description "1551.19 nm/193.265625 THz 3.125GHz spacing";
             }
             enum "1551.17" {
               description "1551.17 nm/193.268750 THz 3.125/6.25GHz spacing";
             }
             enum "1551.14" {
               description "1551.14 nm/193.271875 THz 3.125GHz spacing";
             }
             enum "1551.12" {
               description "1551.12 nm/193.275000 THz 3.125/6.25/12.5/75GHz spacing";
             }
             enum "1551.09" {
               description "1551.09 nm/193.278125 THz 3.125GHz spacing";
             }
             enum "1551.07" {
               description "1551.07 nm/193.281250 THz 3.125/6.25GHz spacing";
             }
             enum "1551.04" {
               description "1551.04 nm/193.284375 THz 3.125GHz spacing";
             }
             enum "1551.02" {
               description "1551.02 nm/193.287500 THz 3.125/6.25/12.5GHz spacing";
             }
             enum "1550.99" {
               description "1550.99 nm/193.290625 THz 3.125GHz spacing";
             }
             enum "1550.97" {
               description "1550.97 nm/193.293750 THz 3.125/6.25GHz spacing";
             }
             enum "1550.94" {
               description "1550.94 nm/193.296875 THz 3.125GHz spacing";
             }
             enum "1550.92" {
               description "1550.92 nm/193.300000 THz 3.125/6.25/12.5/100GHz spacing";
             }
             enum "1550.89" {
               description "1550.89 nm/193.303125 THz 3.125GHz spacing";
             }
             enum "1550.87" {
               description "1550.87 nm/193.306250 THz 3.125/6.25GHz spacing";
             }
             enum "1550.84" {
               description "1550.84 nm/193.309375 THz 3.125GHz spacing";
             }
             enum "1550.82" {
               description "1550.82 nm/193.312500 THz 3.125/6.25/12.5GHz spacing";
             }
             enum "1550.79" {
               description "1550.79 nm/193.315625 THz 3.125GHz spacing";
             }
             enum "1550.77" {
               description "1550.77 nm/193.318750 THz 3.125/6.25GHz spacing";
             }
             enum "1550.74" {
               description "1550.74 nm/193.321875 THz 3.125GHz spacing";
             }
             enum "1550.72" {
               description "1550.72 nm/193.325000 THz 3.125/6.25/12.5GHz spacing";
             }
             enum "1550.69" {
               description "1550.69 nm/193.328125 THz 3.125GHz spacing";
             }
             enum "1550.67" {
               description "1550.67 nm/193.331250 THz 3.125/6.25GHz spacing";
             }
             enum "1550.64" {
               description "1550.64 nm/193.334375 THz 3.125GHz spacing";
             }
             enum "1550.62" {
               description "1550.62 nm/193.337500 THz 3.125/6.25/12.5GHz spacing";
             }
             enum "1550.59" {
               description "1550.59 nm/193.340625 THz 3.125GHz spacing";
             }
             enum "1550.57" {
               description "1550.57 nm/193.343750 THz 3.125/6.25GHz spacing";
             }
             enum "1550.54" {
               description "1550.54 nm/193.346875 THz 3.125GHz spacing";
             }
             enum "1550.52" {
               description "1550.52 nm/193.350000 THz 3.125/6.25/12.5/50/75GHz spacing";
             }
             enum "1550.49" {
               description "1550.49 nm/193.353125 THz 3.125GHz spacing";
             }
             enum "1550.47" {
               description "1550.47 nm/193.356250 THz 3.125/6.25GHz spacing";
             }
             enum "1550.44" {
               description "1550.44 nm/193.359375 THz 3.125GHz spacing";
             }
             enum "1550.42" {
               description "1550.42 nm/193.362500 THz 3.125/6.25/12.5GHz spacing";
             }
             enum "1550.39" {
               description "1550.39 nm/193.365625 THz 3.125GHz spacing";
             }
             enum "1550.37" {
               description "1550.37 nm/193.368750 THz 3.125/6.25GHz spacing";
             }
             enum "1550.34" {
               description "1550.34 nm/193.371875 THz 3.125GHz spacing";
             }
             enum "1550.32" {
               description "1550.32 nm/193.375000 THz 3.125/6.25/12.5GHz spacing";
             }
             enum "1550.29" {
               description "1550.29 nm/193.378125 THz 3.125GHz spacing";
             }
             enum "1550.27" {
               description "1550.27 nm/193.381250 THz 3.125/6.25GHz spacing";
             }
             enum "1550.24" {
               description "1550.24 nm/193.384375 THz 3.125GHz spacing";
             }
             enum "1550.22" {
               description "1550.22 nm/193.387500 THz 3.125/6.25/12.5GHz spacing";
             }
             enum "1550.19" {
               description "1550.19 nm/193.390625 THz 3.125GHz spacing";
             }
             enum "1550.17" {
               description "1550.17 nm/193.393750 THz 3.125/6.25GHz spacing";
             }
             enum "1550.14" {
               description "1550.14 nm/193.396875 THz 3.125GHz spacing";
             }
             enum "1550.12" {
               description "1550.12 nm/193.400000 THz 3.125/6.25/12.5/100GHz spacing";
             }
             enum "1550.09" {
               description "1550.09 nm/193.403125 THz 3.125GHz spacing";
             }
             enum "1550.07" {
               description "1550.07 nm/193.406250 THz 3.125/6.25GHz spacing";
             }
             enum "1550.04" {
               description "1550.04 nm/193.409375 THz 3.125GHz spacing";
             }
             enum "1550.02" {
               description "1550.02 nm/193.412500 THz 3.125/6.25/12.5GHz spacing";
             }
             enum "1549.99" {
               description "1549.99 nm/193.415625 THz 3.125GHz spacing";
             }
             enum "1549.97" {
               description "1549.97 nm/193.418750 THz 3.125/6.25GHz spacing";
             }
             enum "1549.94" {
               description "1549.94 nm/193.421875 THz 3.125GHz spacing";
             }
             enum "1549.92" {
               description "1549.92 nm/193.425000 THz 3.125/6.25/12.5/75GHz spacing";
             }
             enum "1549.89" {
               description "1549.89 nm/193.428125 THz 3.125GHz spacing";
             }
             enum "1549.87" {
               description "1549.87 nm/193.431250 THz 3.125/6.25GHz spacing";
             }
             enum "1549.84" {
               description "1549.84 nm/193.434375 THz 3.125GHz spacing";
             }
             enum "1549.82" {
               description "1549.82 nm/193.437500 THz 3.125/6.25/12.5GHz spacing";
             }
             enum "1549.79" {
               description "1549.79 nm/193.440625 THz 3.125GHz spacing";
             }
             enum "1549.77" {
               description "1549.77 nm/193.443750 THz 3.125/6.25GHz spacing";
             }
             enum "1549.74" {
               description "1549.74 nm/193.446875 THz 3.125GHz spacing";
             }
             enum "1549.72" {
               description "1549.72 nm/193.450000 THz 3.125/6.25/12.5/50GHz spacing";
             }
             enum "1549.69" {
               description "1549.69 nm/193.453125 THz 3.125GHz spacing";
             }
             enum "1549.67" {
               description "1549.67 nm/193.456250 THz 3.125/6.25GHz spacing";
             }
             enum "1549.64" {
               description "1549.64 nm/193.459375 THz 3.125GHz spacing";
             }
             enum "1549.62" {
               description "1549.62 nm/193.462500 THz 3.125/6.25/12.5GHz spacing";
             }
             enum "1549.59" {
               description "1549.59 nm/193.465625 THz 3.125GHz spacing";
             }
             enum "1549.57" {
               description "1549.57 nm/193.468750 THz 3.125/6.25GHz spacing";
             }
             enum "1549.54" {
               description "1549.54 nm/193.471875 THz 3.125GHz spacing";
             }
             enum "1549.52" {
               description "1549.52 nm/193.475000 THz 3.125/6.25/12.5GHz spacing";
             }
             enum "1549.49" {
               description "1549.49 nm/193.478125 THz 3.125GHz spacing";
             }
             enum "1549.47" {
               description "1549.47 nm/193.481250 THz 3.125/6.25GHz spacing";
             }
             enum "1549.44" {
               description "1549.44 nm/193.484375 THz 3.125GHz spacing";
             }
             enum "1549.42" {
               description "1549.42 nm/193.487500 THz 3.125/6.25/12.5GHz spacing";
             }
             enum "1549.39" {
               description "1549.39 nm/193.490625 THz 3.125GHz spacing";
             }
             enum "1549.37" {
               description "1549.37 nm/193.493750 THz 3.125/6.25GHz spacing";
             }
             enum "1549.34" {
               description "1549.34 nm/193.496875 THz 3.125GHz spacing";
             }
             enum "1549.32" {
               description "1549.32 nm/193.500000 THz 3.125/6.25/12.5/50/75/100GHz spacing";
             }
             enum "1549.29" {
               description "1549.29 nm/193.503125 THz 3.125GHz spacing";
             }
             enum "1549.26" {
               description "1549.26 nm/193.506250 THz 3.125/6.25GHz spacing";
             }
             enum "1549.24" {
               description "1549.24 nm/193.509375 THz 3.125GHz spacing";
             }
             enum "1549.21" {
               description "1549.21 nm/193.512500 THz 3.125/6.25/12.5GHz spacing";
             }
             enum "1549.19" {
               description "1549.19 nm/193.515625 THz 3.125GHz spacing";
             }
             enum "1549.16" {
               description "1549.16 nm/193.518750 THz 3.125/6.25GHz spacing";
             }
             enum "1549.14" {
               description "1549.14 nm/193.521875 THz 3.125GHz spacing";
             }
             enum "1549.11" {
               description "1549.11 nm/193.525000 THz 3.125/6.25/12.5GHz spacing";
             }
             enum "1549.09" {
               description "1549.09 nm/193.528125 THz 3.125GHz spacing";
             }
             enum "1549.06" {
               description "1549.06 nm/193.531250 THz 3.125/6.25GHz spacing";
             }
             enum "1549.04" {
               description "1549.04 nm/193.534375 THz 3.125GHz spacing";
             }
             enum "1549.01" {
               description "1549.01 nm/193.537500 THz 3.125/6.25/12.5GHz spacing";
             }
             enum "1548.99" {
               description "1548.99 nm/193.540625 THz 3.125GHz spacing";
             }
             enum "1548.96" {
               description "1548.96 nm/193.543750 THz 3.125/6.25GHz spacing";
             }
             enum "1548.94" {
               description "1548.94 nm/193.546875 THz 3.125GHz spacing";
             }
             enum "1548.91" {
               description "1548.91 nm/193.550000 THz 3.125/6.25/12.5/50GHz spacing";
             }
             enum "1548.89" {
               description "1548.89 nm/193.553125 THz 3.125GHz spacing";
             }
             enum "1548.86" {
               description "1548.86 nm/193.556250 THz 3.125/6.25GHz spacing";
             }
             enum "1548.84" {
               description "1548.84 nm/193.559375 THz 3.125GHz spacing";
             }
             enum "1548.81" {
               description "1548.81 nm/193.562500 THz 3.125/6.25/12.5GHz spacing";
             }
             enum "1548.79" {
               description "1548.79 nm/193.565625 THz 3.125GHz spacing";
             }
             enum "1548.76" {
               description "1548.76 nm/193.568750 THz 3.125/6.25GHz spacing";
             }
             enum "1548.74" {
               description "1548.74 nm/193.571875 THz 3.125GHz spacing";
             }
             enum "1548.71" {
               description "1548.71 nm/193.575000 THz 3.125/6.25/12.5/75GHz spacing";
             }
             enum "1548.69" {
               description "1548.69 nm/193.578125 THz 3.125GHz spacing";
             }
             enum "1548.66" {
               description "1548.66 nm/193.581250 THz 3.125/6.25GHz spacing";
             }
             enum "1548.64" {
               description "1548.64 nm/193.584375 THz 3.125GHz spacing";
             }
             enum "1548.61" {
               description "1548.61 nm/193.587500 THz 3.125/6.25/12.5GHz spacing";
             }
             enum "1548.59" {
               description "1548.59 nm/193.590625 THz 3.125GHz spacing";
             }
             enum "1548.56" {
               description "1548.56 nm/193.593750 THz 3.125/6.25GHz spacing";
             }
             enum "1548.54" {
               description "1548.54 nm/193.596875 THz 3.125GHz spacing";
             }
             enum "1548.51" {
               description "1548.51 nm/193.600000 THz 3.125/6.25/12.5/100GHz spacing";
             }
             enum "1548.49" {
               description "1548.49 nm/193.603125 THz 3.125GHz spacing";
             }
             enum "1548.46" {
               description "1548.46 nm/193.606250 THz 3.125/6.25GHz spacing";
             }
             enum "1548.44" {
               description "1548.44 nm/193.609375 THz 3.125GHz spacing";
             }
             enum "1548.41" {
               description "1548.41 nm/193.612500 THz 3.125/6.25/12.5GHz spacing";
             }
             enum "1548.39" {
               description "1548.39 nm/193.615625 THz 3.125GHz spacing";
             }
             enum "1548.36" {
               description "1548.36 nm/193.618750 THz 3.125/6.25GHz spacing";
             }
             enum "1548.34" {
               description "1548.34 nm/193.621875 THz 3.125GHz spacing";
             }
             enum "1548.31" {
               description "1548.31 nm/193.625000 THz 3.125/6.25/12.5GHz spacing";
             }
             enum "1548.29" {
               description "1548.29 nm/193.628125 THz 3.125GHz spacing";
             }
             enum "1548.26" {
               description "1548.26 nm/193.631250 THz 3.125/6.25GHz spacing";
             }
             enum "1548.24" {
               description "1548.24 nm/193.634375 THz 3.125GHz spacing";
             }
             enum "1548.21" {
               description "1548.21 nm/193.637500 THz 3.125/6.25/12.5GHz spacing";
             }
             enum "1548.19" {
               description "1548.19 nm/193.640625 THz 3.125GHz spacing";
             }
             enum "1548.16" {
               description "1548.16 nm/193.643750 THz 3.125/6.25GHz spacing";
             }
             enum "1548.14" {
               description "1548.14 nm/193.646875 THz 3.125GHz spacing";
             }
             enum "1548.11" {
               description "1548.11 nm/193.650000 THz 3.125/6.25/12.5/50/75GHz spacing";
             }
             enum "1548.09" {
               description "1548.09 nm/193.653125 THz 3.125GHz spacing";
             }
             enum "1548.06" {
               description "1548.06 nm/193.656250 THz 3.125/6.25GHz spacing";
             }
             enum "1548.04" {
               description "1548.04 nm/193.659375 THz 3.125GHz spacing";
             }
             enum "1548.02" {
               description "1548.02 nm/193.662500 THz 3.125/6.25/12.5GHz spacing";
             }
             enum "1547.99" {
               description "1547.99 nm/193.665625 THz 3.125GHz spacing";
             }
             enum "1547.97" {
               description "1547.97 nm/193.668750 THz 3.125/6.25GHz spacing";
             }
             enum "1547.94" {
               description "1547.94 nm/193.671875 THz 3.125GHz spacing";
             }
             enum "1547.92" {
               description "1547.92 nm/193.675000 THz 3.125/6.25/12.5GHz spacing";
             }
             enum "1547.89" {
               description "1547.89 nm/193.678125 THz 3.125GHz spacing";
             }
             enum "1547.87" {
               description "1547.87 nm/193.681250 THz 3.125/6.25GHz spacing";
             }
             enum "1547.84" {
               description "1547.84 nm/193.684375 THz 3.125GHz spacing";
             }
             enum "1547.82" {
               description "1547.82 nm/193.687500 THz 3.125/6.25/12.5GHz spacing";
             }
             enum "1547.79" {
               description "1547.79 nm/193.690625 THz 3.125GHz spacing";
             }
             enum "1547.77" {
               description "1547.77 nm/193.693750 THz 3.125/6.25GHz spacing";
             }
             enum "1547.74" {
               description "1547.74 nm/193.696875 THz 3.125GHz spacing";
             }
             enum "1547.72" {
               description "1547.72 nm/193.700000 THz 3.125/6.25/12.5/100GHz spacing";
             }
             enum "1547.69" {
               description "1547.69 nm/193.703125 THz 3.125GHz spacing";
             }
             enum "1547.67" {
               description "1547.67 nm/193.706250 THz 3.125/6.25GHz spacing";
             }
             enum "1547.64" {
               description "1547.64 nm/193.709375 THz 3.125GHz spacing";
             }
             enum "1547.62" {
               description "1547.62 nm/193.712500 THz 3.125/6.25/12.5GHz spacing";
             }
             enum "1547.59" {
               description "1547.59 nm/193.715625 THz 3.125GHz spacing";
             }
             enum "1547.57" {
               description "1547.57 nm/193.718750 THz 3.125/6.25GHz spacing";
             }
             enum "1547.54" {
               description "1547.54 nm/193.721875 THz 3.125GHz spacing";
             }
             enum "1547.52" {
               description "1547.52 nm/193.725000 THz 3.125/6.25/12.5/75GHz spacing";
             }
             enum "1547.49" {
               description "1547.49 nm/193.728125 THz 3.125GHz spacing";
             }
             enum "1547.47" {
               description "1547.47 nm/193.731250 THz 3.125/6.25GHz spacing";
             }
             enum "1547.44" {
               description "1547.44 nm/193.734375 THz 3.125GHz spacing";
             }
             enum "1547.42" {
               description "1547.42 nm/193.737500 THz 3.125/6.25/12.5GHz spacing";
             }
             enum "1547.39" {
               description "1547.39 nm/193.740625 THz 3.125GHz spacing";
             }
             enum "1547.37" {
               description "1547.37 nm/193.743750 THz 3.125/6.25GHz spacing";
             }
             enum "1547.34" {
               description "1547.34 nm/193.746875 THz 3.125GHz spacing";
             }
             enum "1547.32" {
               description "1547.32 nm/193.750000 THz 3.125/6.25/12.5/50GHz spacing";
             }
             enum "1547.29" {
               description "1547.29 nm/193.753125 THz 3.125GHz spacing";
             }
             enum "1547.27" {
               description "1547.27 nm/193.756250 THz 3.125/6.25GHz spacing";
             }
             enum "1547.24" {
               description "1547.24 nm/193.759375 THz 3.125GHz spacing";
             }
             enum "1547.22" {
               description "1547.22 nm/193.762500 THz 3.125/6.25/12.5GHz spacing";
             }
             enum "1547.19" {
               description "1547.19 nm/193.765625 THz 3.125GHz spacing";
             }
             enum "1547.17" {
               description "1547.17 nm/193.768750 THz 3.125/6.25GHz spacing";
             }
             enum "1547.14" {
               description "1547.14 nm/193.771875 THz 3.125GHz spacing";
             }
             enum "1547.12" {
               description "1547.12 nm/193.775000 THz 3.125/6.25/12.5GHz spacing";
             }
             enum "1547.09" {
               description "1547.09 nm/193.778125 THz 3.125GHz spacing";
             }
             enum "1547.07" {
               description "1547.07 nm/193.781250 THz 3.125/6.25GHz spacing";
             }
             enum "1547.04" {
               description "1547.04 nm/193.784375 THz 3.125GHz spacing";
             }
             enum "1547.02" {
               description "1547.02 nm/193.787500 THz 3.125/6.25/12.5GHz spacing";
             }
             enum "1546.99" {
               description "1546.99 nm/193.790625 THz 3.125GHz spacing";
             }
             enum "1546.97" {
               description "1546.97 nm/193.793750 THz 3.125/6.25GHz spacing";
             }
             enum "1546.94" {
               description "1546.94 nm/193.796875 THz 3.125GHz spacing";
             }
             enum "1546.92" {
               description "1546.92 nm/193.800000 THz 3.125/6.25/12.5/50/75/100GHz spacing";
             }
             enum "1546.89" {
               description "1546.89 nm/193.803125 THz 3.125GHz spacing";
             }
             enum "1546.87" {
               description "1546.87 nm/193.806250 THz 3.125/6.25GHz spacing";
             }
             enum "1546.84" {
               description "1546.84 nm/193.809375 THz 3.125GHz spacing";
             }
             enum "1546.82" {
               description "1546.82 nm/193.812500 THz 3.125/6.25/12.5GHz spacing";
             }
             enum "1546.79" {
               description "1546.79 nm/193.815625 THz 3.125GHz spacing";
             }
             enum "1546.77" {
               description "1546.77 nm/193.818750 THz 3.125/6.25GHz spacing";
             }
             enum "1546.74" {
               description "1546.74 nm/193.821875 THz 3.125GHz spacing";
             }
             enum "1546.72" {
               description "1546.72 nm/193.825000 THz 3.125/6.25/12.5GHz spacing";
             }
             enum "1546.69" {
               description "1546.69 nm/193.828125 THz 3.125GHz spacing";
             }
             enum "1546.67" {
               description "1546.67 nm/193.831250 THz 3.125/6.25GHz spacing";
             }
             enum "1546.64" {
               description "1546.64 nm/193.834375 THz 3.125GHz spacing";
             }
             enum "1546.62" {
               description "1546.62 nm/193.837500 THz 3.125/6.25/12.5GHz spacing";
             }
             enum "1546.59" {
               description "1546.59 nm/193.840625 THz 3.125GHz spacing";
             }
             enum "1546.57" {
               description "1546.57 nm/193.843750 THz 3.125/6.25GHz spacing";
             }
             enum "1546.54" {
               description "1546.54 nm/193.846875 THz 3.125GHz spacing";
             }
             enum "1546.52" {
               description "1546.52 nm/193.850000 THz 3.125/6.25/12.5/50GHz spacing";
             }
             enum "1546.49" {
               description "1546.49 nm/193.853125 THz 3.125GHz spacing";
             }
             enum "1546.47" {
               description "1546.47 nm/193.856250 THz 3.125/6.25GHz spacing";
             }
             enum "1546.44" {
               description "1546.44 nm/193.859375 THz 3.125GHz spacing";
             }
             enum "1546.42" {
               description "1546.42 nm/193.862500 THz 3.125/6.25/12.5GHz spacing";
             }
             enum "1546.39" {
               description "1546.39 nm/193.865625 THz 3.125GHz spacing";
             }
             enum "1546.37" {
               description "1546.37 nm/193.868750 THz 3.125/6.25GHz spacing";
             }
             enum "1546.34" {
               description "1546.34 nm/193.871875 THz 3.125GHz spacing";
             }
             enum "1546.32" {
               description "1546.32 nm/193.875000 THz 3.125/6.25/12.5/75GHz spacing";
             }
             enum "1546.29" {
               description "1546.29 nm/193.878125 THz 3.125GHz spacing";
             }
             enum "1546.27" {
               description "1546.27 nm/193.881250 THz 3.125/6.25GHz spacing";
             }
             enum "1546.24" {
               description "1546.24 nm/193.884375 THz 3.125GHz spacing";
             }
             enum "1546.22" {
               description "1546.22 nm/193.887500 THz 3.125/6.25/12.5GHz spacing";
             }
             enum "1546.19" {
               description "1546.19 nm/193.890625 THz 3.125GHz spacing";
             }
             enum "1546.17" {
               description "1546.17 nm/193.893750 THz 3.125/6.25GHz spacing";
             }
             enum "1546.14" {
               description "1546.14 nm/193.896875 THz 3.125GHz spacing";
             }
             enum "1546.12" {
               description "1546.12 nm/193.900000 THz 3.125/6.25/12.5/100GHz spacing";
             }
             enum "1546.09" {
               description "1546.09 nm/193.903125 THz 3.125GHz spacing";
             }
             enum "1546.07" {
               description "1546.07 nm/193.906250 THz 3.125/6.25GHz spacing";
             }
             enum "1546.04" {
               description "1546.04 nm/193.909375 THz 3.125GHz spacing";
             }
             enum "1546.02" {
               description "1546.02 nm/193.912500 THz 3.125/6.25/12.5GHz spacing";
             }
             enum "1545.99" {
               description "1545.99 nm/193.915625 THz 3.125GHz spacing";
             }
             enum "1545.97" {
               description "1545.97 nm/193.918750 THz 3.125/6.25GHz spacing";
             }
             enum "1545.94" {
               description "1545.94 nm/193.921875 THz 3.125GHz spacing";
             }
             enum "1545.92" {
               description "1545.92 nm/193.925000 THz 3.125/6.25/12.5GHz spacing";
             }
             enum "1545.89" {
               description "1545.89 nm/193.928125 THz 3.125GHz spacing";
             }
             enum "1545.87" {
               description "1545.87 nm/193.931250 THz 3.125/6.25GHz spacing";
             }
             enum "1545.84" {
               description "1545.84 nm/193.934375 THz 3.125GHz spacing";
             }
             enum "1545.82" {
               description "1545.82 nm/193.937500 THz 3.125/6.25/12.5GHz spacing";
             }
             enum "1545.80" {
               description "1545.80 nm/193.940625 THz 3.125GHz spacing";
             }
             enum "1545.77" {
               description "1545.77 nm/193.943750 THz 3.125/6.25GHz spacing";
             }
             enum "1545.75" {
               description "1545.75 nm/193.946875 THz 3.125GHz spacing";
             }
             enum "1545.72" {
               description "1545.72 nm/193.950000 THz 3.125/6.25/12.5/50/75GHz spacing";
             }
             enum "1545.70" {
               description "1545.70 nm/193.953125 THz 3.125GHz spacing";
             }
             enum "1545.67" {
               description "1545.67 nm/193.956250 THz 3.125/6.25GHz spacing";
             }
             enum "1545.65" {
               description "1545.65 nm/193.959375 THz 3.125GHz spacing";
             }
             enum "1545.62" {
               description "1545.62 nm/193.962500 THz 3.125/6.25/12.5GHz spacing";
             }
             enum "1545.60" {
               description "1545.60 nm/193.965625 THz 3.125GHz spacing";
             }
             enum "1545.57" {
               description "1545.57 nm/193.968750 THz 3.125/6.25GHz spacing";
             }
             enum "1545.55" {
               description "1545.55 nm/193.971875 THz 3.125GHz spacing";
             }
             enum "1545.52" {
               description "1545.52 nm/193.975000 THz 3.125/6.25/12.5GHz spacing";
             }
             enum "1545.50" {
               description "1545.50 nm/193.978125 THz 3.125GHz spacing";
             }
             enum "1545.47" {
               description "1545.47 nm/193.981250 THz 3.125/6.25GHz spacing";
             }
             enum "1545.45" {
               description "1545.45 nm/193.984375 THz 3.125GHz spacing";
             }
             enum "1545.42" {
               description "1545.42 nm/193.987500 THz 3.125/6.25/12.5GHz spacing";
             }
             enum "1545.40" {
               description "1545.40 nm/193.990625 THz 3.125GHz spacing";
             }
             enum "1545.37" {
               description "1545.37 nm/193.993750 THz 3.125/6.25GHz spacing";
             }
             enum "1545.35" {
               description "1545.35 nm/193.996875 THz 3.125GHz spacing";
             }
             enum "1545.32" {
               description "1545.32 nm/194.000000 THz 3.125/6.25/12.5/100GHz spacing";
             }
             enum "1545.30" {
               description "1545.30 nm/194.003125 THz 3.125GHz spacing";
             }
             enum "1545.27" {
               description "1545.27 nm/194.006250 THz 3.125/6.25GHz spacing";
             }
             enum "1545.25" {
               description "1545.25 nm/194.009375 THz 3.125GHz spacing";
             }
             enum "1545.22" {
               description "1545.22 nm/194.012500 THz 3.125/6.25/12.5GHz spacing";
             }
             enum "1545.20" {
               description "1545.20 nm/194.015625 THz 3.125GHz spacing";
             }
             enum "1545.17" {
               description "1545.17 nm/194.018750 THz 3.125/6.25GHz spacing";
             }
             enum "1545.15" {
               description "1545.15 nm/194.021875 THz 3.125GHz spacing";
             }
             enum "1545.12" {
               description "1545.12 nm/194.025000 THz 3.125/6.25/12.5/75GHz spacing";
             }
             enum "1545.10" {
               description "1545.10 nm/194.028125 THz 3.125GHz spacing";
             }
             enum "1545.07" {
               description "1545.07 nm/194.031250 THz 3.125/6.25GHz spacing";
             }
             enum "1545.05" {
               description "1545.05 nm/194.034375 THz 3.125GHz spacing";
             }
             enum "1545.02" {
               description "1545.02 nm/194.037500 THz 3.125/6.25/12.5GHz spacing";
             }
             enum "1545.00" {
               description "1545.00 nm/194.040625 THz 3.125GHz spacing";
             }
             enum "1544.97" {
               description "1544.97 nm/194.043750 THz 3.125/6.25GHz spacing";
             }
             enum "1544.95" {
               description "1544.95 nm/194.046875 THz 3.125GHz spacing";
             }
             enum "1544.92" {
               description "1544.92 nm/194.050000 THz 3.125/6.25/12.5/50GHz spacing";
             }
             enum "1544.90" {
               description "1544.90 nm/194.053125 THz 3.125GHz spacing";
             }
             enum "1544.87" {
               description "1544.87 nm/194.056250 THz 3.125/6.25GHz spacing";
             }
             enum "1544.85" {
               description "1544.85 nm/194.059375 THz 3.125GHz spacing";
             }
             enum "1544.82" {
               description "1544.82 nm/194.062500 THz 3.125/6.25/12.5GHz spacing";
             }
             enum "1544.80" {
               description "1544.80 nm/194.065625 THz 3.125GHz spacing";
             }
             enum "1544.77" {
               description "1544.77 nm/194.068750 THz 3.125/6.25GHz spacing";
             }
             enum "1544.75" {
               description "1544.75 nm/194.071875 THz 3.125GHz spacing";
             }
             enum "1544.72" {
               description "1544.72 nm/194.075000 THz 3.125/6.25/12.5GHz spacing";
             }
             enum "1544.70" {
               description "1544.70 nm/194.078125 THz 3.125GHz spacing";
             }
             enum "1544.68" {
               description "1544.68 nm/194.081250 THz 3.125/6.25GHz spacing";
             }
             enum "1544.65" {
               description "1544.65 nm/194.084375 THz 3.125GHz spacing";
             }
             enum "1544.63" {
               description "1544.63 nm/194.087500 THz 3.125/6.25/12.5GHz spacing";
             }
             enum "1544.60" {
               description "1544.60 nm/194.090625 THz 3.125GHz spacing";
             }
             enum "1544.58" {
               description "1544.58 nm/194.093750 THz 3.125/6.25GHz spacing";
             }
             enum "1544.55" {
               description "1544.55 nm/194.096875 THz 3.125GHz spacing";
             }
             enum "1544.53" {
               description "1544.53 nm/194.100000 THz 3.125/6.25/12.5/50/75/100GHz spacing";
             }
             enum "1544.50" {
               description "1544.50 nm/194.103125 THz 3.125GHz spacing";
             }
             enum "1544.48" {
               description "1544.48 nm/194.106250 THz 3.125/6.25GHz spacing";
             }
             enum "1544.45" {
               description "1544.45 nm/194.109375 THz 3.125GHz spacing";
             }
             enum "1544.43" {
               description "1544.43 nm/194.112500 THz 3.125/6.25/12.5GHz spacing";
             }
             enum "1544.40" {
               description "1544.40 nm/194.115625 THz 3.125GHz spacing";
             }
             enum "1544.38" {
               description "1544.38 nm/194.118750 THz 3.125/6.25GHz spacing";
             }
             enum "1544.35" {
               description "1544.35 nm/194.121875 THz 3.125GHz spacing";
             }
             enum "1544.33" {
               description "1544.33 nm/194.125000 THz 3.125/6.25/12.5GHz spacing";
             }
             enum "1544.30" {
               description "1544.30 nm/194.128125 THz 3.125GHz spacing";
             }
             enum "1544.28" {
               description "1544.28 nm/194.131250 THz 3.125/6.25GHz spacing";
             }
             enum "1544.25" {
               description "1544.25 nm/194.134375 THz 3.125GHz spacing";
             }
             enum "1544.23" {
               description "1544.23 nm/194.137500 THz 3.125/6.25/12.5GHz spacing";
             }
             enum "1544.20" {
               description "1544.20 nm/194.140625 THz 3.125GHz spacing";
             }
             enum "1544.18" {
               description "1544.18 nm/194.143750 THz 3.125/6.25GHz spacing";
             }
             enum "1544.15" {
               description "1544.15 nm/194.146875 THz 3.125GHz spacing";
             }
             enum "1544.13" {
               description "1544.13 nm/194.150000 THz 3.125/6.25/12.5/50GHz spacing";
             }
             enum "1544.10" {
               description "1544.10 nm/194.153125 THz 3.125GHz spacing";
             }
             enum "1544.08" {
               description "1544.08 nm/194.156250 THz 3.125/6.25GHz spacing";
             }
             enum "1544.05" {
               description "1544.05 nm/194.159375 THz 3.125GHz spacing";
             }
             enum "1544.03" {
               description "1544.03 nm/194.162500 THz 3.125/6.25/12.5GHz spacing";
             }
             enum "1544.00" {
               description "1544.00 nm/194.165625 THz 3.125GHz spacing";
             }
             enum "1543.98" {
               description "1543.98 nm/194.168750 THz 3.125/6.25GHz spacing";
             }
             enum "1543.95" {
               description "1543.95 nm/194.171875 THz 3.125GHz spacing";
             }
             enum "1543.93" {
               description "1543.93 nm/194.175000 THz 3.125/6.25/12.5/75GHz spacing";
             }
             enum "1543.90" {
               description "1543.90 nm/194.178125 THz 3.125GHz spacing";
             }
             enum "1543.88" {
               description "1543.88 nm/194.181250 THz 3.125/6.25GHz spacing";
             }
             enum "1543.85" {
               description "1543.85 nm/194.184375 THz 3.125GHz spacing";
             }
             enum "1543.83" {
               description "1543.83 nm/194.187500 THz 3.125/6.25/12.5GHz spacing";
             }
             enum "1543.81" {
               description "1543.81 nm/194.190625 THz 3.125GHz spacing";
             }
             enum "1543.78" {
               description "1543.78 nm/194.193750 THz 3.125/6.25GHz spacing";
             }
             enum "1543.76" {
               description "1543.76 nm/194.196875 THz 3.125GHz spacing";
             }
             enum "1543.73" {
               description "1543.73 nm/194.200000 THz 3.125/6.25/12.5/100GHz spacing";
             }
             enum "1543.71" {
               description "1543.71 nm/194.203125 THz 3.125GHz spacing";
             }
             enum "1543.68" {
               description "1543.68 nm/194.206250 THz 3.125/6.25GHz spacing";
             }
             enum "1543.66" {
               description "1543.66 nm/194.209375 THz 3.125GHz spacing";
             }
             enum "1543.63" {
               description "1543.63 nm/194.212500 THz 3.125/6.25/12.5GHz spacing";
             }
             enum "1543.61" {
               description "1543.61 nm/194.215625 THz 3.125GHz spacing";
             }
             enum "1543.58" {
               description "1543.58 nm/194.218750 THz 3.125/6.25GHz spacing";
             }
             enum "1543.56" {
               description "1543.56 nm/194.221875 THz 3.125GHz spacing";
             }
             enum "1543.53" {
               description "1543.53 nm/194.225000 THz 3.125/6.25/12.5GHz spacing";
             }
             enum "1543.51" {
               description "1543.51 nm/194.228125 THz 3.125GHz spacing";
             }
             enum "1543.48" {
               description "1543.48 nm/194.231250 THz 3.125/6.25GHz spacing";
             }
             enum "1543.46" {
               description "1543.46 nm/194.234375 THz 3.125GHz spacing";
             }
             enum "1543.43" {
               description "1543.43 nm/194.237500 THz 3.125/6.25/12.5GHz spacing";
             }
             enum "1543.41" {
               description "1543.41 nm/194.240625 THz 3.125GHz spacing";
             }
             enum "1543.38" {
               description "1543.38 nm/194.243750 THz 3.125/6.25GHz spacing";
             }
             enum "1543.36" {
               description "1543.36 nm/194.246875 THz 3.125GHz spacing";
             }
             enum "1543.33" {
               description "1543.33 nm/194.250000 THz 3.125/6.25/12.5/50/75GHz spacing";
             }
             enum "1543.31" {
               description "1543.31 nm/194.253125 THz 3.125GHz spacing";
             }
             enum "1543.28" {
               description "1543.28 nm/194.256250 THz 3.125/6.25GHz spacing";
             }
             enum "1543.26" {
               description "1543.26 nm/194.259375 THz 3.125GHz spacing";
             }
             enum "1543.23" {
               description "1543.23 nm/194.262500 THz 3.125/6.25/12.5GHz spacing";
             }
             enum "1543.21" {
               description "1543.21 nm/194.265625 THz 3.125GHz spacing";
             }
             enum "1543.18" {
               description "1543.18 nm/194.268750 THz 3.125/6.25GHz spacing";
             }
             enum "1543.16" {
               description "1543.16 nm/194.271875 THz 3.125GHz spacing";
             }
             enum "1543.13" {
               description "1543.13 nm/194.275000 THz 3.125/6.25/12.5GHz spacing";
             }
             enum "1543.11" {
               description "1543.11 nm/194.278125 THz 3.125GHz spacing";
             }
             enum "1543.08" {
               description "1543.08 nm/194.281250 THz 3.125/6.25GHz spacing";
             }
             enum "1543.06" {
               description "1543.06 nm/194.284375 THz 3.125GHz spacing";
             }
             enum "1543.04" {
               description "1543.04 nm/194.287500 THz 3.125/6.25/12.5GHz spacing";
             }
             enum "1543.01" {
               description "1543.01 nm/194.290625 THz 3.125GHz spacing";
             }
             enum "1542.99" {
               description "1542.99 nm/194.293750 THz 3.125/6.25GHz spacing";
             }
             enum "1542.96" {
               description "1542.96 nm/194.296875 THz 3.125GHz spacing";
             }
             enum "1542.94" {
               description "1542.94 nm/194.300000 THz 3.125/6.25/12.5/100GHz spacing";
             }
             enum "1542.91" {
               description "1542.91 nm/194.303125 THz 3.125GHz spacing";
             }
             enum "1542.89" {
               description "1542.89 nm/194.306250 THz 3.125/6.25GHz spacing";
             }
             enum "1542.86" {
               description "1542.86 nm/194.309375 THz 3.125GHz spacing";
             }
             enum "1542.84" {
               description "1542.84 nm/194.312500 THz 3.125/6.25/12.5GHz spacing";
             }
             enum "1542.81" {
               description "1542.81 nm/194.315625 THz 3.125GHz spacing";
             }
             enum "1542.79" {
               description "1542.79 nm/194.318750 THz 3.125/6.25GHz spacing";
             }
             enum "1542.76" {
               description "1542.76 nm/194.321875 THz 3.125GHz spacing";
             }
             enum "1542.74" {
               description "1542.74 nm/194.325000 THz 3.125/6.25/12.5/75GHz spacing";
             }
             enum "1542.71" {
               description "1542.71 nm/194.328125 THz 3.125GHz spacing";
             }
             enum "1542.69" {
               description "1542.69 nm/194.331250 THz 3.125/6.25GHz spacing";
             }
             enum "1542.66" {
               description "1542.66 nm/194.334375 THz 3.125GHz spacing";
             }
             enum "1542.64" {
               description "1542.64 nm/194.337500 THz 3.125/6.25/12.5GHz spacing";
             }
             enum "1542.61" {
               description "1542.61 nm/194.340625 THz 3.125GHz spacing";
             }
             enum "1542.59" {
               description "1542.59 nm/194.343750 THz 3.125/6.25GHz spacing";
             }
             enum "1542.56" {
               description "1542.56 nm/194.346875 THz 3.125GHz spacing";
             }
             enum "1542.54" {
               description "1542.54 nm/194.350000 THz 3.125/6.25/12.5/50GHz spacing";
             }
             enum "1542.51" {
               description "1542.51 nm/194.353125 THz 3.125GHz spacing";
             }
             enum "1542.49" {
               description "1542.49 nm/194.356250 THz 3.125/6.25GHz spacing";
             }
             enum "1542.46" {
               description "1542.46 nm/194.359375 THz 3.125GHz spacing";
             }
             enum "1542.44" {
               description "1542.44 nm/194.362500 THz 3.125/6.25/12.5GHz spacing";
             }
             enum "1542.42" {
               description "1542.42 nm/194.365625 THz 3.125GHz spacing";
             }
             enum "1542.39" {
               description "1542.39 nm/194.368750 THz 3.125/6.25GHz spacing";
             }
             enum "1542.37" {
               description "1542.37 nm/194.371875 THz 3.125GHz spacing";
             }
             enum "1542.34" {
               description "1542.34 nm/194.375000 THz 3.125/6.25/12.5GHz spacing";
             }
             enum "1542.32" {
               description "1542.32 nm/194.378125 THz 3.125GHz spacing";
             }
             enum "1542.29" {
               description "1542.29 nm/194.381250 THz 3.125/6.25GHz spacing";
             }
             enum "1542.27" {
               description "1542.27 nm/194.384375 THz 3.125GHz spacing";
             }
             enum "1542.24" {
               description "1542.24 nm/194.387500 THz 3.125/6.25/12.5GHz spacing";
             }
             enum "1542.22" {
               description "1542.22 nm/194.390625 THz 3.125GHz spacing";
             }
             enum "1542.19" {
               description "1542.19 nm/194.393750 THz 3.125/6.25GHz spacing";
             }
             enum "1542.17" {
               description "1542.17 nm/194.396875 THz 3.125GHz spacing";
             }
             enum "1542.14" {
               description "1542.14 nm/194.400000 THz 3.125/6.25/12.5/50/75/100GHz spacing";
             }
             enum "1542.12" {
               description "1542.12 nm/194.403125 THz 3.125GHz spacing";
             }
             enum "1542.09" {
               description "1542.09 nm/194.406250 THz 3.125/6.25GHz spacing";
             }
             enum "1542.07" {
               description "1542.07 nm/194.409375 THz 3.125GHz spacing";
             }
             enum "1542.04" {
               description "1542.04 nm/194.412500 THz 3.125/6.25/12.5GHz spacing";
             }
             enum "1542.02" {
               description "1542.02 nm/194.415625 THz 3.125GHz spacing";
             }
             enum "1541.99" {
               description "1541.99 nm/194.418750 THz 3.125/6.25GHz spacing";
             }
             enum "1541.97" {
               description "1541.97 nm/194.421875 THz 3.125GHz spacing";
             }
             enum "1541.94" {
               description "1541.94 nm/194.425000 THz 3.125/6.25/12.5GHz spacing";
             }
             enum "1541.92" {
               description "1541.92 nm/194.428125 THz 3.125GHz spacing";
             }
             enum "1541.89" {
               description "1541.89 nm/194.431250 THz 3.125/6.25GHz spacing";
             }
             enum "1541.87" {
               description "1541.87 nm/194.434375 THz 3.125GHz spacing";
             }
             enum "1541.84" {
               description "1541.84 nm/194.437500 THz 3.125/6.25/12.5GHz spacing";
             }
             enum "1541.82" {
               description "1541.82 nm/194.440625 THz 3.125GHz spacing";
             }
             enum "1541.80" {
               description "1541.80 nm/194.443750 THz 3.125/6.25GHz spacing";
             }
             enum "1541.77" {
               description "1541.77 nm/194.446875 THz 3.125GHz spacing";
             }
             enum "1541.75" {
               description "1541.75 nm/194.450000 THz 3.125/6.25/12.5/50GHz spacing";
             }
             enum "1541.72" {
               description "1541.72 nm/194.453125 THz 3.125GHz spacing";
             }
             enum "1541.70" {
               description "1541.70 nm/194.456250 THz 3.125/6.25GHz spacing";
             }
             enum "1541.67" {
               description "1541.67 nm/194.459375 THz 3.125GHz spacing";
             }
             enum "1541.65" {
               description "1541.65 nm/194.462500 THz 3.125/6.25/12.5GHz spacing";
             }
             enum "1541.62" {
               description "1541.62 nm/194.465625 THz 3.125GHz spacing";
             }
             enum "1541.60" {
               description "1541.60 nm/194.468750 THz 3.125/6.25GHz spacing";
             }
             enum "1541.57" {
               description "1541.57 nm/194.471875 THz 3.125GHz spacing";
             }
             enum "1541.55" {
               description "1541.55 nm/194.475000 THz 3.125/6.25/12.5/75GHz spacing";
             }
             enum "1541.52" {
               description "1541.52 nm/194.478125 THz 3.125GHz spacing";
             }
             enum "1541.50" {
               description "1541.50 nm/194.481250 THz 3.125/6.25GHz spacing";
             }
             enum "1541.47" {
               description "1541.47 nm/194.484375 THz 3.125GHz spacing";
             }
             enum "1541.45" {
               description "1541.45 nm/194.487500 THz 3.125/6.25/12.5GHz spacing";
             }
             enum "1541.42" {
               description "1541.42 nm/194.490625 THz 3.125GHz spacing";
             }
             enum "1541.40" {
               description "1541.40 nm/194.493750 THz 3.125/6.25GHz spacing";
             }
             enum "1541.37" {
               description "1541.37 nm/194.496875 THz 3.125GHz spacing";
             }
             enum "1541.35" {
               description "1541.35 nm/194.500000 THz 3.125/6.25/12.5/100GHz spacing";
             }
             enum "1541.32" {
               description "1541.32 nm/194.503125 THz 3.125GHz spacing";
             }
             enum "1541.30" {
               description "1541.30 nm/194.506250 THz 3.125/6.25GHz spacing";
             }
             enum "1541.28" {
               description "1541.28 nm/194.509375 THz 3.125GHz spacing";
             }
             enum "1541.25" {
               description "1541.25 nm/194.512500 THz 3.125/6.25/12.5GHz spacing";
             }
             enum "1541.23" {
               description "1541.23 nm/194.515625 THz 3.125GHz spacing";
             }
             enum "1541.20" {
               description "1541.20 nm/194.518750 THz 3.125/6.25GHz spacing";
             }
             enum "1541.18" {
               description "1541.18 nm/194.521875 THz 3.125GHz spacing";
             }
             enum "1541.15" {
               description "1541.15 nm/194.525000 THz 3.125/6.25/12.5GHz spacing";
             }
             enum "1541.13" {
               description "1541.13 nm/194.528125 THz 3.125GHz spacing";
             }
             enum "1541.10" {
               description "1541.10 nm/194.531250 THz 3.125/6.25GHz spacing";
             }
             enum "1541.08" {
               description "1541.08 nm/194.534375 THz 3.125GHz spacing";
             }
             enum "1541.05" {
               description "1541.05 nm/194.537500 THz 3.125/6.25/12.5GHz spacing";
             }
             enum "1541.03" {
               description "1541.03 nm/194.540625 THz 3.125GHz spacing";
             }
             enum "1541.00" {
               description "1541.00 nm/194.543750 THz 3.125/6.25GHz spacing";
             }
             enum "1540.98" {
               description "1540.98 nm/194.546875 THz 3.125GHz spacing";
             }
             enum "1540.95" {
               description "1540.95 nm/194.550000 THz 3.125/6.25/12.5/50/75GHz spacing";
             }
             enum "1540.93" {
               description "1540.93 nm/194.553125 THz 3.125GHz spacing";
             }
             enum "1540.90" {
               description "1540.90 nm/194.556250 THz 3.125/6.25GHz spacing";
             }
             enum "1540.88" {
               description "1540.88 nm/194.559375 THz 3.125GHz spacing";
             }
             enum "1540.85" {
               description "1540.85 nm/194.562500 THz 3.125/6.25/12.5GHz spacing";
             }
             enum "1540.83" {
               description "1540.83 nm/194.565625 THz 3.125GHz spacing";
             }
             enum "1540.80" {
               description "1540.80 nm/194.568750 THz 3.125/6.25GHz spacing";
             }
             enum "1540.78" {
               description "1540.78 nm/194.571875 THz 3.125GHz spacing";
             }
             enum "1540.76" {
               description "1540.76 nm/194.575000 THz 3.125/6.25/12.5GHz spacing";
             }
             enum "1540.73" {
               description "1540.73 nm/194.578125 THz 3.125GHz spacing";
             }
             enum "1540.71" {
               description "1540.71 nm/194.581250 THz 3.125/6.25GHz spacing";
             }
             enum "1540.68" {
               description "1540.68 nm/194.584375 THz 3.125GHz spacing";
             }
             enum "1540.66" {
               description "1540.66 nm/194.587500 THz 3.125/6.25/12.5GHz spacing";
             }
             enum "1540.63" {
               description "1540.63 nm/194.590625 THz 3.125GHz spacing";
             }
             enum "1540.61" {
               description "1540.61 nm/194.593750 THz 3.125/6.25GHz spacing";
             }
             enum "1540.58" {
               description "1540.58 nm/194.596875 THz 3.125GHz spacing";
             }
             enum "1540.56" {
               description "1540.56 nm/194.600000 THz 3.125/6.25/12.5/100GHz spacing";
             }
             enum "1540.53" {
               description "1540.53 nm/194.603125 THz 3.125GHz spacing";
             }
             enum "1540.51" {
               description "1540.51 nm/194.606250 THz 3.125/6.25GHz spacing";
             }
             enum "1540.48" {
               description "1540.48 nm/194.609375 THz 3.125GHz spacing";
             }
             enum "1540.46" {
               description "1540.46 nm/194.612500 THz 3.125/6.25/12.5GHz spacing";
             }
             enum "1540.43" {
               description "1540.43 nm/194.615625 THz 3.125GHz spacing";
             }
             enum "1540.41" {
               description "1540.41 nm/194.618750 THz 3.125/6.25GHz spacing";
             }
             enum "1540.38" {
               description "1540.38 nm/194.621875 THz 3.125GHz spacing";
             }
             enum "1540.36" {
               description "1540.36 nm/194.625000 THz 3.125/6.25/12.5/75GHz spacing";
             }
             enum "1540.33" {
               description "1540.33 nm/194.628125 THz 3.125GHz spacing";
             }
             enum "1540.31" {
               description "1540.31 nm/194.631250 THz 3.125/6.25GHz spacing";
             }
             enum "1540.29" {
               description "1540.29 nm/194.634375 THz 3.125GHz spacing";
             }
             enum "1540.26" {
               description "1540.26 nm/194.637500 THz 3.125/6.25/12.5GHz spacing";
             }
             enum "1540.24" {
               description "1540.24 nm/194.640625 THz 3.125GHz spacing";
             }
             enum "1540.21" {
               description "1540.21 nm/194.643750 THz 3.125/6.25GHz spacing";
             }
             enum "1540.19" {
               description "1540.19 nm/194.646875 THz 3.125GHz spacing";
             }
             enum "1540.16" {
               description "1540.16 nm/194.650000 THz 3.125/6.25/12.5/50GHz spacing";
             }
             enum "1540.14" {
               description "1540.14 nm/194.653125 THz 3.125GHz spacing";
             }
             enum "1540.11" {
               description "1540.11 nm/194.656250 THz 3.125/6.25GHz spacing";
             }
             enum "1540.09" {
               description "1540.09 nm/194.659375 THz 3.125GHz spacing";
             }
             enum "1540.06" {
               description "1540.06 nm/194.662500 THz 3.125/6.25/12.5GHz spacing";
             }
             enum "1540.04" {
               description "1540.04 nm/194.665625 THz 3.125GHz spacing";
             }
             enum "1540.01" {
               description "1540.01 nm/194.668750 THz 3.125/6.25GHz spacing";
             }
             enum "1539.99" {
               description "1539.99 nm/194.671875 THz 3.125GHz spacing";
             }
             enum "1539.96" {
               description "1539.96 nm/194.675000 THz 3.125/6.25/12.5/75GHz spacing";
             }
             enum "1539.94" {
               description "1539.94 nm/194.678125 THz 3.125GHz spacing";
             }
             enum "1539.91" {
               description "1539.91 nm/194.681250 THz 3.125/6.25GHz spacing";
             }
             enum "1539.89" {
               description "1539.89 nm/194.684375 THz 3.125GHz spacing";
             }
             enum "1539.86" {
               description "1539.86 nm/194.687500 THz 3.125/6.25/12.5GHz spacing";
             }
             enum "1539.84" {
               description "1539.84 nm/194.690625 THz 3.125GHz spacing";
             }
             enum "1539.82" {
               description "1539.82 nm/194.693750 THz 3.125/6.25GHz spacing";
             }
             enum "1539.79" {
               description "1539.79 nm/194.696875 THz 3.125GHz spacing";
             }
             enum "1539.77" {
               description "1539.77 nm/194.700000 THz 3.125/6.25/12.5/50/75/100GHz spacing";
             }
             enum "1539.74" {
               description "1539.74 nm/194.703125 THz 3.125GHz spacing";
             }
             enum "1539.72" {
               description "1539.72 nm/194.706250 THz 3.125/6.25GHz spacing";
             }
             enum "1539.69" {
               description "1539.69 nm/194.709375 THz 3.125GHz spacing";
             }
             enum "1539.67" {
               description "1539.67 nm/194.712500 THz 3.125/6.25/12.5GHz spacing";
             }
             enum "1539.64" {
               description "1539.64 nm/194.715625 THz 3.125GHz spacing";
             }
             enum "1539.62" {
               description "1539.62 nm/194.718750 THz 3.125/6.25GHz spacing";
             }
             enum "1539.59" {
               description "1539.59 nm/194.721875 THz 3.125GHz spacing";
             }
             enum "1539.57" {
               description "1539.57 nm/194.725000 THz 3.125/6.25/12.5GHz spacing";
             }
             enum "1539.54" {
               description "1539.54 nm/194.728125 THz 3.125GHz spacing";
             }
             enum "1539.52" {
               description "1539.52 nm/194.731250 THz 3.125/6.25GHz spacing";
             }
             enum "1539.49" {
               description "1539.49 nm/194.734375 THz 3.125GHz spacing";
             }
             enum "1539.47" {
               description "1539.47 nm/194.737500 THz 3.125/6.25/12.5GHz spacing";
             }
             enum "1539.44" {
               description "1539.44 nm/194.740625 THz 3.125GHz spacing";
             }
             enum "1539.42" {
               description "1539.42 nm/194.743750 THz 3.125/6.25GHz spacing";
             }
             enum "1539.40" {
               description "1539.40 nm/194.746875 THz 3.125GHz spacing";
             }
             enum "1539.37" {
               description "1539.37 nm/194.750000 THz 3.125/6.25/12.5/50GHz spacing";
             }
             enum "1539.35" {
               description "1539.35 nm/194.753125 THz 3.125GHz spacing";
             }
             enum "1539.32" {
               description "1539.32 nm/194.756250 THz 3.125/6.25GHz spacing";
             }
             enum "1539.30" {
               description "1539.30 nm/194.759375 THz 3.125GHz spacing";
             }
             enum "1539.27" {
               description "1539.27 nm/194.762500 THz 3.125/6.25/12.5GHz spacing";
             }
             enum "1539.25" {
               description "1539.25 nm/194.765625 THz 3.125GHz spacing";
             }
             enum "1539.22" {
               description "1539.22 nm/194.768750 THz 3.125/6.25GHz spacing";
             }
             enum "1539.20" {
               description "1539.20 nm/194.771875 THz 3.125GHz spacing";
             }
             enum "1539.17" {
               description "1539.17 nm/194.775000 THz 3.125/6.25/12.5/75GHz spacing";
             }
             enum "1539.15" {
               description "1539.15 nm/194.778125 THz 3.125GHz spacing";
             }
             enum "1539.12" {
               description "1539.12 nm/194.781250 THz 3.125/6.25GHz spacing";
             }
             enum "1539.10" {
               description "1539.10 nm/194.784375 THz 3.125GHz spacing";
             }
             enum "1539.07" {
               description "1539.07 nm/194.787500 THz 3.125/6.25/12.5GHz spacing";
             }
             enum "1539.05" {
               description "1539.05 nm/194.790625 THz 3.125GHz spacing";
             }
             enum "1539.03" {
               description "1539.03 nm/194.793750 THz 3.125/6.25GHz spacing";
             }
             enum "1539.00" {
               description "1539.00 nm/194.796875 THz 3.125GHz spacing";
             }
             enum "1538.98" {
               description "1538.98 nm/194.800000 THz 3.125/6.25/12.5/100GHz spacing";
             }
             enum "1538.95" {
               description "1538.95 nm/194.803125 THz 3.125GHz spacing";
             }
             enum "1538.93" {
               description "1538.93 nm/194.806250 THz 3.125/6.25GHz spacing";
             }
             enum "1538.90" {
               description "1538.90 nm/194.809375 THz 3.125GHz spacing";
             }
             enum "1538.88" {
               description "1538.88 nm/194.812500 THz 3.125/6.25/12.5GHz spacing";
             }
             enum "1538.85" {
               description "1538.85 nm/194.815625 THz 3.125GHz spacing";
             }
             enum "1538.83" {
               description "1538.83 nm/194.818750 THz 3.125/6.25GHz spacing";
             }
             enum "1538.80" {
               description "1538.80 nm/194.821875 THz 3.125GHz spacing";
             }
             enum "1538.78" {
               description "1538.78 nm/194.825000 THz 3.125/6.25/12.5GHz spacing";
             }
             enum "1538.75" {
               description "1538.75 nm/194.828125 THz 3.125GHz spacing";
             }
             enum "1538.73" {
               description "1538.73 nm/194.831250 THz 3.125/6.25GHz spacing";
             }
             enum "1538.70" {
               description "1538.70 nm/194.834375 THz 3.125GHz spacing";
             }
             enum "1538.68" {
               description "1538.68 nm/194.837500 THz 3.125/6.25/12.5GHz spacing";
             }
             enum "1538.65" {
               description "1538.65 nm/194.840625 THz 3.125GHz spacing";
             }
             enum "1538.63" {
               description "1538.63 nm/194.843750 THz 3.125/6.25GHz spacing";
             }
             enum "1538.61" {
               description "1538.61 nm/194.846875 THz 3.125GHz spacing";
             }
             enum "1538.58" {
               description "1538.58 nm/194.850000 THz 3.125/6.25/12.5/50/75GHz spacing";
             }
             enum "1538.56" {
               description "1538.56 nm/194.853125 THz 3.125GHz spacing";
             }
             enum "1538.53" {
               description "1538.53 nm/194.856250 THz 3.125/6.25GHz spacing";
             }
             enum "1538.51" {
               description "1538.51 nm/194.859375 THz 3.125GHz spacing";
             }
             enum "1538.48" {
               description "1538.48 nm/194.862500 THz 3.125/6.25/12.5GHz spacing";
             }
             enum "1538.46" {
               description "1538.46 nm/194.865625 THz 3.125GHz spacing";
             }
             enum "1538.43" {
               description "1538.43 nm/194.868750 THz 3.125/6.25GHz spacing";
             }
             enum "1538.41" {
               description "1538.41 nm/194.871875 THz 3.125GHz spacing";
             }
             enum "1538.38" {
               description "1538.38 nm/194.875000 THz 3.125/6.25/12.5GHz spacing";
             }
             enum "1538.36" {
               description "1538.36 nm/194.878125 THz 3.125GHz spacing";
             }
             enum "1538.33" {
               description "1538.33 nm/194.881250 THz 3.125/6.25GHz spacing";
             }
             enum "1538.31" {
               description "1538.31 nm/194.884375 THz 3.125GHz spacing";
             }
             enum "1538.28" {
               description "1538.28 nm/194.887500 THz 3.125/6.25/12.5GHz spacing";
             }
             enum "1538.26" {
               description "1538.26 nm/194.890625 THz 3.125GHz spacing";
             }
             enum "1538.24" {
               description "1538.24 nm/194.893750 THz 3.125/6.25GHz spacing";
             }
             enum "1538.21" {
               description "1538.21 nm/194.896875 THz 3.125GHz spacing";
             }
             enum "1538.19" {
               description "1538.19 nm/194.900000 THz 3.125/6.25/12.5/100GHz spacing";
             }
             enum "1538.16" {
               description "1538.16 nm/194.903125 THz 3.125GHz spacing";
             }
             enum "1538.14" {
               description "1538.14 nm/194.906250 THz 3.125/6.25GHz spacing";
             }
             enum "1538.11" {
               description "1538.11 nm/194.909375 THz 3.125GHz spacing";
             }
             enum "1538.09" {
               description "1538.09 nm/194.912500 THz 3.125/6.25/12.5GHz spacing";
             }
             enum "1538.06" {
               description "1538.06 nm/194.915625 THz 3.125GHz spacing";
             }
             enum "1538.04" {
               description "1538.04 nm/194.918750 THz 3.125/6.25GHz spacing";
             }
             enum "1538.01" {
               description "1538.01 nm/194.921875 THz 3.125GHz spacing";
             }
             enum "1537.99" {
               description "1537.99 nm/194.925000 THz 3.125/6.25/12.5/75GHz spacing";
             }
             enum "1537.96" {
               description "1537.96 nm/194.928125 THz 3.125GHz spacing";
             }
             enum "1537.94" {
               description "1537.94 nm/194.931250 THz 3.125/6.25GHz spacing";
             }
             enum "1537.91" {
               description "1537.91 nm/194.934375 THz 3.125GHz spacing";
             }
             enum "1537.89" {
               description "1537.89 nm/194.937500 THz 3.125/6.25/12.5GHz spacing";
             }
             enum "1537.87" {
               description "1537.87 nm/194.940625 THz 3.125GHz spacing";
             }
             enum "1537.84" {
               description "1537.84 nm/194.943750 THz 3.125/6.25GHz spacing";
             }
             enum "1537.82" {
               description "1537.82 nm/194.946875 THz 3.125GHz spacing";
             }
             enum "1537.79" {
               description "1537.79 nm/194.950000 THz 3.125/6.25/12.5/50GHz spacing";
             }
             enum "1537.77" {
               description "1537.77 nm/194.953125 THz 3.125GHz spacing";
             }
             enum "1537.74" {
               description "1537.74 nm/194.956250 THz 3.125/6.25GHz spacing";
             }
             enum "1537.72" {
               description "1537.72 nm/194.959375 THz 3.125GHz spacing";
             }
             enum "1537.69" {
               description "1537.69 nm/194.962500 THz 3.125/6.25/12.5GHz spacing";
             }
             enum "1537.67" {
               description "1537.67 nm/194.965625 THz 3.125GHz spacing";
             }
             enum "1537.64" {
               description "1537.64 nm/194.968750 THz 3.125/6.25GHz spacing";
             }
             enum "1537.62" {
               description "1537.62 nm/194.971875 THz 3.125GHz spacing";
             }
             enum "1537.59" {
               description "1537.59 nm/194.975000 THz 3.125/6.25/12.5GHz spacing";
             }
             enum "1537.57" {
               description "1537.57 nm/194.978125 THz 3.125GHz spacing";
             }
             enum "1537.55" {
               description "1537.55 nm/194.981250 THz 3.125/6.25GHz spacing";
             }
             enum "1537.52" {
               description "1537.52 nm/194.984375 THz 3.125GHz spacing";
             }
             enum "1537.50" {
               description "1537.50 nm/194.987500 THz 3.125/6.25/12.5GHz spacing";
             }
             enum "1537.47" {
               description "1537.47 nm/194.990625 THz 3.125GHz spacing";
             }
             enum "1537.45" {
               description "1537.45 nm/194.993750 THz 3.125/6.25GHz spacing";
             }
             enum "1537.42" {
               description "1537.42 nm/194.996875 THz 3.125GHz spacing";
             }
             enum "1537.40" {
               description "1537.40 nm/195.000000 THz 3.125/6.25/12.5/50/75/100GHz spacing";
             }
             enum "1537.37" {
               description "1537.37 nm/195.003125 THz 3.125GHz spacing";
             }
             enum "1537.35" {
               description "1537.35 nm/195.006250 THz 3.125/6.25GHz spacing";
             }
             enum "1537.32" {
               description "1537.32 nm/195.009375 THz 3.125GHz spacing";
             }
             enum "1537.30" {
               description "1537.30 nm/195.012500 THz 3.125/6.25/12.5GHz spacing";
             }
             enum "1537.27" {
               description "1537.27 nm/195.015625 THz 3.125GHz spacing";
             }
             enum "1537.25" {
               description "1537.25 nm/195.018750 THz 3.125/6.25GHz spacing";
             }
             enum "1537.22" {
               description "1537.22 nm/195.021875 THz 3.125GHz spacing";
             }
             enum "1537.20" {
               description "1537.20 nm/195.025000 THz 3.125/6.25/12.5GHz spacing";
             }
             enum "1537.18" {
               description "1537.18 nm/195.028125 THz 3.125GHz spacing";
             }
             enum "1537.15" {
               description "1537.15 nm/195.031250 THz 3.125/6.25GHz spacing";
             }
             enum "1537.13" {
               description "1537.13 nm/195.034375 THz 3.125GHz spacing";
             }
             enum "1537.10" {
               description "1537.10 nm/195.037500 THz 3.125/6.25/12.5GHz spacing";
             }
             enum "1537.08" {
               description "1537.08 nm/195.040625 THz 3.125GHz spacing";
             }
             enum "1537.05" {
               description "1537.05 nm/195.043750 THz 3.125/6.25GHz spacing";
             }
             enum "1537.03" {
               description "1537.03 nm/195.046875 THz 3.125GHz spacing";
             }
             enum "1537.00" {
               description "1537.00 nm/195.050000 THz 3.125/6.25/12.5/50GHz spacing";
             }
             enum "1536.98" {
               description "1536.98 nm/195.053125 THz 3.125GHz spacing";
             }
             enum "1536.95" {
               description "1536.95 nm/195.056250 THz 3.125/6.25GHz spacing";
             }
             enum "1536.93" {
               description "1536.93 nm/195.059375 THz 3.125GHz spacing";
             }
             enum "1536.90" {
               description "1536.90 nm/195.062500 THz 3.125/6.25/12.5GHz spacing";
             }
             enum "1536.88" {
               description "1536.88 nm/195.065625 THz 3.125GHz spacing";
             }
             enum "1536.86" {
               description "1536.86 nm/195.068750 THz 3.125/6.25GHz spacing";
             }
             enum "1536.83" {
               description "1536.83 nm/195.071875 THz 3.125GHz spacing";
             }
             enum "1536.81" {
               description "1536.81 nm/195.075000 THz 3.125/6.25/12.5/75GHz spacing";
             }
             enum "1536.78" {
               description "1536.78 nm/195.078125 THz 3.125GHz spacing";
             }
             enum "1536.76" {
               description "1536.76 nm/195.081250 THz 3.125/6.25GHz spacing";
             }
             enum "1536.73" {
               description "1536.73 nm/195.084375 THz 3.125GHz spacing";
             }
             enum "1536.71" {
               description "1536.71 nm/195.087500 THz 3.125/6.25/12.5GHz spacing";
             }
             enum "1536.68" {
               description "1536.68 nm/195.090625 THz 3.125GHz spacing";
             }
             enum "1536.66" {
               description "1536.66 nm/195.093750 THz 3.125/6.25GHz spacing";
             }
             enum "1536.63" {
               description "1536.63 nm/195.096875 THz 3.125GHz spacing";
             }
             enum "1536.61" {
               description "1536.61 nm/195.100000 THz 3.125/6.25/12.5/100GHz spacing";
             }
             enum "1536.58" {
               description "1536.58 nm/195.103125 THz 3.125GHz spacing";
             }
             enum "1536.56" {
               description "1536.56 nm/195.106250 THz 3.125/6.25GHz spacing";
             }
             enum "1536.54" {
               description "1536.54 nm/195.109375 THz 3.125GHz spacing";
             }
             enum "1536.51" {
               description "1536.51 nm/195.112500 THz 3.125/6.25/12.5GHz spacing";
             }
             enum "1536.49" {
               description "1536.49 nm/195.115625 THz 3.125GHz spacing";
             }
             enum "1536.46" {
               description "1536.46 nm/195.118750 THz 3.125/6.25GHz spacing";
             }
             enum "1536.44" {
               description "1536.44 nm/195.121875 THz 3.125GHz spacing";
             }
             enum "1536.41" {
               description "1536.41 nm/195.125000 THz 3.125/6.25/12.5GHz spacing";
             }
             enum "1536.39" {
               description "1536.39 nm/195.128125 THz 3.125GHz spacing";
             }
             enum "1536.36" {
               description "1536.36 nm/195.131250 THz 3.125/6.25GHz spacing";
             }
             enum "1536.34" {
               description "1536.34 nm/195.134375 THz 3.125GHz spacing";
             }
             enum "1536.31" {
               description "1536.31 nm/195.137500 THz 3.125/6.25/12.5GHz spacing";
             }
             enum "1536.29" {
               description "1536.29 nm/195.140625 THz 3.125GHz spacing";
             }
             enum "1536.26" {
               description "1536.26 nm/195.143750 THz 3.125/6.25GHz spacing";
             }
             enum "1536.24" {
               description "1536.24 nm/195.146875 THz 3.125GHz spacing";
             }
             enum "1536.22" {
               description "1536.22 nm/195.150000 THz 3.125/6.25/12.5/50/75GHz spacing";
             }
             enum "1536.19" {
               description "1536.19 nm/195.153125 THz 3.125GHz spacing";
             }
             enum "1536.17" {
               description "1536.17 nm/195.156250 THz 3.125/6.25GHz spacing";
             }
             enum "1536.14" {
               description "1536.14 nm/195.159375 THz 3.125GHz spacing";
             }
             enum "1536.12" {
               description "1536.12 nm/195.162500 THz 3.125/6.25/12.5GHz spacing";
             }
             enum "1536.09" {
               description "1536.09 nm/195.165625 THz 3.125GHz spacing";
             }
             enum "1536.07" {
               description "1536.07 nm/195.168750 THz 3.125/6.25GHz spacing";
             }
             enum "1536.04" {
               description "1536.04 nm/195.171875 THz 3.125GHz spacing";
             }
             enum "1536.02" {
               description "1536.02 nm/195.175000 THz 3.125/6.25/12.5GHz spacing";
             }
             enum "1535.99" {
               description "1535.99 nm/195.178125 THz 3.125GHz spacing";
             }
             enum "1535.97" {
               description "1535.97 nm/195.181250 THz 3.125/6.25GHz spacing";
             }
             enum "1535.94" {
               description "1535.94 nm/195.184375 THz 3.125GHz spacing";
             }
             enum "1535.92" {
               description "1535.92 nm/195.187500 THz 3.125/6.25/12.5GHz spacing";
             }
             enum "1535.90" {
               description "1535.90 nm/195.190625 THz 3.125GHz spacing";
             }
             enum "1535.87" {
               description "1535.87 nm/195.193750 THz 3.125/6.25GHz spacing";
             }
             enum "1535.85" {
               description "1535.85 nm/195.196875 THz 3.125GHz spacing";
             }
             enum "1535.82" {
               description "1535.82 nm/195.200000 THz 3.125/6.25/12.5/100GHz spacing";
             }
             enum "1535.80" {
               description "1535.80 nm/195.203125 THz 3.125GHz spacing";
             }
             enum "1535.77" {
               description "1535.77 nm/195.206250 THz 3.125/6.25GHz spacing";
             }
             enum "1535.75" {
               description "1535.75 nm/195.209375 THz 3.125GHz spacing";
             }
             enum "1535.72" {
               description "1535.72 nm/195.212500 THz 3.125/6.25/12.5GHz spacing";
             }
             enum "1535.70" {
               description "1535.70 nm/195.215625 THz 3.125GHz spacing";
             }
             enum "1535.67" {
               description "1535.67 nm/195.218750 THz 3.125/6.25GHz spacing";
             }
             enum "1535.65" {
               description "1535.65 nm/195.221875 THz 3.125GHz spacing";
             }
             enum "1535.63" {
               description "1535.63 nm/195.225000 THz 3.125/6.25/12.5/75GHz spacing";
             }
             enum "1535.60" {
               description "1535.60 nm/195.228125 THz 3.125GHz spacing";
             }
             enum "1535.58" {
               description "1535.58 nm/195.231250 THz 3.125/6.25GHz spacing";
             }
             enum "1535.55" {
               description "1535.55 nm/195.234375 THz 3.125GHz spacing";
             }
             enum "1535.53" {
               description "1535.53 nm/195.237500 THz 3.125/6.25/12.5GHz spacing";
             }
             enum "1535.50" {
               description "1535.50 nm/195.240625 THz 3.125GHz spacing";
             }
             enum "1535.48" {
               description "1535.48 nm/195.243750 THz 3.125/6.25GHz spacing";
             }
             enum "1535.45" {
               description "1535.45 nm/195.246875 THz 3.125GHz spacing";
             }
             enum "1535.43" {
               description "1535.43 nm/195.250000 THz 3.125/6.25/12.5/50GHz spacing";
             }
             enum "1535.40" {
               description "1535.40 nm/195.253125 THz 3.125GHz spacing";
             }
             enum "1535.38" {
               description "1535.38 nm/195.256250 THz 3.125/6.25GHz spacing";
             }
             enum "1535.36" {
               description "1535.36 nm/195.259375 THz 3.125GHz spacing";
             }
             enum "1535.33" {
               description "1535.33 nm/195.262500 THz 3.125/6.25/12.5GHz spacing";
             }
             enum "1535.31" {
               description "1535.31 nm/195.265625 THz 3.125GHz spacing";
             }
             enum "1535.28" {
               description "1535.28 nm/195.268750 THz 3.125/6.25GHz spacing";
             }
             enum "1535.26" {
               description "1535.26 nm/195.271875 THz 3.125GHz spacing";
             }
             enum "1535.23" {
               description "1535.23 nm/195.275000 THz 3.125/6.25/12.5GHz spacing";
             }
             enum "1535.21" {
               description "1535.21 nm/195.278125 THz 3.125GHz spacing";
             }
             enum "1535.18" {
               description "1535.18 nm/195.281250 THz 3.125/6.25GHz spacing";
             }
             enum "1535.16" {
               description "1535.16 nm/195.284375 THz 3.125GHz spacing";
             }
             enum "1535.13" {
               description "1535.13 nm/195.287500 THz 3.125/6.25/12.5GHz spacing";
             }
             enum "1535.11" {
               description "1535.11 nm/195.290625 THz 3.125GHz spacing";
             }
             enum "1535.08" {
               description "1535.08 nm/195.293750 THz 3.125/6.25GHz spacing";
             }
             enum "1535.06" {
               description "1535.06 nm/195.296875 THz 3.125GHz spacing";
             }
             enum "1535.04" {
               description "1535.04 nm/195.300000 THz 3.125/6.25/12.5/50/75/100GHz spacing";
             }
             enum "1535.01" {
               description "1535.01 nm/195.303125 THz 3.125GHz spacing";
             }
             enum "1534.99" {
               description "1534.99 nm/195.306250 THz 3.125/6.25GHz spacing";
             }
             enum "1534.96" {
               description "1534.96 nm/195.309375 THz 3.125GHz spacing";
             }
             enum "1534.94" {
               description "1534.94 nm/195.312500 THz 3.125/6.25/12.5GHz spacing";
             }
             enum "1534.91" {
               description "1534.91 nm/195.315625 THz 3.125GHz spacing";
             }
             enum "1534.89" {
               description "1534.89 nm/195.318750 THz 3.125/6.25GHz spacing";
             }
             enum "1534.86" {
               description "1534.86 nm/195.321875 THz 3.125GHz spacing";
             }
             enum "1534.84" {
               description "1534.84 nm/195.325000 THz 3.125/6.25/12.5GHz spacing";
             }
             enum "1534.81" {
               description "1534.81 nm/195.328125 THz 3.125GHz spacing";
             }
             enum "1534.79" {
               description "1534.79 nm/195.331250 THz 3.125/6.25GHz spacing";
             }
             enum "1534.77" {
               description "1534.77 nm/195.334375 THz 3.125GHz spacing";
             }
             enum "1534.74" {
               description "1534.74 nm/195.337500 THz 3.125/6.25/12.5GHz spacing";
             }
             enum "1534.72" {
               description "1534.72 nm/195.340625 THz 3.125GHz spacing";
             }
             enum "1534.69" {
               description "1534.69 nm/195.343750 THz 3.125/6.25GHz spacing";
             }
             enum "1534.67" {
               description "1534.67 nm/195.346875 THz 3.125GHz spacing";
             }
             enum "1534.64" {
               description "1534.64 nm/195.350000 THz 3.125/6.25/12.5/50GHz spacing";
             }
             enum "1534.62" {
               description "1534.62 nm/195.353125 THz 3.125GHz spacing";
             }
             enum "1534.59" {
               description "1534.59 nm/195.356250 THz 3.125/6.25GHz spacing";
             }
             enum "1534.57" {
               description "1534.57 nm/195.359375 THz 3.125GHz spacing";
             }
             enum "1534.54" {
               description "1534.54 nm/195.362500 THz 3.125/6.25/12.5GHz spacing";
             }
             enum "1534.52" {
               description "1534.52 nm/195.365625 THz 3.125GHz spacing";
             }
             enum "1534.50" {
               description "1534.50 nm/195.368750 THz 3.125/6.25GHz spacing";
             }
             enum "1534.47" {
               description "1534.47 nm/195.371875 THz 3.125GHz spacing";
             }
             enum "1534.45" {
               description "1534.45 nm/195.375000 THz 3.125/6.25/12.5/75GHz spacing";
             }
             enum "1534.42" {
               description "1534.42 nm/195.378125 THz 3.125GHz spacing";
             }
             enum "1534.40" {
               description "1534.40 nm/195.381250 THz 3.125/6.25GHz spacing";
             }
             enum "1534.37" {
               description "1534.37 nm/195.384375 THz 3.125GHz spacing";
             }
             enum "1534.35" {
               description "1534.35 nm/195.387500 THz 3.125/6.25/12.5GHz spacing";
             }
             enum "1534.32" {
               description "1534.32 nm/195.390625 THz 3.125GHz spacing";
             }
             enum "1534.30" {
               description "1534.30 nm/195.393750 THz 3.125/6.25GHz spacing";
             }
             enum "1534.27" {
               description "1534.27 nm/195.396875 THz 3.125GHz spacing";
             }
             enum "1534.25" {
               description "1534.25 nm/195.400000 THz 3.125/6.25/12.5/100GHz spacing";
             }
             enum "1534.23" {
               description "1534.23 nm/195.403125 THz 3.125GHz spacing";
             }
             enum "1534.20" {
               description "1534.20 nm/195.406250 THz 3.125/6.25GHz spacing";
             }
             enum "1534.18" {
               description "1534.18 nm/195.409375 THz 3.125GHz spacing";
             }
             enum "1534.15" {
               description "1534.15 nm/195.412500 THz 3.125/6.25/12.5GHz spacing";
             }
             enum "1534.13" {
               description "1534.13 nm/195.415625 THz 3.125GHz spacing";
             }
             enum "1534.10" {
               description "1534.10 nm/195.418750 THz 3.125/6.25GHz spacing";
             }
             enum "1534.08" {
               description "1534.08 nm/195.421875 THz 3.125GHz spacing";
             }
             enum "1534.05" {
               description "1534.05 nm/195.425000 THz 3.125/6.25/12.5GHz spacing";
             }
             enum "1534.03" {
               description "1534.03 nm/195.428125 THz 3.125GHz spacing";
             }
             enum "1534.00" {
               description "1534.00 nm/195.431250 THz 3.125/6.25GHz spacing";
             }
             enum "1533.98" {
               description "1533.98 nm/195.434375 THz 3.125GHz spacing";
             }
             enum "1533.96" {
               description "1533.96 nm/195.437500 THz 3.125/6.25/12.5GHz spacing";
             }
             enum "1533.93" {
               description "1533.93 nm/195.440625 THz 3.125GHz spacing";
             }
             enum "1533.91" {
               description "1533.91 nm/195.443750 THz 3.125/6.25GHz spacing";
             }
             enum "1533.88" {
               description "1533.88 nm/195.446875 THz 3.125GHz spacing";
             }
             enum "1533.86" {
               description "1533.86 nm/195.450000 THz 3.125/6.25/12.5/50/75GHz spacing";
             }
             enum "1533.83" {
               description "1533.83 nm/195.453125 THz 3.125GHz spacing";
             }
             enum "1533.81" {
               description "1533.81 nm/195.456250 THz 3.125/6.25GHz spacing";
             }
             enum "1533.78" {
               description "1533.78 nm/195.459375 THz 3.125GHz spacing";
             }
             enum "1533.76" {
               description "1533.76 nm/195.462500 THz 3.125/6.25/12.5GHz spacing";
             }
             enum "1533.73" {
               description "1533.73 nm/195.465625 THz 3.125GHz spacing";
             }
             enum "1533.71" {
               description "1533.71 nm/195.468750 THz 3.125/6.25GHz spacing";
             }
             enum "1533.69" {
               description "1533.69 nm/195.471875 THz 3.125GHz spacing";
             }
             enum "1533.66" {
               description "1533.66 nm/195.475000 THz 3.125/6.25/12.5GHz spacing";
             }
             enum "1533.64" {
               description "1533.64 nm/195.478125 THz 3.125GHz spacing";
             }
             enum "1533.61" {
               description "1533.61 nm/195.481250 THz 3.125/6.25GHz spacing";
             }
             enum "1533.59" {
               description "1533.59 nm/195.484375 THz 3.125GHz spacing";
             }
             enum "1533.56" {
               description "1533.56 nm/195.487500 THz 3.125/6.25/12.5GHz spacing";
             }
             enum "1533.54" {
               description "1533.54 nm/195.490625 THz 3.125GHz spacing";
             }
             enum "1533.51" {
               description "1533.51 nm/195.493750 THz 3.125/6.25GHz spacing";
             }
             enum "1533.49" {
               description "1533.49 nm/195.496875 THz 3.125GHz spacing";
             }
             enum "1533.47" {
               description "1533.47 nm/195.500000 THz 3.125/6.25/12.5/100GHz spacing";
             }
             enum "1533.44" {
               description "1533.44 nm/195.503125 THz 3.125GHz spacing";
             }
             enum "1533.42" {
               description "1533.42 nm/195.506250 THz 3.125/6.25GHz spacing";
             }
             enum "1533.39" {
               description "1533.39 nm/195.509375 THz 3.125GHz spacing";
             }
             enum "1533.37" {
               description "1533.37 nm/195.512500 THz 3.125/6.25/12.5GHz spacing";
             }
             enum "1533.34" {
               description "1533.34 nm/195.515625 THz 3.125GHz spacing";
             }
             enum "1533.32" {
               description "1533.32 nm/195.518750 THz 3.125/6.25GHz spacing";
             }
             enum "1533.29" {
               description "1533.29 nm/195.521875 THz 3.125GHz spacing";
             }
             enum "1533.27" {
               description "1533.27 nm/195.525000 THz 3.125/6.25/12.5/75GHz spacing";
             }
             enum "1533.24" {
               description "1533.24 nm/195.528125 THz 3.125GHz spacing";
             }
             enum "1533.22" {
               description "1533.22 nm/195.531250 THz 3.125/6.25GHz spacing";
             }
             enum "1533.20" {
               description "1533.20 nm/195.534375 THz 3.125GHz spacing";
             }
             enum "1533.17" {
               description "1533.17 nm/195.537500 THz 3.125/6.25/12.5GHz spacing";
             }
             enum "1533.15" {
               description "1533.15 nm/195.540625 THz 3.125GHz spacing";
             }
             enum "1533.12" {
               description "1533.12 nm/195.543750 THz 3.125/6.25GHz spacing";
             }
             enum "1533.10" {
               description "1533.10 nm/195.546875 THz 3.125GHz spacing";
             }
             enum "1533.07" {
               description "1533.07 nm/195.550000 THz 3.125/6.25/12.5/50GHz spacing";
             }
             enum "1533.05" {
               description "1533.05 nm/195.553125 THz 3.125GHz spacing";
             }
             enum "1533.02" {
               description "1533.02 nm/195.556250 THz 3.125/6.25GHz spacing";
             }
             enum "1533.00" {
               description "1533.00 nm/195.559375 THz 3.125GHz spacing";
             }
             enum "1532.98" {
               description "1532.98 nm/195.562500 THz 3.125/6.25/12.5GHz spacing";
             }
             enum "1532.95" {
               description "1532.95 nm/195.565625 THz 3.125GHz spacing";
             }
             enum "1532.93" {
               description "1532.93 nm/195.568750 THz 3.125/6.25GHz spacing";
             }
             enum "1532.90" {
               description "1532.90 nm/195.571875 THz 3.125GHz spacing";
             }
             enum "1532.88" {
               description "1532.88 nm/195.575000 THz 3.125/6.25/12.5GHz spacing";
             }
             enum "1532.85" {
               description "1532.85 nm/195.578125 THz 3.125GHz spacing";
             }
             enum "1532.83" {
               description "1532.83 nm/195.581250 THz 3.125/6.25GHz spacing";
             }
             enum "1532.80" {
               description "1532.80 nm/195.584375 THz 3.125GHz spacing";
             }
             enum "1532.78" {
               description "1532.78 nm/195.587500 THz 3.125/6.25/12.5GHz spacing";
             }
             enum "1532.75" {
               description "1532.75 nm/195.590625 THz 3.125GHz spacing";
             }
             enum "1532.73" {
               description "1532.73 nm/195.593750 THz 3.125/6.25GHz spacing";
             }
             enum "1532.71" {
               description "1532.71 nm/195.596875 THz 3.125GHz spacing";
             }
             enum "1532.68" {
               description "1532.68 nm/195.600000 THz 3.125/6.25/12.5/50/75/100GHz spacing";
             }
             enum "1532.66" {
               description "1532.66 nm/195.603125 THz 3.125GHz spacing";
             }
             enum "1532.63" {
               description "1532.63 nm/195.606250 THz 3.125/6.25GHz spacing";
             }
             enum "1532.61" {
               description "1532.61 nm/195.609375 THz 3.125GHz spacing";
             }
             enum "1532.58" {
               description "1532.58 nm/195.612500 THz 3.125/6.25/12.5GHz spacing";
             }
             enum "1532.56" {
               description "1532.56 nm/195.615625 THz 3.125GHz spacing";
             }
             enum "1532.53" {
               description "1532.53 nm/195.618750 THz 3.125/6.25GHz spacing";
             }
             enum "1532.51" {
               description "1532.51 nm/195.621875 THz 3.125GHz spacing";
             }
             enum "1532.49" {
               description "1532.49 nm/195.625000 THz 3.125/6.25/12.5GHz spacing";
             }
             enum "1532.46" {
               description "1532.46 nm/195.628125 THz 3.125GHz spacing";
             }
             enum "1532.44" {
               description "1532.44 nm/195.631250 THz 3.125/6.25GHz spacing";
             }
             enum "1532.41" {
               description "1532.41 nm/195.634375 THz 3.125GHz spacing";
             }
             enum "1532.39" {
               description "1532.39 nm/195.637500 THz 3.125/6.25/12.5GHz spacing";
             }
             enum "1532.36" {
               description "1532.36 nm/195.640625 THz 3.125GHz spacing";
             }
             enum "1532.34" {
               description "1532.34 nm/195.643750 THz 3.125/6.25GHz spacing";
             }
             enum "1532.31" {
               description "1532.31 nm/195.646875 THz 3.125GHz spacing";
             }
             enum "1532.29" {
               description "1532.29 nm/195.650000 THz 3.125/6.25/12.5/50GHz spacing";
             }
             enum "1532.27" {
               description "1532.27 nm/195.653125 THz 3.125GHz spacing";
             }
             enum "1532.24" {
               description "1532.24 nm/195.656250 THz 3.125/6.25GHz spacing";
             }
             enum "1532.22" {
               description "1532.22 nm/195.659375 THz 3.125GHz spacing";
             }
             enum "1532.19" {
               description "1532.19 nm/195.662500 THz 3.125/6.25/12.5GHz spacing";
             }
             enum "1532.17" {
               description "1532.17 nm/195.665625 THz 3.125GHz spacing";
             }
             enum "1532.14" {
               description "1532.14 nm/195.668750 THz 3.125/6.25GHz spacing";
             }
             enum "1532.12" {
               description "1532.12 nm/195.671875 THz 3.125GHz spacing";
             }
             enum "1532.09" {
               description "1532.09 nm/195.675000 THz 3.125/6.25/12.5/75GHz spacing";
             }
             enum "1532.07" {
               description "1532.07 nm/195.678125 THz 3.125GHz spacing";
             }
             enum "1532.04" {
               description "1532.04 nm/195.681250 THz 3.125/6.25GHz spacing";
             }
             enum "1532.02" {
               description "1532.02 nm/195.684375 THz 3.125GHz spacing";
             }
             enum "1532.00" {
               description "1532.00 nm/195.687500 THz 3.125/6.25/12.5GHz spacing";
             }
             enum "1531.97" {
               description "1531.97 nm/195.690625 THz 3.125GHz spacing";
             }
             enum "1531.95" {
               description "1531.95 nm/195.693750 THz 3.125/6.25GHz spacing";
             }
             enum "1531.92" {
               description "1531.92 nm/195.696875 THz 3.125GHz spacing";
             }
             enum "1531.90" {
               description "1531.90 nm/195.700000 THz 3.125/6.25/12.5/100GHz spacing";
             }
             enum "1531.87" {
               description "1531.87 nm/195.703125 THz 3.125GHz spacing";
             }
             enum "1531.85" {
               description "1531.85 nm/195.706250 THz 3.125/6.25GHz spacing";
             }
             enum "1531.82" {
               description "1531.82 nm/195.709375 THz 3.125GHz spacing";
             }
             enum "1531.80" {
               description "1531.80 nm/195.712500 THz 3.125/6.25/12.5GHz spacing";
             }
             enum "1531.78" {
               description "1531.78 nm/195.715625 THz 3.125GHz spacing";
             }
             enum "1531.75" {
               description "1531.75 nm/195.718750 THz 3.125/6.25GHz spacing";
             }
             enum "1531.73" {
               description "1531.73 nm/195.721875 THz 3.125GHz spacing";
             }
             enum "1531.70" {
               description "1531.70 nm/195.725000 THz 3.125/6.25/12.5GHz spacing";
             }
             enum "1531.68" {
               description "1531.68 nm/195.728125 THz 3.125GHz spacing";
             }
             enum "1531.65" {
               description "1531.65 nm/195.731250 THz 3.125/6.25GHz spacing";
             }
             enum "1531.63" {
               description "1531.63 nm/195.734375 THz 3.125GHz spacing";
             }
             enum "1531.60" {
               description "1531.60 nm/195.737500 THz 3.125/6.25/12.5GHz spacing";
             }
             enum "1531.58" {
               description "1531.58 nm/195.740625 THz 3.125GHz spacing";
             }
             enum "1531.56" {
               description "1531.56 nm/195.743750 THz 3.125/6.25GHz spacing";
             }
             enum "1531.53" {
               description "1531.53 nm/195.746875 THz 3.125GHz spacing";
             }
             enum "1531.51" {
               description "1531.51 nm/195.750000 THz 3.125/6.25/12.5/50/75GHz spacing";
             }
             enum "1531.48" {
               description "1531.48 nm/195.753125 THz 3.125GHz spacing";
             }
             enum "1531.46" {
               description "1531.46 nm/195.756250 THz 3.125/6.25GHz spacing";
             }
             enum "1531.43" {
               description "1531.43 nm/195.759375 THz 3.125GHz spacing";
             }
             enum "1531.41" {
               description "1531.41 nm/195.762500 THz 3.125/6.25/12.5GHz spacing";
             }
             enum "1531.38" {
               description "1531.38 nm/195.765625 THz 3.125GHz spacing";
             }
             enum "1531.36" {
               description "1531.36 nm/195.768750 THz 3.125/6.25GHz spacing";
             }
             enum "1531.34" {
               description "1531.34 nm/195.771875 THz 3.125GHz spacing";
             }
             enum "1531.31" {
               description "1531.31 nm/195.775000 THz 3.125/6.25/12.5GHz spacing";
             }
             enum "1531.29" {
               description "1531.29 nm/195.778125 THz 3.125GHz spacing";
             }
             enum "1531.26" {
               description "1531.26 nm/195.781250 THz 3.125/6.25GHz spacing";
             }
             enum "1531.24" {
               description "1531.24 nm/195.784375 THz 3.125GHz spacing";
             }
             enum "1531.21" {
               description "1531.21 nm/195.787500 THz 3.125/6.25/12.5GHz spacing";
             }
             enum "1531.19" {
               description "1531.19 nm/195.790625 THz 3.125GHz spacing";
             }
             enum "1531.16" {
               description "1531.16 nm/195.793750 THz 3.125/6.25GHz spacing";
             }
             enum "1531.14" {
               description "1531.14 nm/195.796875 THz 3.125GHz spacing";
             }
             enum "1531.12" {
               description "1531.12 nm/195.800000 THz 3.125/6.25/12.5/100GHz spacing";
             }
             enum "1531.09" {
               description "1531.09 nm/195.803125 THz 3.125GHz spacing";
             }
             enum "1531.07" {
               description "1531.07 nm/195.806250 THz 3.125/6.25GHz spacing";
             }
             enum "1531.04" {
               description "1531.04 nm/195.809375 THz 3.125GHz spacing";
             }
             enum "1531.02" {
               description "1531.02 nm/195.812500 THz 3.125/6.25/12.5GHz spacing";
             }
             enum "1530.99" {
               description "1530.99 nm/195.815625 THz 3.125GHz spacing";
             }
             enum "1530.97" {
               description "1530.97 nm/195.818750 THz 3.125/6.25GHz spacing";
             }
             enum "1530.94" {
               description "1530.94 nm/195.821875 THz 3.125GHz spacing";
             }
             enum "1530.92" {
               description "1530.92 nm/195.825000 THz 3.125/6.25/12.5/75GHz spacing";
             }
             enum "1530.90" {
               description "1530.90 nm/195.828125 THz 3.125GHz spacing";
             }
             enum "1530.87" {
               description "1530.87 nm/195.831250 THz 3.125/6.25GHz spacing";
             }
             enum "1530.85" {
               description "1530.85 nm/195.834375 THz 3.125GHz spacing";
             }
             enum "1530.82" {
               description "1530.82 nm/195.837500 THz 3.125/6.25/12.5GHz spacing";
             }
             enum "1530.80" {
               description "1530.80 nm/195.840625 THz 3.125GHz spacing";
             }
             enum "1530.77" {
               description "1530.77 nm/195.843750 THz 3.125/6.25GHz spacing";
             }
             enum "1530.75" {
               description "1530.75 nm/195.846875 THz 3.125GHz spacing";
             }
             enum "1530.72" {
               description "1530.72 nm/195.850000 THz 3.125/6.25/12.5/50GHz spacing";
             }
             enum "1530.70" {
               description "1530.70 nm/195.853125 THz 3.125GHz spacing";
             }
             enum "1530.68" {
               description "1530.68 nm/195.856250 THz 3.125/6.25GHz spacing";
             }
             enum "1530.65" {
               description "1530.65 nm/195.859375 THz 3.125GHz spacing";
             }
             enum "1530.63" {
               description "1530.63 nm/195.862500 THz 3.125/6.25/12.5GHz spacing";
             }
             enum "1530.60" {
               description "1530.60 nm/195.865625 THz 3.125GHz spacing";
             }
             enum "1530.58" {
               description "1530.58 nm/195.868750 THz 3.125/6.25GHz spacing";
             }
             enum "1530.55" {
               description "1530.55 nm/195.871875 THz 3.125GHz spacing";
             }
             enum "1530.53" {
               description "1530.53 nm/195.875000 THz 3.125/6.25/12.5GHz spacing";
             }
             enum "1530.51" {
               description "1530.51 nm/195.878125 THz 3.125GHz spacing";
             }
             enum "1530.48" {
               description "1530.48 nm/195.881250 THz 3.125/6.25GHz spacing";
             }
             enum "1530.46" {
               description "1530.46 nm/195.884375 THz 3.125GHz spacing";
             }
             enum "1530.43" {
               description "1530.43 nm/195.887500 THz 3.125/6.25/12.5GHz spacing";
             }
             enum "1530.41" {
               description "1530.41 nm/195.890625 THz 3.125GHz spacing";
             }
             enum "1530.38" {
               description "1530.38 nm/195.893750 THz 3.125/6.25GHz spacing";
             }
             enum "1530.36" {
               description "1530.36 nm/195.896875 THz 3.125GHz spacing";
             }
             enum "1530.33" {
               description "1530.33 nm/195.900000 THz 3.125/6.25/12.5/50/75/100GHz spacing";
             }
             enum "1530.31" {
               description "1530.31 nm/195.903125 THz 3.125GHz spacing";
             }
             enum "1530.29" {
               description "1530.29 nm/195.906250 THz 3.125/6.25GHz spacing";
             }
             enum "1530.26" {
               description "1530.26 nm/195.909375 THz 3.125GHz spacing";
             }
             enum "1530.24" {
               description "1530.24 nm/195.912500 THz 3.125/6.25/12.5GHz spacing";
             }
             enum "1530.21" {
               description "1530.21 nm/195.915625 THz 3.125GHz spacing";
             }
             enum "1530.19" {
               description "1530.19 nm/195.918750 THz 3.125/6.25GHz spacing";
             }
             enum "1530.16" {
               description "1530.16 nm/195.921875 THz 3.125GHz spacing";
             }
             enum "1530.14" {
               description "1530.14 nm/195.925000 THz 3.125/6.25/12.5GHz spacing";
             }
             enum "1530.11" {
               description "1530.11 nm/195.928125 THz 3.125GHz spacing";
             }
             enum "1530.09" {
               description "1530.09 nm/195.931250 THz 3.125/6.25GHz spacing";
             }
             enum "1530.07" {
               description "1530.07 nm/195.934375 THz 3.125GHz spacing";
             }
             enum "1530.04" {
               description "1530.04 nm/195.937500 THz 3.125/6.25/12.5GHz spacing";
             }
             enum "1530.02" {
               description "1530.02 nm/195.940625 THz 3.125GHz spacing";
             }
             enum "1529.99" {
               description "1529.99 nm/195.943750 THz 3.125/6.25GHz spacing";
             }
             enum "1529.97" {
               description "1529.97 nm/195.946875 THz 3.125GHz spacing";
             }
             enum "1529.94" {
               description "1529.94 nm/195.950000 THz 3.125/6.25/12.5/50GHz spacing";
             }
             enum "1529.92" {
               description "1529.92 nm/195.953125 THz 3.125GHz spacing";
             }
             enum "1529.89" {
               description "1529.89 nm/195.956250 THz 3.125/6.25GHz spacing";
             }
             enum "1529.87" {
               description "1529.87 nm/195.959375 THz 3.125GHz spacing";
             }
             enum "1529.85" {
               description "1529.85 nm/195.962500 THz 3.125/6.25/12.5GHz spacing";
             }
             enum "1529.82" {
               description "1529.82 nm/195.965625 THz 3.125GHz spacing";
             }
             enum "1529.80" {
               description "1529.80 nm/195.968750 THz 3.125/6.25GHz spacing";
             }
             enum "1529.77" {
               description "1529.77 nm/195.971875 THz 3.125GHz spacing";
             }
             enum "1529.75" {
               description "1529.75 nm/195.975000 THz 3.125/6.25/12.5/75GHz spacing";
             }
             enum "1529.72" {
               description "1529.72 nm/195.978125 THz 3.125GHz spacing";
             }
             enum "1529.70" {
               description "1529.70 nm/195.981250 THz 3.125/6.25GHz spacing";
             }
             enum "1529.68" {
               description "1529.68 nm/195.984375 THz 3.125GHz spacing";
             }
             enum "1529.65" {
               description "1529.65 nm/195.987500 THz 3.125/6.25/12.5GHz spacing";
             }
             enum "1529.63" {
               description "1529.63 nm/195.990625 THz 3.125GHz spacing";
             }
             enum "1529.60" {
               description "1529.60 nm/195.993750 THz 3.125/6.25GHz spacing";
             }
             enum "1529.58" {
               description "1529.58 nm/195.996875 THz 3.125GHz spacing";
             }
             enum "1529.55" {
               description "1529.55 nm/196.000000 THz 3.125/6.25/12.5/100GHz spacing";
             }
             enum "1529.53" {
               description "1529.53 nm/196.003125 THz 3.125GHz spacing";
             }
             enum "1529.50" {
               description "1529.50 nm/196.006250 THz 3.125/6.25GHz spacing";
             }
             enum "1529.48" {
               description "1529.48 nm/196.009375 THz 3.125GHz spacing";
             }
             enum "1529.46" {
               description "1529.46 nm/196.012500 THz 3.125/6.25/12.5GHz spacing";
             }
             enum "1529.43" {
               description "1529.43 nm/196.015625 THz 3.125GHz spacing";
             }
             enum "1529.41" {
               description "1529.41 nm/196.018750 THz 3.125/6.25GHz spacing";
             }
             enum "1529.38" {
               description "1529.38 nm/196.021875 THz 3.125GHz spacing";
             }
             enum "1529.36" {
               description "1529.36 nm/196.025000 THz 3.125/6.25/12.5GHz spacing";
             }
             enum "1529.33" {
               description "1529.33 nm/196.028125 THz 3.125GHz spacing";
             }
             enum "1529.31" {
               description "1529.31 nm/196.031250 THz 3.125/6.25GHz spacing";
             }
             enum "1529.29" {
               description "1529.29 nm/196.034375 THz 3.125GHz spacing";
             }
             enum "1529.26" {
               description "1529.26 nm/196.037500 THz 3.125/6.25/12.5GHz spacing";
             }
             enum "1529.24" {
               description "1529.24 nm/196.040625 THz 3.125GHz spacing";
             }
             enum "1529.21" {
               description "1529.21 nm/196.043750 THz 3.125/6.25GHz spacing";
             }
             enum "1529.19" {
               description "1529.19 nm/196.046875 THz 3.125GHz spacing";
             }
             enum "1529.16" {
               description "1529.16 nm/196.050000 THz 3.125/6.25/12.5/50/75GHz spacing";
             }
             enum "1529.14" {
               description "1529.14 nm/196.053125 THz 3.125GHz spacing";
             }
             enum "1529.11" {
               description "1529.11 nm/196.056250 THz 3.125/6.25GHz spacing";
             }
             enum "1529.09" {
               description "1529.09 nm/196.059375 THz 3.125GHz spacing";
             }
             enum "1529.07" {
               description "1529.07 nm/196.062500 THz 3.125/6.25/12.5GHz spacing";
             }
             enum "1529.04" {
               description "1529.04 nm/196.065625 THz 3.125GHz spacing";
             }
             enum "1529.02" {
               description "1529.02 nm/196.068750 THz 3.125/6.25GHz spacing";
             }
             enum "1528.99" {
               description "1528.99 nm/196.071875 THz 3.125GHz spacing";
             }
             enum "1528.97" {
               description "1528.97 nm/196.075000 THz 3.125/6.25/12.5GHz spacing";
             }
             enum "1528.94" {
               description "1528.94 nm/196.078125 THz 3.125GHz spacing";
             }
             enum "1528.92" {
               description "1528.92 nm/196.081250 THz 3.125/6.25GHz spacing";
             }
             enum "1528.90" {
               description "1528.90 nm/196.084375 THz 3.125GHz spacing";
             }
             enum "1528.87" {
               description "1528.87 nm/196.087500 THz 3.125/6.25/12.5GHz spacing";
             }
             enum "1528.85" {
               description "1528.85 nm/196.090625 THz 3.125GHz spacing";
             }
             enum "1528.82" {
               description "1528.82 nm/196.093750 THz 3.125/6.25GHz spacing";
             }
             enum "1528.80" {
               description "1528.80 nm/196.096875 THz 3.125GHz spacing";
             }
             enum "1528.77" {
               description "1528.77 nm/196.100000 THz 3.125/6.25/12.5/50/75/100GHz spacing";
             }
             enum "1528.75" {
               description "1528.75 nm/196.103125 THz 3.125GHz spacing";
             }
             enum "1528.72" {
               description "1528.72 nm/196.106250 THz 3.125/6.25GHz spacing";
             }
             enum "1528.70" {
               description "1528.70 nm/196.109375 THz 3.125GHz spacing";
             }
             enum "1528.68" {
               description "1528.68 nm/196.112500 THz 3.125/6.25/12.5GHz spacing";
             }
             enum "1528.65" {
               description "1528.65 nm/196.115625 THz 3.125GHz spacing";
             }
             enum "1528.63" {
               description "1528.63 nm/196.118750 THz 3.125/6.25GHz spacing";
             }
             enum "1528.60" {
               description "1528.60 nm/196.121875 THz 3.125GHz spacing";
             }
             enum "1528.58" {
               description "1528.58 nm/196.125000 THz 3.125/6.25/12.5/75GHz spacing";
             }
             enum "1528.55" {
               description "1528.55 nm/196.128125 THz 3.125GHz spacing";
             }
             enum "1528.53" {
               description "1528.53 nm/196.131250 THz 3.125/6.25GHz spacing";
             }
             enum "1528.51" {
               description "1528.51 nm/196.134375 THz 3.125GHz spacing";
             }
             enum "1528.48" {
               description "1528.48 nm/196.137500 THz 3.125/6.25/12.5GHz spacing";
             }
             enum "1528.46" {
               description "1528.46 nm/196.140625 THz 3.125GHz spacing";
             }
             enum "1528.43" {
               description "1528.43 nm/196.143750 THz 3.125/6.25GHz spacing";
             }
             enum "1528.41" {
               description "1528.41 nm/196.146875 THz 3.125GHz spacing";
             }
             enum "1528.38" {
               description "1528.38 nm/196.15040 THz 50Ghz spacing";
             }
           }
         }
         uses apply-advanced;
         choice wss {
           case case_1 {
             container switch {
               presence "enable switch";
               description "Switch the wavelength to an optical interface";
               uses apply-advanced;
               leaf interface-name {
                 description "Name of physical interface";
                 type string;
               }
             }
           }
           case case_2 {
             leaf wss-express-in {
               description "Express-in this wavelength to another optical card";
               type empty;
             }
           }
         }
       }
       container tca {
         description "Set tca for optical properties";
         uses apply-advanced;
         container osc-tx-power-high-tca {
           description "OSC TX power high TCA";
           uses apply-advanced;
           choice enable-tca-choice {
             leaf enable-tca {
               description "Enable tca";
               type empty;
             }
             leaf no-enable-tca {
               description "Don't enable tca";
               type empty;
             }
           }
           leaf threshold {
             description "Threshold for 15 minute osc tx power high TCA in dBm";
             type string;
           }
           leaf threshold-24hrs {
             description "Threshold for 24 hour osc tx power high TCA in dBm";
             type string;
           }
         }
         container osc-tx-power-low-tca {
           description "OSC TX power low TCA";
           uses apply-advanced;
           choice enable-tca-choice {
             leaf enable-tca {
               description "Enable tca";
               type empty;
             }
             leaf no-enable-tca {
               description "Don't enable tca";
               type empty;
             }
           }
           leaf threshold {
             description "Threshold for 15 minute osc tx power low TCA in dBm";
             type string;
           }
           leaf threshold-24hrs {
             description "Threshold for 24 hour osc tx power low TCA in dBm";
             type string;
           }
         }
         container osc-rx-power-high-tca {
           description "OSC RX power high TCA";
           uses apply-advanced;
           choice enable-tca-choice {
             leaf enable-tca {
               description "Enable tca";
               type empty;
             }
             leaf no-enable-tca {
               description "Don't enable tca";
               type empty;
             }
           }
           leaf threshold {
             description "Threshold for 15 minute osc rx power high TCA in dBm";
             type string;
           }
           leaf threshold-24hrs {
             description "Threshold for 24 hour osc rx power high TCA in dBm";
             type string;
           }
         }
         container osc-rx-power-low-tca {
           description "OSC RX power low TCA";
           uses apply-advanced;
           choice enable-tca-choice {
             leaf enable-tca {
               description "Enable tca";
               type empty;
             }
             leaf no-enable-tca {
               description "Don't enable tca";
               type empty;
             }
           }
           leaf threshold {
             description "Threshold for 15 minute osc rx power low TCA in dBm";
             type string;
           }
           leaf threshold-24hrs {
             description "Threshold for 24 hour osc rx power low TCA in dBm";
             type string;
           }
         }
         container osc-fiber-loss-high-tca {
           description "OSC fiber loss high TCA";
           uses apply-advanced;
           choice enable-tca-choice {
             leaf enable-tca {
               description "Enable tca";
               type empty;
             }
             leaf no-enable-tca {
               description "Don't enable tca";
               type empty;
             }
           }
           leaf threshold {
             description "Threshold for 15 minute osc fiber loss high TCA in dB";
             type string;
           }
           leaf threshold-24hrs {
             description "Threshold for 24 hour osc fiber loss high TCA in dB";
             type string;
           }
         }
         container osc-fiber-loss-low-tca {
           description "OSC fiber loss low TCA";
           uses apply-advanced;
           choice enable-tca-choice {
             leaf enable-tca {
               description "Enable tca";
               type empty;
             }
             leaf no-enable-tca {
               description "Don't enable tca";
               type empty;
             }
           }
           leaf threshold {
             description "Threshold for 15 minute osc fiber loss low TCA in dB";
             type string;
           }
           leaf threshold-24hrs {
             description "Threshold for 24 hour osc fiber loss low TCA in dB";
             type string;
           }
         }
         container lout-voa-high-tca {
           description "LOUT VOA high TCA";
           uses apply-advanced;
           choice enable-tca-choice {
             leaf enable-tca {
               description "Enable tca";
               type empty;
             }
             leaf no-enable-tca {
               description "Don't enable tca";
               type empty;
             }
           }
           leaf threshold {
             description "Threshold for 15 minute LOUT VOA high TCA in dB";
             type string;
           }
           leaf threshold-24hrs {
             description "Threshold for 24 hour LOUT VOA high TCA in dB";
             type string;
           }
         }
         container lout-voa-low-tca {
           description "LOUT VOA low TCA";
           uses apply-advanced;
           choice enable-tca-choice {
             leaf enable-tca {
               description "Enable tca";
               type empty;
             }
             leaf no-enable-tca {
               description "Don't enable tca";
               type empty;
             }
           }
           leaf threshold {
             description "Threshold for 15 minute LOUT VOA low TCA in dB";
             type string;
           }
           leaf threshold-24hrs {
             description "Threshold for 24 hour LOUT VOA low TCA in dB";
             type string;
           }
         }
         container edfa1-in-power-high-tca {
           description "Ingress EDFA input power high TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA input power high TCA in dBm";
             type string;
           }
           leaf threshold-24hrs {
             description "Threshold for 24 hour Ingress EDFA input power high TCA in dBm";
             type string;
           }
         }
         container edfa1-in-power-low-tca {
           description "Ingress EDFA input power low TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA input power low TCA in dBm";
             type string;
           }
           leaf threshold-24hrs {
             description "Threshold for 24 hour Ingress EDFA input power low TCA in dBm";
             type string;
           }
         }
         container edfa1-out-power-high-tca {
           description "Ingress EDFA output power high TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA output power high TCA in dBm";
             type string;
           }
           leaf threshold-24hrs {
             description "Threshold for 24 hour Ingress EDFA output power high TCA in dBm";
             type string;
           }
         }
         container edfa1-out-power-low-tca {
           description "Ingress EDFA output power low TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA output power low TCA in dBm";
             type string;
           }
           leaf threshold-24hrs {
             description "Threshold for 24 hour Ingress EDFA output power low TCA in dBm";
             type string;
           }
         }
         container edfa1-sig-power-high-tca {
           description "Ingress EDFA signal power high TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA signal power high TCA in dBm";
             type string;
           }
           leaf threshold-24hrs {
             description "Threshold for 24 hour Ingress EDFA signal power high TCA in dBm";
             type string;
           }
         }
         container edfa1-sig-power-low-tca {
           description "Ingress EDFA signal power low TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA signal power low TCA in dBm";
             type string;
           }
           leaf threshold-24hrs {
             description "Threshold for 24 hour Ingress EDFA signal power low TCA in dBm";
             type string;
           }
         }
         container edfa1-awg-high-tca {
           description "Ingress EDFA pump AWG high TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA pump AWG high TCA in mW";
             type string;
           }
           leaf threshold-24hrs {
             description "Threshold for 24 hour Ingress EDFA pump AWG high TCA in mW";
             type string;
           }
         }
         container edfa1-awg-low-tca {
           description "Ingress EDFA pump AWG low TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA pump AWG low TCA in mW";
             type string;
           }
           leaf threshold-24hrs {
             description "Threshold for 24 hour Ingress EDFA pump AWG low TCA in mW";
             type string;
           }
         }
         container edfa1-express-high-tca {
           description "Ingress EDFA pump express high TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA pump express high TCA in mW";
             type string;
           }
           leaf threshold-24hrs {
             description "Threshold for 24 hour Ingress EDFA pump express high TCA in mW";
             type string;
           }
         }
         container edfa1-express-low-tca {
           description "Ingress EDFA pump express low TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA pump express low TCA in mW";
             type string;
           }
           leaf threshold-24hrs {
             description "Threshold for 24 hour Ingress EDFA pump express low TCA in mW";
             type string;
           }
         }
         container edfa2-in-power-high-tca {
           description "Egress EDFA input power high TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA input power high TCA in dBm";
             type string;
           }
           leaf threshold-24hrs {
             description "Threshold for 24 hour Egress EDFA input power high TCA in dBm";
             type string;
           }
         }
         container edfa2-in-power-low-tca {
           description "Egress EDFA input power low TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA input power low TCA in dBm";
             type string;
           }
           leaf threshold-24hrs {
             description "Threshold for 24 hour Egress EDFA input power low TCA in dBm";
             type string;
           }
         }
         container edfa2-out-power-high-tca {
           description "Egress EDFA output power high TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA output power high TCA in dBm";
             type string;
           }
           leaf threshold-24hrs {
             description "Threshold for 24 hour Egress EDFA output power high TCA in dBm";
             type string;
           }
         }
         container edfa2-out-power-low-tca {
           description "Egress EDFA output power low TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA output power low TCA in dBm";
             type string;
           }
           leaf threshold-24hrs {
             description "Threshold for 24 hour Egress EDFA output power low TCA in dBm";
             type string;
           }
         }
         container edfa2-sig-power-high-tca {
           description "Egress EDFA signal power high TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA signal power high TCA in dBm";
             type string;
           }
           leaf threshold-24hrs {
             description "Threshold for 24 hour Egress EDFA signal power high TCA in dBm";
             type string;
           }
         }
         container edfa2-sig-power-low-tca {
           description "Egress EDFA signal power low TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA signal power low TCA in dBm";
             type string;
           }
           leaf threshold-24hrs {
             description "Threshold for 24 hour Egress EDFA signal power low TCA in dBm";
             type string;
           }
         }
         container edfa2-awg-high-tca {
           description "Egress EDFA pump AWG high TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA pump AWG high TCA in mW";
             type string;
           }
           leaf threshold-24hrs {
             description "Threshold for 24 hour Egress EDFA pump AWG high TCA in mW";
             type string;
           }
         }
         container edfa2-awg-low-tca {
           description "Egress EDFA pump AWG low TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA pump AWG low TCA in mW";
             type string;
           }
           leaf threshold-24hrs {
             description "Threshold for 24 hour Egress EDFA pump AWG low TCA in mW";
             type string;
           }
         }
         container edfa2-express-high-tca {
           description "Egress EDFA pump express high TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA pump express high TCA in mW";
             type string;
           }
           leaf threshold-24hrs {
             description "Threshold for 24 hour Egress EDFA pump express high TCA in mW";
             type string;
           }
         }
         container edfa2-express-low-tca {
           description "Egress EDFA pump express low TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA pump express low TCA in mW";
             type string;
           }
           leaf threshold-24hrs {
             description "Threshold for 24 hour Egress EDFA pump express low TCA in mW";
             type string;
           }
         }
         container ocm-power-high-line-out-tca {
           description "OCM Power Line Out high TCA";
           uses apply-advanced;
           choice enable-tca-choice {
             leaf enable-tca {
               description "Enable tca";
               type empty;
             }
             leaf no-enable-tca {
               description "Don't enable tca";
               type empty;
             }
           }
           leaf threshold {
             description "Threshold for 15 minute OCM Power high TCA in dBm";
             type string;
           }
           leaf threshold-24hrs {
             description "Threshold for 24 hour OCM Power high TCA in dBm";
             type string;
           }
         }
         container ocm-power-low-line-out-tca {
           description "OCM Power Line Out low TCA";
           uses apply-advanced;
           choice enable-tca-choice {
             leaf enable-tca {
               description "Enable tca";
               type empty;
             }
             leaf no-enable-tca {
               description "Don't enable tca";
               type empty;
             }
           }
           leaf threshold {
             description "Threshold for 15 minute OCM Power low TCA in dBm";
             type string;
           }
           leaf threshold-24hrs {
             description "Threshold for 24 hour OCM Power low TCA in dBm";
             type string;
           }
         }
       }
       container expansion-card {
         description "Associate an expansion card with the IPLC card";
         uses apply-advanced;
         container fpc {
           presence "enable fpc";
           uses apply-advanced;
           leaf fpc-slot {
             type union {
               type string {
                 pattern "<.*>|$.*";
               }
               type uint32;
             }
           }
         }
       }
       container express-in {
         description "Associate an express-in card with the IPLC card";
         uses apply-advanced;
         container fpc {
           presence "enable fpc";
           uses apply-advanced;
           leaf fpc-slot {
             type union {
               type string {
                 pattern "<.*>|$.*";
               }
               type uint32;
             }
           }
         }
       }
       container amplifier-chain {
         description "In-line amplifier options";
         uses apply-advanced;
         choice anchor-iplc-choice {
           leaf anchor-iplc {
             description "Mark IPLC as anchor for In-line amplifier chain";
             type empty;
           }
           leaf no-anchor-iplc {
             description "Don't mark IPLC as anchor for In-line amplifier chain";
             type empty;
           }
         }
         leaf osc-ip {
           description "IPLC OSC path IPv4 address format w.x.y.z/a";
           type string;
         }
         leaf osc-mac {
           description "IPLC OSC path MAC address format a:b:c:d:e:f";
           type string;
         }
         list ila {
           key name;
           description "Configure In-line amplifier number";
           leaf name {
             description "In-line amplifier Chain position number";
             type union {
               type string {
                 pattern "<.*>|$.*";
               }
               type uint32 {
                 range "0 .. 14";
               }
             }
           }
           uses apply-advanced;
           container ila-options {
             description "In-line amplifier settings";
             uses apply-advanced;
             leaf ila-ipv4-address {
               description "In-line amplifier IPV4 address format w.x.y.z/a";
               type string;
             }
             leaf ila-user {
               description "ILA User Name";
               type string;
             }
             leaf ila-password {
               description "ILA password string";
               type jt:unreadable;
             }
             container edfa-a-b {
               description "Configure edfa-a-b";
               uses apply-advanced;
               container tca-input-power-low {
                 description "Input power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute input power low TCA in dBm";
                   type string;
                 }
                 leaf threshold-24hrs {
                   description "Threshold for 24 hour input power low TCA in dBm";
                   type string;
                 }
               }
               container tca-input-power-high {
                 description "Input power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute input power high TCA in dBm";
                   type string;
                 }
                 leaf threshold-24hrs {
                   description "Threshold for 24 hour input power high TCA in dBm";
                   type string;
                 }
               }
               container tca-output-power-low {
                 description "Output power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute output power low TCA in dBm";
                   type string;
                 }
                 leaf threshold-24hrs {
                   description "Threshold for 24 hour output power low TCA in dBm";
                   type string;
                 }
               }
               container tca-output-power-high {
                 description "Output power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute output power high TCA in dBm";
                   type string;
                 }
                 leaf threshold-24hrs {
                   description "Threshold for 24 hour output power high TCA in dBm";
                   type string;
                 }
               }
               container tca-signal-output-power-low {
                 description "Signal output power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute signal output power low TCA in dBm";
                   type string;
                 }
                 leaf threshold-24hrs {
                   description "Threshold for 24 hour signal output power low TCA in dBm";
                   type string;
                 }
               }
               container tca-signal-output-power-high {
                 description "Signal output power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute signal output power high TCA in dBm";
                   type string;
                 }
                 leaf threshold-24hrs {
                   description "Threshold for 24 hour signal output power high TCA in dBm";
                   type string;
                 }
               }
               container tca-pump0-current-low {
                 description "Pump0 current low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump0 current low TCA in mA";
                   type string;
                 }
                 leaf threshold-24hrs {
                   description "Threshold for 24 hour pump0 current low TCA in mA";
                   type string;
                 }
               }
               container tca-pump0-current-high {
                 description "Pump0 current high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump0 current high TCA in mA";
                   type string;
                 }
                 leaf threshold-24hrs {
                   description "Threshold for 24 hour pump0 current high TCA in mA";
                   type string;
                 }
               }
               container tca-pump1-current-low {
                 description "Pump1 current low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump1 current low TCA in mA";
                   type string;
                 }
                 leaf threshold-24hrs {
                   description "Threshold for 24 hour pump1 current low TCA in mA";
                   type string;
                 }
               }
               container tca-pump1-current-high {
                 description "Pump1 current high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump1 current high TCA in mA";
                   type string;
                 }
                 leaf threshold-24hrs {
                   description "Threshold for 24 hour pump1 current high TCA in mA";
                   type string;
                 }
               }
               container tca-pump0-temperature-low {
                 description "Pump0 temperature low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump0 temperature low TCA in C";
                   type string;
                 }
                 leaf threshold-24hrs {
                   description "Threshold for 24 hour pump0 temperature low TCA in C";
                   type string;
                 }
               }
               container tca-pump0-temperature-high {
                 description "Pump0 temperature high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump0 temperature high TCA in C";
                   type string;
                 }
                 leaf threshold-24hrs {
                   description "Threshold for 24 hour pump0 temperature high TCA in C";
                   type string;
                 }
               }
               container tca-pump1-temperature-low {
                 description "Pump1 temperature low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump1 temperature low TCA in C";
                   type string;
                 }
                 leaf threshold-24hrs {
                   description "Threshold for 24 hour pump1 temperature low TCA in C";
                   type string;
                 }
               }
               container tca-pump1-temperature-high {
                 description "Pump1 temperature high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump1 temperature high TCA in C";
                   type string;
                 }
                 leaf threshold-24hrs {
                   description "Threshold for 24 hour pump1 temperature high TCA in C";
                   type string;
                 }
               }
             }
             container voa-a {
               description "Configure voa-a";
               uses apply-advanced;
               container tca-attenuation-low {
                 description "Attenuation low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute attenuation low TCA in dBm";
                   type string;
                 }
                 leaf threshold-24hrs {
                   description "Threshold for 24 hour attenuation low TCA in dBm";
                   type string;
                 }
               }
               container tca-attenuation-high {
                 description "Attenuation high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute attenuation high TCA in dBm";
                   type string;
                 }
                 leaf threshold-24hrs {
                   description "Threshold for 24 hour attenuation high TCA in dBm";
                   type string;
                 }
               }
             }
             container osc-a {
               description "Configure osc-a";
               uses apply-advanced;
               container osc-tx-power-high-tca {
                 description "OSC TX power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc tx power high TCA in dBm";
                   type string;
                 }
                 leaf threshold-24hrs {
                   description "Threshold for 24 hour osc tx power high TCA in dBm";
                   type string;
                 }
               }
               container osc-tx-power-low-tca {
                 description "OSC TX power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc tx power low TCA in dBm";
                   type string;
                 }
                 leaf threshold-24hrs {
                   description "Threshold for 24 hour osc tx power low TCA in dBm";
                   type string;
                 }
               }
               container osc-rx-power-high-tca {
                 description "OSC RX power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc rx power high TCA in dBm";
                   type string;
                 }
                 leaf threshold-24hrs {
                   description "Threshold for 24 hour osc rx power high TCA in dBm";
                   type string;
                 }
               }
               container osc-rx-power-low-tca {
                 description "OSC RX power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc rx power low TCA in dBm";
                   type string;
                 }
                 leaf threshold-24hrs {
                   description "Threshold for 24 hour osc rx power low TCA in dBm";
                   type string;
                 }
               }
               container osc-fiber-loss-high-tca {
                 description "OSC fiber loss high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc fiber loss high TCA in dBm";
                   type string;
                 }
                 leaf threshold-24hrs {
                   description "Threshold for 24 hour osc fiber loss high TCA in dBm";
                   type string;
                 }
               }
               container osc-fiber-loss-low-tca {
                 description "OSC fiber loss low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc fiber loss low TCA in dBm";
                   type string;
                 }
                 leaf threshold-24hrs {
                   description "Threshold for 24 hour osc fiber loss low TCA in dBm";
                   type string;
                 }
               }
             }
             container edfa-b-a {
               description "Configure edfa-b-a";
               uses apply-advanced;
               container tca-input-power-low {
                 description "Input power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute input power low TCA in dBm";
                   type string;
                 }
                 leaf threshold-24hrs {
                   description "Threshold for 24 hour input power low TCA in dBm";
                   type string;
                 }
               }
               container tca-input-power-high {
                 description "Input power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute input power high TCA in dBm";
                   type string;
                 }
                 leaf threshold-24hrs {
                   description "Threshold for 24 hour input power high TCA in dBm";
                   type string;
                 }
               }
               container tca-output-power-low {
                 description "Output power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute output power low TCA in dBm";
                   type string;
                 }
                 leaf threshold-24hrs {
                   description "Threshold for 24 hour output power low TCA in dBm";
                   type string;
                 }
               }
               container tca-output-power-high {
                 description "Output power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute output power high TCA in dBm";
                   type string;
                 }
                 leaf threshold-24hrs {
                   description "Threshold for 24 hour output power high TCA in dBm";
                   type string;
                 }
               }
               container tca-signal-output-power-low {
                 description "Signal output power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute signal output power low TCA in dBm";
                   type string;
                 }
                 leaf threshold-24hrs {
                   description "Threshold for 24 hour signal output power low TCA in dBm";
                   type string;
                 }
               }
               container tca-signal-output-power-high {
                 description "Signal output power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute signal output power high TCA in dBm";
                   type string;
                 }
                 leaf threshold-24hrs {
                   description "Threshold for 24 hour signal output power high TCA in dBm";
                   type string;
                 }
               }
               container tca-pump0-current-low {
                 description "Pump0 current low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump0 current low TCA in dBm";
                   type string;
                 }
                 leaf threshold-24hrs {
                   description "Threshold for 24 hour pump0 current low TCA in dBm";
                   type string;
                 }
               }
               container tca-pump0-current-high {
                 description "Pump0 current high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump0 current high TCA in dBm";
                   type string;
                 }
                 leaf threshold-24hrs {
                   description "Threshold for 24 hour pump0 current high TCA in dBm";
                   type string;
                 }
               }
               container tca-pump1-current-low {
                 description "Pump1 current low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump1 current low TCA in dBm";
                   type string;
                 }
                 leaf threshold-24hrs {
                   description "Threshold for 24 hour pump1 current low TCA in dBm";
                   type string;
                 }
               }
               container tca-pump1-current-high {
                 description "Pump1 current high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump1 current high TCA in dBm";
                   type string;
                 }
                 leaf threshold-24hrs {
                   description "Threshold for 24 hour pump1 current high TCA in dBm";
                   type string;
                 }
               }
               container tca-pump0-temperature-low {
                 description "Pump0 temperature low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump0 temperature low TCA in C";
                   type string;
                 }
                 leaf threshold-24hrs {
                   description "Threshold for 24 hour pump0 temperature low TCA in C";
                   type string;
                 }
               }
               container tca-pump0-temperature-high {
                 description "Pump0 temperature high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump0 temperature high TCA in C";
                   type string;
                 }
                 leaf threshold-24hrs {
                   description "Threshold for 24 hour pump0 temperature high TCA in C";
                   type string;
                 }
               }
               container tca-pump1-temperature-low {
                 description "Pump1 temperature low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump1 temperature low TCA in C";
                   type string;
                 }
                 leaf threshold-24hrs {
                   description "Threshold for 24 hour pump1 temperature low TCA in C";
                   type string;
                 }
               }
               container tca-pump1-temperature-high {
                 description "Pump1 temperature high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump1 temperature high TCA in C";
                   type string;
                 }
                 leaf threshold-24hrs {
                   description "Threshold for 24 hour pump1 temperature high TCA in C";
                   type string;
                 }
               }
             }
             container voa-b {
               description "Configure voa-b";
               uses apply-advanced;
               container tca-attenuation-low {
                 description "Attenuation low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute attenuation low TCA in dBm";
                   type string;
                 }
                 leaf threshold-24hrs {
                   description "Threshold for 24 hour attenuation low TCA in dBm";
                   type string;
                 }
               }
               container tca-attenuation-high {
                 description "Attenuation high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute attenuation high TCA in dBm";
                   type string;
                 }
                 leaf threshold-24hrs {
                   description "Threshold for 24 hour attenuation high TCA in dBm";
                   type string;
                 }
               }
             }
             container osc-b {
               description "Configure osc-b";
               uses apply-advanced;
               container osc-tx-power-high-tca {
                 description "OSC TX power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc tx power high TCA in dBm";
                   type string;
                 }
                 leaf threshold-24hrs {
                   description "Threshold for 24 hour osc tx power high TCA in dBm";
                   type string;
                 }
               }
               container osc-tx-power-low-tca {
                 description "OSC TX power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc tx power low TCA in dBm";
                   type string;
                 }
                 leaf threshold-24hrs {
                   description "Threshold for 24 hour osc tx power low TCA in dBm";
                   type string;
                 }
               }
               container osc-rx-power-high-tca {
                 description "OSC RX power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc rx power high TCA in dBm";
                   type string;
                 }
                 leaf threshold-24hrs {
                   description "Threshold for 24 hour osc rx power high TCA in dBm";
                   type string;
                 }
               }
               container osc-rx-power-low-tca {
                 description "OSC RX power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc rx power low TCA in dBm";
                   type string;
                 }
                 leaf threshold-24hrs {
                   description "Threshold for 24 hour osc rx power low TCA in dBm";
                   type string;
                 }
               }
               container osc-fiber-loss-high-tca {
                 description "OSC fiber loss high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc fiber loss high TCA in dBm";
                   type string;
                 }
                 leaf threshold-24hrs {
                   description "Threshold for 24 hour osc fiber loss high TCA in dBm";
                   type string;
                 }
               }
               container osc-fiber-loss-low-tca {
                 description "OSC fiber loss low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc fiber loss low TCA in dBm";
                   type string;
                 }
                 leaf threshold-24hrs {
                   description "Threshold for 24 hour osc fiber loss low TCA in dBm";
                   type string;
                 }
               }
             }
           }
         }
       }
     }
     leaf power {
       description "Power FPCs on or off";
       type enumeration {
         enum "off" {
           description "Do not provide power to FPCs";
         }
         enum "on" {
           description "Provide power to FPCs";
         }
       }
     }
     leaf no-vlan-tagging {
       description "Disable vlan support on FPC with default tpid 0x8100";
       type empty;
     }
     leaf temp-perf-throttle-disable {
       description "Disable temperature based PFE performance throttling";
       type empty;
     }
     container traffic-manager {
       description "Configure traffic-manager attributes";
       uses apply-advanced;
       leaf buffer-monitor-enable {
         description "Enable port buffer monitoring";
         type empty;
       }
       container queue-threshold {
         description "Set queue thresholds";
         uses apply-advanced;
         container fabric-queue {
           description "Set fabric queue thresholds";
           uses apply-advanced;
           list priority {
             key name;
             ordered-by user;
             description "Queue priority";
             leaf name {
               description "Priority level";
               type enumeration {
                 enum "low" {
                   description "Low fabric priority";
                 }
                 enum "high" {
                   description "High fabric priority";
                 }
               }
             }
             uses apply-advanced;
             leaf threshold {
               description "Threshold percentage to be set";
               type union {
                 type string {
                   pattern "<.*>|$.*";
                 }
                 type uint32 {
                   range "1 .. 100";
                 }
               }
             }
           }
         }
         container wan-queue {
           description "Set wan queue thresholds";
           uses apply-advanced;
           list priority {
             key name;
             ordered-by user;
             description "Queue Priority";
             leaf name {
               description "Priority level";
               type enumeration {
                 enum "low" {
                   description "Low wan priority";
                 }
                 enum "medium-low" {
                   description "Medium low wan priority";
                 }
                 enum "medium-high" {
                   description "Medium high wan priority";
                 }
                 enum "high" {
                   description "High wan priority";
                 }
               }
             }
             uses apply-advanced;
             leaf threshold {
               description "Threshold percentage to be set";
               type union {
                 type string {
                   pattern "<.*>|$.*";
                 }
                 type uint32 {
                   range "1 .. 100";
                 }
               }
             }
           }
         }
       }
       choice enhanced-priority-mode-choice {
         leaf enhanced-priority-mode {
           description "Enable enhanced priority mode";
           type empty;
         }
         leaf no-enhanced-priority-mode {
           description "Don't enable enhanced priority mode";
           type empty;
         }
       }
       leaf packet-timestamp {
         description "Configure collecting CoS last packet enqueued timestamp";
         default "disable";
         type enumeration {
           enum "enable" {
             description "Enables collecting CoS last packet enqueued timestamp";
           }
           enum "disable" {
             description "Disables collecting CoS last packet enqueued timestamp";
           }
         }
       }
     }
     leaf max-power {
       description "Max power to be consumed by MPC";
       type union {
         type uint32;
         type string {
           pattern "<.*>|$.*";
         }
       }
     }
     leaf route-localization {
       description "Route-Localization fib-remote or fib-local";
       type enumeration {
         enum "fib-remote" {
           description "Route-Localization fib-remote";
         }
         enum "fib-local" {
           description "Route-Localization fib-local";
         }
       }
     }
     leaf vpn-localization {
       description "VPN-localization core-facing-only  or core-facing-default";
       type enumeration {
         enum "vpn-core-facing-only" {
           description "VPN core-facing-fpc which has no vpn-label state";
         }
         enum "vpn-core-facing-default" {
           description "VPN core-facing-fpc which has all the state";
         }
       }
     }
     leaf power-budget-priority {
       description "FPC priority number";
       type union {
         type string {
           pattern "<.*>|$.*";
         }
         type uint32;
       }
     }
     choice mode {
       case case_1 {
         leaf disable-power {
           description "Do not provide power to the card";
           status deprecated;
           type empty;
         }
       }
       case case_2 {
         leaf allow-sram-parity-errors {
           description "Do not power cycle FPC when SRAM parity errors occur";
           type empty;
         }
       }
     }
     choice riot-mode {
       case case_1 {
         container performance-mode {
           presence "enable performance-mode";
           description "Enable performance mode, FPC will restart if mode changes from lite mode to performance mode";
           uses apply-advanced;
           leaf number-of-ucode-workers {
             description "Configure number of ucode worker cores, FPC will restart if there is a change in number of ucode worker cores";
             default "0";
             type union {
               type string {
                 pattern "<.*>|$.*";
               }
               type uint32 {
                 range "0 .. 100";
               }
             }
           }
         }
       }
       case case_2 {
         leaf lite-mode {
           description "Enable lite mode, FPC will restart if mode changes from performance mode to lite mode";
           type empty;
         }
       }
     }
     leaf services-offload {
       description "Enable services offload on fpc";
       status deprecated;
       type empty;
     }
     leaf cfp-to-et {
       description "Enable ET interface and remove CFP client";
       type empty;
     }
     leaf napt {
       description "Enable NAPT on PFE";
       type empty;
     }
     container lossless-flow-control {
       presence "enable lossless-flow-control";
       description "Lossless buffer config for Ethernet Mac pause";
       uses apply-advanced;
       choice enable_choice {
         case case_1 {
           leaf lossless-flow-control-enable {
             description "Enable Lossless buffer config for Ethernet Mac pause";
             type empty;
           }
         }
         case case_2 {
           leaf no-lossless-flow-control-enable {
             description "Disable Lossless buffer config for Ethernet Mac pause";
             type empty;
           }
         }
       }
     }
     leaf np-cache {
       description "Enable NP cache and services offload on fpc";
       status deprecated;
       type empty;
     }
     leaf np-cache-disable {
       description "Disable NP cache and services offload on fpc";
       type empty;
     }
     leaf offline {
       description "Keep FPC offline";
       type empty;
     }
     leaf offline-on-fabric-bandwidth-reduction {
       description "Bring FPC offline when running with reduced fabric bandwidth";
       type empty;
     }
     leaf autoheal {
       description "Restart FPC when CM connection with RE drops";
       type enumeration {
         enum "off" {
           description "Disable FPC restart on connection drop";
         }
         enum "on" {
           description "Enable FPC restart on connection drop";
         }
       }
     }
     leaf ir-mode {
       description "Configure IR or R mode for MPC4 and above cards";
       type enumeration {
         enum "IR" {
           description "Set IR mode";
         }
         enum "R" {
           description "Set R mode";
         }
       }
     }
     container no-loss {
       description "PFC lossless buffer configuratios";
       uses apply-advanced;
       container buffer {
         description "PFC lossless buffer";
         uses apply-advanced;
         leaf percentage {
           description "Configure buffer space for lossless traffic handling";
           units "percent";
           type union {
             type string {
               pattern "<.*>|$.*";
             }
             type uint32 {
               range "1 .. 100";
             }
           }
         }
       }
     }
     leaf license-mode {
       description "Configure license mode for PTX FPC3 and later cards";
       type enumeration {
         enum "r" {
           description "Set card to R mode";
         }
         enum "ir" {
           description "Set card to IR mode";
         }
         enum "lsr" {
           description "Set card to LSR mode";
         }
         enum "ip" {
           description "Set card to full IP mode";
         }
       }
     }
     container fabric {
       presence "enable fabric";
       uses apply-advanced;
       container loopback {
         presence "enable loopback";
         description "Set fpc fabric loopback mode";
         uses apply-advanced;
         leaf wan {
           description "Enable/Disable fpc fabric  wan loopback";
           type enumeration {
             enum "off" {
               description "Disable fpc fabric wan loopback";
             }
             enum "on" {
               description "Enable fpc fabric wan loopback";
             }
           }
         }
       }
       leaf blackhole-action {
         description "Action taken upon fabric plane blackhole involving the FPC";
         type enumeration {
           enum "log-only" {
             description "Log the detected blackhole condition";
           }
           enum "offline" {
             description "Offline the FPC";
           }
           enum "restart" {
             description "Restart the FPC";
           }
           enum "restart-then-offline" {
             description "Restart the FPC and offline in subsequent action. ";
           }
         }
       }
       container bandwidth-degradation {
         description "Take FPC recovery action when FPC running with reduced fabric bandwidth";
         uses apply-advanced;
         leaf percentage {
           description "The percentage of PFE bandwidth degradation to trigger action";
           type union {
             type string {
               pattern "<.*>|$.*";
             }
             type uint32 {
               range "1 .. 99";
             }
           }
         }
         leaf no-fabric-switchover {
           description "Do not perform switchover to spare CB";
           type empty;
         }
         leaf action {
           description "Type of action to trigger";
           type enumeration {
             enum "log-only" {
               description "Log the bandwidth degradation only";
             }
             enum "offline" {
               description "Offline the FPC, default action";
             }
             enum "restart" {
               description "Restart the FPC";
             }
             enum "restart-then-offline" {
               description "Restart the FPC and offline in subsequent action";
             }
           }
         }
       }
     }
     list port-mirror-instance {
       key name;
       ordered-by user;
       max-elements 2;
       leaf name {
         description "Associate a port mirroring instance with the FPC";
         type string {
           length "1 .. 64";
         }
       }
       uses apply-advanced;
     }
     list sampling-instance {
       key name;
       ordered-by user;
       max-elements 1;
       leaf name {
         description "Associate a sampling instance with the FPC";
         type string {
           length "1 .. 64";
         }
       }
       uses apply-advanced;
     }
     container inline-services {
       uses apply-advanced;
       leaf report-zero-oif-gw-on-discard {
         description "Jflow reports value zero in OIF and GW when traffic is not forwarded";
         type empty;
       }
       leaf flex-flow-sizing {
         description "No fixed size allocation of flow tables for proto families";
         type empty;
       }
       leaf use-extended-flow-memory {
         description "Use extended memory for flow records";
         type empty;
       }
       container flow-table-size {
         uses apply-advanced;
         leaf ipv4-flow-table-size {
           description "IPv4 flow table size in units of 256k";
           type union {
             type string {
               pattern "<.*>|$.*";
             }
             type uint32 {
               range "1 .. 245";
             }
           }
         }
         leaf ipv6-flow-table-size {
           description "IPv6 flow table size in units of 256k";
           type union {
             type string {
               pattern "<.*>|$.*";
             }
             type uint32 {
               range "1 .. 245";
             }
           }
         }
         leaf vpls-flow-table-size {
           description "VPLS flow table size in units of 256k";
           status deprecated;
           type union {
             type string {
               pattern "<.*>|$.*";
             }
             type uint32 {
               range "1 .. 245";
             }
           }
         }
         leaf bridge-flow-table-size {
           description "BRIDGE flow table size in units of 256k";
           type union {
             type string {
               pattern "<.*>|$.*";
             }
             type uint32 {
               range "1 .. 245";
             }
           }
         }
         leaf ipv6-extended-attrib {
           description "Enable extended flow attribute";
           type empty;
         }
         leaf mpls-flow-table-size {
           description "MPLS flow table size in units of 256k";
           type union {
             type string {
               pattern "<.*>|$.*";
             }
             type uint32 {
               range "1 .. 245";
             }
           }
         }
       }
       leaf no-inline-jflow {
         description "Disable Inline-Jflow on the SPC3 Linecard";
         type empty;
       }
     }
     container inline-video-monitoring {
       uses apply-advanced;
       leaf maximum-flows-count {
         description "Maximum number of inline video monitoring flows per PFE instance.";
         status deprecated;
         type union {
           type string {
             pattern "<.*>|$.*";
           }
           type uint32 {
             range "16 .. 8192";
           }
         }
       }
       leaf flow-table-size {
         description "Size of flow table size per PFE instance";
         type union {
           type string {
             pattern "<.*>|$.*";
           }
           type uint32 {
             range "16 .. 8192";
           }
         }
       }
     }
     container service-offload {
       presence "enable service-offload";
       description "Service-Offload Personality";
       uses apply-advanced;
       leaf flow-table-size {
         description "Size of service-offload flow table size units per ASIC, 1 unit = 256K";
         type union {
           type string {
             pattern "<.*>|$.*";
           }
           type uint32 {
             range "1 .. 48";
           }
         }
       }
     }
     container application-services {
       description "Application services configuration";
       uses apply-advanced;
       leaf package {
         description "Package selection";
         type string;
       }
     }
     container slamon-services {
       description "SLA monitoring services";
       uses apply-advanced;
       leaf rfc2544 {
         description "Enable sla monitoring services";
         type empty;
       }
     }
     leaf flexible-queuing-mode {
       description "Enable flexible queuing mode";
       type empty;
     }
     leaf loopback-device-count {
       description "Number of loopbacks";
       default "0";
       type union {
         type string {
           pattern "<.*>|$.*";
         }
         type uint32 {
           range "0 .. 4";
         }
       }
     }
     leaf interasic-linkerror-recovery-enable {
       description "Enable inter-asic link error recovery";
       type empty;
     }
     leaf number-of-ports {
       description "Number of physical ports to enable on FPC";
       type enumeration {
         enum "8" {
           description "Enable 8 ports";
         }
         enum "12" {
           description "Enable 12 ports";
         }
       }
     }
     list pfe-instance {
       key name;
       description "Packet forwarding engine parameters";
       uses chassis_pfe_type;
     }
     list pfe {
       key name;
       description "Packet forwarding engine parameters";
       uses chassis_pfe_type;
     }
     leaf service-package {
       description "Service package to be loaded on FPC";
       default "bundle-rfc2544";
       type enumeration {
         enum "bundle-rfc2544" {
           description "Service Package for RFC2544";
         }
         enum "bundle-nat-ipsec" {
           description "Service Package for NAT and IPSEC";
         }
         enum "bundle-ptp-enterprise-profile" {
           description "Service Package for PTP Enterprise Profile";
         }
       }
     }
     leaf max-queues {
       description "Maximum number of queues configurable on FPC";
       type enumeration {
         enum "8k" {
           description "8K maximum queues";
         }
         enum "16k" {
           description "16K maximum queues";
         }
         enum "32k" {
           description "32K maximum queues";
         }
         enum "48k" {
           description "48K maximum queues";
         }
         enum "64k" {
           description "64K maximum queues ";
         }
         enum "96k" {
           description "96K maximum queues ";
         }
         enum "128k" {
           description "128K maximum queues";
         }
         enum "192k" {
           description "192K maximum queues";
         }
         enum "256k" {
           description "256K maximum queues";
         }
         enum "384k" {
           description "256K maximum queues";
         }
         enum "512k" {
           description "512K maximum queues";
         }
         enum "768k" {
           description "768K maximum queues";
         }
         enum "1M" {
           description "1M maximum queues";
         }
         enum "1536k" {
           description "1536k maximum queues";
         }
         enum "2M" {
           description "2M maximum queues";
         }
       }
     }
     leaf bandwidth {
       description "Configure bandwidth of FPC";
       type enumeration {
         enum "1.6T" {
           description "Configure FPC bandwidth to 1.6T";
         }
       }
     }
     leaf pfe-bandwidth {
       description "Configure per PFE bandwidth";
       type enumeration {
         enum "240G" {
           description "Configure PFE bandwidth to 240G";
         }
         enum "300G" {
           description "Configure PFE bandwidth to 300G";
         }
         enum "400G" {
           description "Configure PFE bandwidth to 400G";
         }
       }
     }
     container error {
       description "Error level configuration for FPC";
       uses chassis_fpc_error_type;
     }
     list ether-type {
       key name;
       ordered-by user;
       description "Set Ethernet type on FPC";
       leaf name {
         description "TCAM slot";
         type union {
           type string {
             pattern "<.*>|$.*";
           }
           type uint8 {
             range "6 .. 27";
           }
         }
       }
       uses apply-advanced;
       leaf etype {
         description "Ether type";
         type string;
       }
     }
     list slc {
       key name;
       description "Sub-line card (SLC)";
       uses chassis_slc_type;
     }
     leaf low-power-mode {
       description "Configure FPC low power mode";
       type empty;
     }
     container relay {
       description "Alarm relays";
       uses chassis_alarm_relay_type;
     }
     leaf ignore-poe-feed {
       description "Ignore PoE feed";
       type empty;
     }
     container openflow {
       description "Openflow configuration";
       uses apply-advanced;
       leaf access-list-partition {
         description "Space reserved for openflow access-list rules";
         units "percents";
         type union {
           type string {
             pattern "<.*>|$.*";
           }
           type uint32 {
             range "0 .. 100";
           }
         }
       }
       leaf buffer-partition {
         description "Buffer space reserved for openflow traffic";
         units "percents";
         type union {
           type string {
             pattern "<.*>|$.*";
           }
           type uint32 {
             range "0 .. 100";
           }
         }
       }
     }
   }
   grouping chassis_fpc_error_type {
     description "Chassis Fpc Error level";
     uses apply-advanced;
     container fatal {
       description "FPC Fatal errors (default threshold = 1)";
       uses chassis_fpc_error_level_major_fatal;
     }
     container major {
       description "FPC Major Level errors (default threshold = 1)";
       uses chassis_fpc_error_level_major_fatal;
     }
     container minor {
       description "FPC Minor Level errors (default threshold = 10)";
       uses chassis_fpc_error_level_minor;
     }
     list override-cmerror {
       key name;
       ordered-by user;
       description "Error configuration override";
       max-elements 100;
       uses chassis_fru_cmerror_override_type;
     }
     container reset-pfe {
       description "FPC config reset-pfe options";
       presence "enable reset-pfe";
       uses chassis_fpc_error_config_reset_pfe_opt;
     }
     container scope {
       description "Error scope";
       uses chassis_fpc_scope_type;
     }
   }
   grouping chassis_fpc_error_config_reset_pfe_opt {
     uses apply-advanced;
     leaf retry-limit {
       description "Reset pfe retry limit";
       type union {
         type string {
           pattern "<.*>|$.*";
         }
         type uint32 {
           range "0 .. 3";
         }
       }
     }
     leaf pause-period {
       description "Reset pfe pause period in minutes";
       type union {
         type string {
           pattern "<.*>|$.*";
         }
         type uint32 {
           range "0 .. 10000000";
         }
       }
     }
     leaf pfe-disable-period {
       description "Reset pfe disable period in minutes";
       type union {
         type string {
           pattern "<.*>|$.*";
         }
         type uint32 {
           range "1 .. 10000000";
         }
       }
     }
   }
   grouping chassis_fpc_error_level_major_fatal {
     uses apply-advanced;
     leaf threshold {
       description "Error count at which to take the action";
       type union {
         type string {
           pattern "<.*>|$.*";
         }
         type uint32 {
           range "1 .. 1024";
         }
       }
     }
     list action {
       key name;
       ordered-by user;
       description "Configure the action for this level";
       leaf name {
         type enumeration {
           enum "reset" {
             description "Reset FPC";
           }
           enum "offline" {
             description "Offline FPC";
           }
           enum "alarm" {
             description "Raise FPC alarm";
           }
           enum "get-state" {
             description "Retreive FPC state for debugging";
           }
           enum "log" {
             description "Log occurence to system log file";
           }
           enum "disable-pfe" {
             description "Disable PFE interfaces on FPC";
           }
           enum "reset-pfe" {
             description "Reset PFE on FPC";
           }
           enum "offline-pic" {
             description "Offline PICs associated with PFE on FPC";
           }
           enum "trap" {
             description "Raise FPC trap";
           }
         }
       }
       uses apply-advanced;
     }
   }
   grouping chassis_fpc_error_level_minor {
     uses apply-advanced;
     leaf threshold {
       description "Error count at which to take the action";
       type union {
         type string {
           pattern "<.*>|$.*";
         }
         type uint32 {
           range "0 .. 1024";
         }
       }
     }
     list action {
       key name;
       ordered-by user;
       description "Configure the action for this level";
       leaf name {
         type enumeration {
           enum "reset" {
             description "Reset FPC";
           }
           enum "offline" {
             description "Offline FPC";
           }
           enum "alarm" {
             description "Raise FPC alarm";
           }
           enum "get-state" {
             description "Retreive FPC state for debugging";
           }
           enum "log" {
             description "Log occurence to system log file";
           }
           enum "disable-pfe" {
             description "Disable PFE interfaces on FPC";
           }
           enum "reset-pfe" {
             description "Reset PFE on FPC";
           }
           enum "offline-pic" {
             description "Offline PICs associated with PFE on FPC";
           }
           enum "trap" {
             description "Raise FPC trap";
           }
         }
       }
       uses apply-advanced;
     }
   }
   grouping chassis_fpc_scope_type {
     description "Chassis Fpc Error Scope";
     uses apply-advanced;
     container board {
       description "Board level scope";
       uses chassis_fpc_scope_category;
     }
     container pfe {
       description "Forwarding engine scope ";
       uses chassis_fpc_scope_category;
     }
     container switch {
       description "SIB scope ";
       uses chassis_sib_scope_category;
     }
   }
   grouping chassis_fpc_scope_category {
     description "Chassis Fpc Error Category";
     uses apply-advanced;
     container category {
       description "FPC error category";
       uses chassis_fpc_scope_category_type;
     }
   }
   grouping chassis_fpc_scope_category_type {
     description "Chassis Fpc Category level";
     uses apply-advanced;
     container functional {
       description "FPC functional category";
       uses chassis_fpc_scope_category_error_type;
     }
     container memory {
       description "FPC memory category";
       uses chassis_fpc_scope_category_error_type;
     }
     container io {
       description "FPC input-output category";
       uses chassis_fpc_scope_category_error_type;
     }
     container storage {
       description "FPC storage category";
       uses chassis_fpc_scope_category_error_type;
     }
     container switch {
       description "FPC switch category";
       uses chassis_fpc_scope_category_error_type;
     }
     container processing {
       description "FPC processing category";
       uses chassis_fpc_scope_category_error_type;
     }
   }
   grouping chassis_fpc_scope_category_error_type {
     description "Chassis Fpc Error level";
     uses apply-advanced;
     container fatal {
       description "FPC Fatal errors (default threshold = 1)";
       uses chassis_fpc_error_level_type;
     }
     container major {
       description "FPC Major Level errors (default threshold = 1)";
       uses chassis_fpc_error_level_type;
     }
     container minor {
       description "FPC Minor Level errors (default threshold = 10)";
       uses chassis_fpc_error_level_type;
     }
   }
   grouping chassis_fpc_error_level_type {
     uses apply-advanced;
     leaf threshold {
       description "Error count at which to take the action (0 - valid for minor only)";
       type union {
         type string {
           pattern "<.*>|$.*";
         }
         type uint32 {
           range "0 .. 4294967295";
         }
       }
     }
     list action {
       key name;
       ordered-by user;
       description "Configure the action for this level";
       leaf name {
         type enumeration {
           enum "reset" {
             description "Reset FPC";
           }
           enum "offline" {
             description "Offline FPC";
           }
           enum "alarm" {
             description "Raise FPC alarm";
           }
           enum "get-state" {
             description "Retrieve FPC state for debugging";
           }
           enum "log" {
             description "Log occurrence to system log file";
           }
           enum "disable-pfe" {
             description "Disable PFE interfaces on FPC";
           }
           enum "reset-pfe" {
             description "Reset PFE on FPC";
           }
           enum "offline-pic" {
             description "Offline PICs associated with PFE on FPC";
           }
           enum "trap" {
             description "Raise trap";
           }
         }
       }
       uses apply-advanced;
     }
   }
   grouping chassis_fpc_type_slot {
     leaf name {
       description "FPC slot number";
       type string;
     }
     uses apply-advanced;
     list pem {
       key name;
       ordered-by user;
       description "Power Supply Module slot";
       uses chassis_pem_type_slot;
     }
   }
   grouping chassis_fru_cmerror_override_type {
     description "Chassis Fpc Error override";
     leaf name {
       description "Error identifier";
       type string {
         length "1 .. 255";
       }
     }
     uses apply-advanced;
     leaf state {
       description "State";
       type enumeration {
         enum "disable" {
           description "Disable error";
         }
       }
     }
     leaf severity {
       description "Severity";
       type enumeration {
         enum "minor" {
           description "Minor Severity";
         }
         enum "major" {
           description "Major Severity";
         }
         enum "fatal" {
           description "Fatal Severity";
         }
       }
     }
     container pfe {
       presence "enable pfe";
       description "Apply to these pfe";
       uses apply-advanced;
       leaf all {
         description "Apply to all pfe";
         type empty;
       }
     }
   }
   grouping chassis_ftc_type {
     leaf name {
       description "Ftc slot number";
       type union {
         type string {
           pattern "<.*>|$.*";
         }
         type uint32;
       }
     }
     uses apply-advanced;
   }
   grouping chassis_junos_fru_error_type {
     description "Chassis Fru Error level";
     uses apply-advanced;
     container fatal {
       description "FRU Fatal errors (default threshold = 1)";
       uses chassis_fru_error_level_major_fatal;
     }
     container major {
       description "FRU Major errors (default threshold = 1)";
       uses chassis_fru_error_level_major_fatal;
     }
     container minor {
       description "FRU Minor errors (default threshold = 10)";
       uses chassis_fru_error_level_minor;
     }
     list override-cmerror {
       key name;
       ordered-by user;
       description "Error configuration override";
       max-elements 100;
       uses chassis_fru_cmerror_override_type;
     }
     container reset-pfe {
       description "FPC config reset-pfe options";
       presence "enable reset-pfe";
       uses chassis_fpc_error_config_reset_pfe_opt;
     }
     container scope {
       description "Error scope";
       uses chassis_fpc_scope_type;
     }
   }
   grouping chassis_fru_error_level_major_fatal {
     uses apply-advanced;
     leaf threshold {
       description "Error count at which to take the action";
       type union {
         type string {
           pattern "<.*>|$.*";
         }
         type uint32 {
           range "1 .. 1024";
         }
       }
     }
     list action {
       key name;
       ordered-by user;
       description "Configure the action for this level";
       leaf name {
         type enumeration {
           enum "reset" {
             description "Reset FRU";
           }
           enum "offline" {
             description "Offline FRU";
           }
           enum "alarm" {
             description "Raise FRU alarm";
           }
           enum "get-state" {
             description "Retrieve FRU state for debugging";
           }
           enum "log" {
             description "Log occurrence to system log file";
           }
           enum "disable-pfe" {
             description "Disable PFE interfaces on FPC";
           }
           enum "reset-pfe" {
             description "Reset PFE on FPC";
           }
           enum "offline-pic" {
             description "Offline PICs associated with PFE on FPC";
           }
           enum "trap" {
             description "Raise FPC trap";
           }
           enum "offline-pfe" {
             description "Offline PFE on FPC";
           }
         }
       }
       uses apply-advanced;
     }
   }
   grouping chassis_fru_error_level_minor {
     uses apply-advanced;
     leaf threshold {
       description "Error count at which to take the action";
       type union {
         type string {
           pattern "<.*>|$.*";
         }
         type uint32 {
           range "0 .. 1024";
         }
       }
     }
     list action {
       key name;
       ordered-by user;
       description "Configure the action for this level";
       leaf name {
         type enumeration {
           enum "reset" {
             description "Reset FRU";
           }
           enum "offline" {
             description "Offline FRU";
           }
           enum "alarm" {
             description "Raise FRU alarm";
           }
           enum "get-state" {
             description "Retrieve FRU state for debugging";
           }
           enum "log" {
             description "Log occurrence to system log file";
           }
           enum "disable-pfe" {
             description "Disable PFE interfaces on FPC";
           }
           enum "reset-pfe" {
             description "Reset PFE on FPC";
           }
           enum "offline-pic" {
             description "Offline PICs associated with PFE on FPC";
           }
           enum "trap" {
             description "Raise FPC trap";
           }
           enum "offline-pfe" {
             description "Offline PFE on FPC";
           }
         }
       }
       uses apply-advanced;
     }
   }
   grouping chassis_mic_type {
     leaf name {
       description "MIC slot number";
       type union {
         type string {
           pattern "<.*>|$.*";
         }
         type uint32;
       }
     }
     uses apply-advanced;
     leaf power {
       description "Power off MIC";
       type enumeration {
         enum "off" {
           description "Do not provide power to MIC";
         }
       }
     }
   }
   grouping chassis_pem_type {
     uses apply-advanced;
     leaf minimum {
       description "Minimum number of power supplies required for normal operation";
       type union {
         type string {
           pattern "<.*>|$.*";
         }
         type uint32;
       }
     }
     leaf feeds {
       description "Number of input feeds required";
       type union {
         type string {
           pattern "<.*>|$.*";
         }
         type uint32 {
           range "4 .. 6";
         }
       }
     }
     leaf input-current {
       description "Input current (Amps) in each feed ";
       default "60";
       type enumeration {
         enum "40" {
           description "40 Amps in each Feed";
         }
         enum "60" {
           description "60 Amps in each Feed";
         }
       }
     }
     container redundancy {
       description "PEM Source/Feed Redundancy configuration";
       uses apply-advanced;
       leaf source-redundancy {
         description "Toggle Source Redundancy for PEM";
         type empty;
       }
       container feed-redundancy {
         description "Toggle Feed Redundancy for a PEM slot";
         uses apply-advanced;
         list slot {
           key name;
           description "PEM Slot Number";
           leaf name {
             description "Select PEM slot";
             type union {
               type string {
                 pattern "<.*>|$.*";
               }
               type uint32;
             }
           }
           uses apply-advanced;
         }
       }
     }
   }
   grouping chassis_pem_type_slot {
     leaf name {
       description "PEM slot number";
       type string;
     }
     uses apply-advanced;
   }
   grouping chassis_pfe_type {
     description "PFE(Packet forwarding engine)";
     leaf name {
       description "PFE(Packet forwarding engine) identifier";
       type union {
         type string {
           pattern "<.*>|$.*";
         }
         type uint32;
       }
     }
     uses apply-advanced;
     container forwarding-packages {
       description "Associated forwarding package configuration";
       uses apply-advanced;
       container mobility {
         description "Mobility related PFE configuration";
         uses apply-advanced;
         choice package-type {
           case case_1 {
             leaf user-plane {
               description "User plane function";
               type empty;
             }
           }
         }
       }
     }
     container exception-reporting {
       description "Enable reporting of exceptions in the forwarding path";
       uses apply-advanced;
       list category {
         key name;
         ordered-by user;
         description "Exception category type";
         leaf name {
           type enumeration {
             enum "layer3" {
               description "Layer 3 exceptions";
             }
             enum "layer2" {
               description "Layer 2 exceptions";
             }
             enum "firewall" {
               description "Firewall exceptions";
             }
             enum "forwarding-state" {
               description "Forwarding state related exceptions";
             }
             enum "packet-errors" {
               description "Packet format error related exceptions";
             }
           }
         }
         uses apply-advanced;
         leaf inline-monitoring-instance {
           description "Inline monitoring to specified instance";
           type string {
             length "1 .. 64";
           }
         }
       }
     }
     leaf power {
       description "Power PFEs on or off";
       type enumeration {
         enum "off" {
           description "Power off PFE";
         }
         enum "on" {
           description "Power on PFE";
         }
       }
     }
     leaf temp-perf-throttle-disable {
       description "Disable temperature based PFE performance throttling";
       type empty;
     }
     leaf node {
       description "PFE(Packet forwarding engine) global identifier";
       type union {
         type string {
           pattern "<.*>|$.*";
         }
         type uint64 {
           range "1 .. 18446744073709551615";
         }
       }
     }
     leaf tunnel-services {
       description "Tunnel services configuration";
       type empty;
     }
     leaf temp-volt-reduction-disable {
       description "Disable temperature based PFE voltage reduction";
       type empty;
     }
     list core {
       key name;
       description "Core number";
       uses chassis_core_type;
     }
   }
   grouping chassis_core_type {
     leaf name {
       description "Core slot number";
       type union {
         type string {
           pattern "<.*>|$.*";
         }
         type uint32;
       }
     }
     uses apply-advanced;
     list channel {
       key name;
       description "Channel number";
       uses chassis_core_channel_type;
     }
   }
   grouping chassis_core_channel_type {
     leaf name {
       description "Channel number";
       type union {
         type string {
           pattern "<.*>|$.*";
         }
         type uint32;
       }
     }
     uses apply-advanced;
     container tunnel-services {
       description "Tunnel services";
       uses chassis_tunnel_services_type;
     }
   }
   grouping chassis_pic_type {
     leaf name {
       description "PIC slot number";
       type union {
         type string {
           pattern "<.*>|$.*";
         }
         type uint32;
       }
     }
     uses apply-advanced;
     leaf alternate-speed-set {
       description "PIC run time mode configuration";
       type enumeration {
         enum "6x100g-1x400g" {
           description "6x100G + 400G mode";
         }
       }
     }
     leaf pic-mode {
       description "PIC mode configuration";
       type enumeration {
         enum "1G" {
           description "1GE mode";
         }
         enum "10G" {
           description "10GE mode";
         }
         enum "25G" {
           description "25GE mode";
         }
         enum "40G" {
           description "40GE mode";
         }
         enum "50G" {
           description "50GE mode";
         }
         enum "100G" {
           description "100GE mode";
         }
         enum "400G" {
           description "400GE mode";
         }
         enum "1G10G" {
           description "1/10GE mode";
         }
         enum "A-1X400G-1X100G-4X50G" {
           description "Port0(400G) Port2(100G) Port6-9(50G)";
         }
         enum "B-1X400G-2X100G-2X50G" {
           description "Port0(400G) Port2,4(100G) Port6,8(50G)";
         }
         enum "C-6X100G-2X50G" {
           description "Port0-5(100G) Port10,12(50G)";
         }
         enum "D-3X100G-8X50G" {
           description "Port0-2(100G) Port6-13(50G)";
         }
         enum "E-4X100G-6X50G" {
           description "Port0-3(100G) Port7,9-13(50G)";
         }
       }
     }
     list port-profile {
       key name;
       ordered-by user;
       description "Port Profile configuration";
       max-elements 1;
       leaf name {
         description "Profile mode options";
         type enumeration {
           enum "A-1X400G-1X100G-4X50G" {
             description "Port0(400G/100G/40G) Port2(100G) Port6-9(50G/25G/10G/1G)";
           }
           enum "B-1X400G-2X100G-2X50G" {
             description "Port0(400G/100G/40G) Port2,4(100G) Port6,8(50G/25G/10G/1G)";
           }
           enum "C-6X100G-2X50G" {
             description "Port0-5(100G) Port10,12(50G/25G/10G/1G)";
           }
           enum "D-3X100G-8X50G" {
             description "Port0(100G/4x10G) Port1-2(100G) Port6-13(50G/25G/10G/1G)";
           }
           enum "E-4X100G-6X50G" {
             description "Port0-3(100G) Port7,9-13(50G/25G/10G/1G)";
           }
         }
       }
       uses apply-advanced;
       list port-num {
         key name;
         ordered-by user;
         description "Port number";
         leaf name {
           description "Refer 'show chassis pic port-profile' for valid port. Commit port-profile change first";
           type union {
             type string {
               pattern "<.*>|$.*";
             }
             type uint32 {
               range "0 .. 13";
             }
           }
         }
         uses apply-advanced;
         leaf speed {
           description "Port speed";
           type enumeration {
             enum "1g" {
               description "Refer 'show chassis pic port-profile' for valid speed. Commit port-profile change first";
             }
             enum "10g" {
             }
             enum "25g" {
             }
             enum "40g" {
             }
             enum "50g" {
             }
             enum "100g" {
             }
             enum "400g" {
             }
           }
         }
         leaf number-of-sub-ports {
           description "Number of subports per physical port";
           type union {
             type string {
               pattern "<.*>|$.*";
             }
             type uint32;
           }
         }
         leaf unused {
           description "Keep the port unused.";
           type empty;
         }
       }
     }
     list tunnel-port {
       key name;
       description "Tunnel port number";
       uses chassis_port_type;
     }
     container tunnel-services {
       presence "enable tunnel-services";
       description "Tunnel services configuration";
       uses apply-advanced;
       leaf bandwidth {
         description "Amount of bandwidth reserved for tunnel service";
         type string;
       }
       leaf interface-type {
         description "Create specific tunnel interface";
         type enumeration {
           enum "gr" {
             description "Create gr tunnel interface";
           }
         }
       }
       leaf tunnel-only {
         description "Support only tunnel traffic";
         type empty;
       }
       container priority {
         presence "enable priority";
         description "Specify bandwidths with priorities";
         uses apply-advanced;
         container high {
           presence "enable high";
           description "High Priority";
           uses apply-advanced;
           leaf bandwidth {
             description "Amount of bandwidth reserved for tunnel service";
             type string;
           }
         }
         container medium {
           presence "enable medium";
           description "Medium Priority";
           uses apply-advanced;
           leaf bandwidth {
             description "Amount of bandwidth reserved for tunnel service";
             type string;
           }
         }
         container low {
           presence "enable low";
           description "Low Priority";
           uses apply-advanced;
           leaf bandwidth {
             description "Amount of bandwidth reserved for tunnel service";
             type string;
           }
         }
       }
       leaf port {
         description "Front panel port number - ACX5048: [16-53], ACX5096: [64-95, 100-103]";
         type union {
           type uint32;
           type string {
             pattern "<.*>|$.*";
           }
         }
       }
       list tunnel-port {
         key name;
         ordered-by user;
         description "Tunnel port number";
         leaf name {
           description "Port number";
           type union {
             type string {
               pattern "<.*>|$.*";
             }
             type uint32;
           }
         }
         uses apply-advanced;
         leaf bandwidth {
           description "Amount of bandwidth reserved for tunnel service";
           type string;
         }
         leaf interface-type {
           description "Create specific tunnel interface";
           type enumeration {
             enum "gr" {
               description "Create gr tunnel interface at port level";
             }
           }
         }
       }
     }
     leaf interface-type {
       description "Interface prefix";
       type enumeration {
         enum "ge" {
           description "Prefix interfaces as ge";
         }
         enum "xe" {
           description "Prefix interfaces as xe";
         }
         enum "et" {
           description "Prefix interfaces as et";
         }
       }
     }
     container inline-services {
       presence "enable inline-services";
       description "Inline services configuration";
       uses apply-advanced;
       list service-port {
         key name;
         ordered-by user;
         description "Service port number";
         leaf name {
           description "Port number";
           type union {
             type string {
               pattern "<.*>|$.*";
             }
             type uint32;
           }
         }
         uses apply-advanced;
         leaf bandwidth {
           description "Amount of bandwidth reserved for inline service";
           type string;
         }
       }
       leaf bandwidth {
         description "Amount of bandwidth reserved for inline service";
         type string;
       }
       leaf fragmentation-mtu {
         description "Set the fragmentation MTU size";
         default "1500";
         type union {
           type string {
             pattern "<.*>|$.*";
           }
           type uint32 {
             range "250 .. 9000";
           }
         }
       }
       leaf reassembly-context-age {
         description "Set the re-assembly context age millisecond timeout";
         default "25";
         type union {
           type string {
             pattern "<.*>|$.*";
           }
           type uint32 {
             range "5 .. 80";
           }
         }
       }
       container service-plane-recovery {
         description "Service plane recovery configuration";
         uses apply-advanced;
         leaf disable {
           type empty;
         }
         leaf downtime-gap-seconds {
           description "Gap between successive downtime events for recovery";
           default "180";
           type union {
             type string {
               pattern "<.*>|$.*";
             }
             type uint32 {
               range "30 .. 86400";
             }
           }
         }
         leaf downtime-events {
           description "Number of downtime events after which recovery is disabled";
           default "3";
           type union {
             type string {
               pattern "<.*>|$.*";
             }
             type uint32 {
               range "1 .. 100";
             }
           }
         }
       }
     }
     choice adaptive-or-monitoring {
       case case_1 {
         container adaptive-services {
           description "Adaptive services configuration";
           uses apply-advanced;
           container service-package {
             description "AS PIC service package";
             uses apply-advanced;
             choice service-package-choice {
               case case_1 {
                 leaf layer-3 {
                   description "Layer 3 service package";
                   type empty;
                 }
               }
               case case_2 {
                 leaf layer-2 {
                   description "Layer 2 service package";
                   type empty;
                 }
               }
               case case_3 {
                 leaf layer-2-3 {
                   description "Combined Layer 2 and Layer 3 service package";
                   type empty;
                 }
               }
               case case_4 {
                 container extension-provider {
                   description "Extension provider package configuration";
                   uses apply-advanced;
                   leaf data-pollers {
                     description "Number of cpus dedicated to poll data packets";
                     default "0";
                     type union {
                       type string {
                         pattern "<.*>|$.*";
                       }
                       type uint32 {
                         range "0 .. 7";
                       }
                     }
                   }
                   container data-flow-affinity {
                     presence "enable data-flow-affinity";
                     description "Enable flow affinity on data cores";
                     uses apply-advanced;
                     leaf hash-key {
                       type enumeration {
                         enum "layer-3" {
                           description "Set layer-3 as hash key";
                         }
                         enum "layer-4" {
                           description "Set layer-4 as hash key (default)";
                         }
                       }
                     }
                   }
                   leaf session-offload {
                     description "Enable session offload";
                     type empty;
                   }
                   leaf no-default-packages {
                     description "Do not load default packages";
                     type empty;
                   }
                   list package {
                     key name;
                     ordered-by user;
                     description "Extension provider package to run on the PIC";
                     max-elements 42;
                     leaf name {
                       description "Name of package";
                       type string;
                     }
                     uses apply-advanced;
                   }
                   list syslog {
                     key name;
                     ordered-by user;
                     description "System logging facility";
                     leaf name {
                       description "Facility type";
                       type enumeration {
                         enum "external" {
                           description "Local external applications";
                         }
                         enum "pfe" {
                           description "Packet Forwarding Engine";
                         }
                         enum "daemon" {
                           description "Various system processes";
                         }
                         enum "kernel" {
                           description "Kernel";
                         }
                       }
                     }
                     uses apply-advanced;
                     choice level {
                       case case_1 {
                         leaf any {
                           description "All levels";
                           type empty;
                         }
                       }
                       case case_2 {
                         leaf emergency {
                           description "Panic conditions";
                           type empty;
                         }
                       }
                       case case_3 {
                         leaf alert {
                           description "Conditions that should be corrected immediately";
                           type empty;
                         }
                       }
                       case case_4 {
                         leaf critical {
                           description "Critical conditions";
                           type empty;
                         }
                       }
                       case case_5 {
                         leaf error {
                           description "Error conditions";
                           type empty;
                         }
                       }
                       case case_6 {
                         leaf warning {
                           description "Warning messages";
                           type empty;
                         }
                       }
                       case case_7 {
                         leaf notice {
                           description "Conditions that should be handled specially";
                           type empty;
                         }
                       }
                       case case_8 {
                         leaf info {
                           description "Informational messages";
                           type empty;
                         }
                       }
                       case case_9 {
                         leaf none {
                           description "No messages";
                           type empty;
                         }
                       }
                     }
                     leaf destination {
                       description "Sylog destination";
                       type enumeration {
                         enum "routing-engine" {
                           description "Forward log messages to RE";
                         }
                         enum "pic-console" {
                           description "Forward to PIC console";
                         }
                       }
                     }
                   }
                 }
               }
             }
           }
         }
       }
       case case_2 {
         container monitoring-services {
           description "Monitoring services configuration";
           uses apply-advanced;
           leaf application {
             description "Application mode";
             type enumeration {
               enum "dynamic-flow-capture" {
                 description "Dynamic flow capture mode";
               }
               enum "flow-collector" {
                 description "Flow collector mode";
               }
               enum "monitor" {
                 description "Monitor mode";
               }
             }
           }
         }
       }
     }
     leaf no-mcast-replication {
       description "No mcast replication";
       type empty;
     }
     container ggsn-services {
       description "GGSN services configuration";
       status deprecated;
       uses apply-advanced;
       leaf application {
         description "Application mode";
         type enumeration {
           enum "ggsn-data" {
             description "GGSN-U mode";
           }
           enum "ggsn-inspection" {
             description "GGSN-I mode";
           }
           enum "ggsn-tunnel" {
             description "GGSN-T mode";
           }
         }
       }
     }
     leaf framing {
       description "Framing mode";
       type enumeration {
         enum "sonet" {
           description "SONET mode";
         }
         enum "sdh" {
           description "SDH mode";
         }
         enum "t3" {
           description "T3 mode";
         }
         enum "e3" {
           description "E3 mode";
         }
         enum "t1" {
           description "T1 mode";
         }
         enum "e1" {
           description "E1 mode";
         }
         enum "lan" {
           description "LAN mode";
         }
       }
     }
     container synchronization {
       description "PIC synchronization source";
       uses apply-advanced;
       choice source {
         case case_1 {
           leaf port {
             description "Port Number";
             type union {
               type string {
                 pattern "<.*>|$.*";
               }
               type uint32 {
                 range "0 .. 11";
               }
             }
           }
         }
       }
     }
     container recovered-clock {
       description "Select recovered clock for this port";
       uses apply-advanced;
       leaf port {
         description "Port Number";
         type union {
           type string {
             pattern "<.*>|$.*";
           }
           type uint32 {
             range "0 .. 47";
           }
         }
       }
       leaf channel {
         description "Channel Number";
         type union {
           type string {
             pattern "<.*>|$.*";
           }
           type uint32 {
             range "0 .. 3";
           }
         }
       }
     }
     leaf vtmapping {
       description "Virtual tunnel mapping mode";
       type enumeration {
         enum "klm" {
           description "KLM mode";
         }
         enum "itu-t" {
           description "ITU-T mode";
         }
       }
     }
     leaf no-concatenate {
       description "Do not concatenate channels";
       type empty;
     }
     leaf no-multi-rate {
       description "Disable multi-rate mode";
       type empty;
     }
     leaf channelization {
       description "Enable Channelization";
       type empty;
     }
     leaf linerate-mode {
       description "Disable oversubscription. PIC operates in line rate mode";
       type empty;
     }
     leaf speed {
       description "Port speed";
       type enumeration {
         enum "1G" {
           description "1GE-Gigabit Ethernet";
         }
       }
     }
     leaf mixed-rate-mode {
       description "PIC operates in mixed-rate-mode. Speed and AE configurable for PIC Ports";
       type empty;
     }
     leaf no-pre-classifier {
       description "No pre-classification of packets";
       type empty;
     }
     leaf aggregate-ports {
       description "Aggregate multiple ports on a PIC as a single port";
       type empty;
     }
     leaf number-of-ports {
       description "Number of physical ports to enable on PIC";
       type union {
         type string {
           pattern "<.*>|$.*";
         }
         type uint32;
       }
     }
     leaf power {
       description "Power off PIC";
       type enumeration {
         enum "off" {
           description "Do not provide power to PIC";
         }
       }
     }
     leaf pic-type {
       description "OID of PIC type to be configured";
       type string {
       }
     }
     container aggregated-devices {
       description "Aggregated devices configuration";
       uses apply-advanced;
       container ima {
         description "Aggregated device options for Inverse Multiplexing for ATM";
         uses apply-advanced;
         leaf device-count {
           description "Number of IMA groups";
           type union {
             type string {
               pattern "<.*>|$.*";
             }
             type uint32 {
               range "1 .. 42";
             }
           }
         }
       }
     }
     leaf sparse-dlcis {
       description "Run in sparse data-link connection identifier mode";
       type empty;
     }
     leaf multi-link-layer-2-inline {
       description "Enable inline layer-2 services";
       type empty;
     }
     container q-pic-large-buffer {
       presence "enable q-pic-large-buffer";
       description "Run in large delay buffer mode";
       uses apply-advanced;
       choice buffer-type {
         case case_1 {
           leaf small-scale {
             description "Supports less number of interfaces";
             type empty;
           }
         }
         case case_2 {
           leaf large-scale {
             description "Supports large number of interfaces";
             type empty;
           }
         }
       }
     }
     container red-buffer-occupancy {
       description "Computation type for RED buffer occupancy";
       uses apply-advanced;
       container weighted-averaged {
         presence "enable weighted-averaged";
         description "Weighted-average computation";
         uses apply-advanced;
         leaf instant-usage-weight-exponent {
           description "Weight for instant buffer usage (negative exponent of 2)";
           type union {
             type uint8;
             type string {
               pattern "<.*>|$.*";
             }
           }
         }
       }
     }
     container traffic-manager {
       description "Configure traffic manager attributes";
       uses apply-advanced;
       leaf ingress-shaping-overhead {
         description "Number of CoS shaping overhead bytes in ingress";
         units "bytes";
         type union {
           type string {
             pattern "<.*>|$.*";
           }
           type int32 {
             range "-62 .. 192";
           }
         }
       }
       leaf egress-shaping-overhead {
         description "Number of CoS shaping overhead bytes in egress";
         units "bytes";
         type union {
           type string {
             pattern "<.*>|$.*";
           }
           type int32 {
             range "-62 .. 192";
           }
         }
       }
       leaf queue-buffer-size {
         description "Set the buffer size of output queue";
         type enumeration {
           enum "small" {
             description "Use small buffer size";
           }
         }
       }
       leaf mode {
         description "Configure traffic manager mode";
         type enumeration {
           enum "egress-only" {
             description "Egress traffic manager enabled, ingress traffic manager disabled";
           }
           enum "session-shaping" {
             description "Enable egress session shaping";
           }
           enum "ingress-and-egress" {
             description "Enable the ingress and egress traffic managers";
           }
         }
       }
     }
     container idle-cell-format {
       description "ATM idle cell configuration";
       uses apply-advanced;
       leaf itu-t {
         description "ITU-T idle cell header format";
         type empty;
       }
       leaf payload-pattern {
         description "Payload pattern byte (0x00-0xff)";
         type string;
       }
     }
     container atm-l2circuit-mode {
       description "Enable ATM Layer 2 circuit transport mode";
       uses apply-advanced;
       choice mode_choice {
         case case_1 {
           leaf aal5 {
             description "ATM Layer 2 circuit AAL5 mode";
             type empty;
           }
         }
         case case_2 {
           leaf cell {
             description "ATM Layer 2 circuit cell mode";
             type empty;
           }
         }
         case case_3 {
           container trunk {
             presence "enable trunk";
             description "Set ATM Layer 2 circuit trunk mode";
             uses apply-advanced;
             choice trunk-mode {
               case case_1 {
                 container uni {
                   presence "enable uni";
                   description "ATM Layer 2 circuit user-to-network interface trunk mode";
                   uses apply-advanced;
                 }
               }
               case case_2 {
                 container nni {
                   presence "enable nni";
                   description "ATM Layer 2 circuit network-to-network interface trunk mode";
                   uses apply-advanced;
                 }
               }
             }
           }
         }
       }
     }
     leaf atm-cell-relay-accumulation {
       description "Enable ATM cell-relay accumulation mode";
       type empty;
     }
     container services-offload {
       presence "enable services-offload";
       description "Enable services offload";
       uses apply-advanced;
       leaf per-session-statistics {
         description "Keep per session statistics in NP";
         type empty;
       }
       leaf low-latency {
         description "Bypass Traffic Management stage to achieve low latency";
         type empty;
       }
     }
     leaf mlfr-uni-nni-bundles {
       description "Number of multilink Frame Relay UNI NNI (FRF.16) bundles to allocate on PIC";
       type union {
         type string {
           pattern "<.*>|$.*";
         }
         type uint32 {
           range "1 .. 255";
         }
       }
     }
     leaf mlfr-uni-nni-bundles-inline {
       description "Number of inline multilink frame relay UNI NNI bundles";
       type union {
         type string {
           pattern "<.*>|$.*";
         }
         type uint32 {
           range "1 .. 255";
         }
       }
     }
     container ct3 {
       description "CT3 NxDS0 PIC configuration";
       uses apply-advanced;
       list port {
         key name;
         description "CT3 port";
         uses ct3_port_type;
       }
     }
     container ce1 {
       description "CE1 NxDS0 PIC configuration";
       uses apply-advanced;
       list e1 {
         key name;
         description "E1 link";
         uses ce1_channel_type;
       }
     }
     leaf max-queues-per-interface {
       description "Maximum number of queues per interface on QOS-capable PIC";
       type enumeration {
         enum "4" {
           description "Maximum 4 queues per interface";
         }
         enum "8" {
           description "Maximum 8 queues per interface";
         }
       }
     }
     container shdsl {
       description "SHDSL chassis configuration";
       uses apply-advanced;
       leaf pic-mode {
         description "PIC mode";
         default "2-port-atm";
         type enumeration {
           enum "1-port-atm" {
             description "Single port ATM, 8 wire mode";
           }
           enum "2-port-atm" {
             description "Two port ATM, 4 wire mode";
           }
           enum "4-port-atm" {
             description "Four port ATM, 2 wire mode";
           }
           enum "efm" {
             description "Single port EFM, 2 wire mode";
           }
         }
       }
     }
     container ethernet {
       description "J-series Ethernet PIM mode configuration";
       uses apply-advanced;
       leaf pic-mode {
         description "PIC mode";
         default "routing";
         type enumeration {
           enum "switching" {
             description "Switched mode of operation";
           }
           enum "routing" {
             description "Routing mode of operation";
           }
           enum "enhanced-switching" {
             description "Enhanced switching mode of operation";
           }
         }
       }
     }
     leaf tunnel-queuing {
       description "Enable queueing for GRE/IPIP tunnels";
       type empty;
     }
     list port-mirror-instance {
       key name;
       ordered-by user;
       max-elements 2;
       leaf name {
         description "Associate a port mirroring instance with the PIC";
         type string {
           length "1 .. 64";
         }
       }
       uses apply-advanced;
     }
     list port {
       key name;
       description "Port number";
       uses chassis_pic_port_framing;
     }
     list port-range {
       key "port-range-low port-range-high";
       ordered-by user;
       description "Physical ports to channelize";
       leaf port-range-low {
         description "Port range low number";
         type union {
           type string {
             pattern "<.*>|$.*";
           }
           type uint32;
         }
       }
       leaf port-range-high {
         description "Port range high number";
         type union {
           type string {
             pattern "<.*>|$.*";
           }
           type uint32;
         }
       }
       uses apply-advanced;
       leaf short-reach-mode {
         description "Short reach mode (For ports 0..47)";
         type enumeration {
           enum "disable" {
             description "Disable";
           }
           enum "enable" {
             description "Enable";
           }
         }
       }
       leaf channel-speed {
         description "Port channel speed";
         type enumeration {
           enum "10g" {
             description "Set the port speed to 10G. This will restart PFE";
           }
           enum "25g" {
             description "Set the port speed to 25G.";
           }
           enum "50g" {
             description "Set the port speed to 50G.";
           }
           enum "disable-auto-speed-detection" {
             description "Disables automatic speed detection";
           }
         }
       }
     }
     container fibre-channel {
       description "Fibre channel configuration option";
       uses chassis_fibre_channel_type;
     }
     container xe {
       description "Ports configurable in 10G mode";
       uses apply-advanced;
       list port {
         key port-number;
         ordered-by user;
         description "Attribute port";
         leaf port-number {
           description "Port number";
           type union {
             type string {
               pattern "<.*>|$.*";
             }
             type uint32;
           }
         }
         uses apply-advanced;
       }
       list port-range {
         key "port-range-low port-range-high";
         ordered-by user;
         description "Attribute port range";
         leaf port-range-low {
           description "Port range low number";
           type union {
             type string {
               pattern "<.*>|$.*";
             }
             type uint32;
           }
         }
         leaf port-range-high {
           description "Port range high number";
           type union {
             type string {
               pattern "<.*>|$.*";
             }
             type uint32;
           }
         }
         uses apply-advanced;
       }
     }
     container xle {
       description "Ports configurable in 40G mode ";
       uses apply-advanced;
       list port {
         key port-number;
         ordered-by user;
         description "Attribute port";
         leaf port-number {
           description "Port number";
           type union {
             type string {
               pattern "<.*>|$.*";
             }
             type uint32;
           }
         }
         uses apply-advanced;
       }
       list port-range {
         key "port-range-low port-range-high";
         ordered-by user;
         description "Attribute port range";
         leaf port-range-low {
           description "Port range low number";
           type union {
             type string {
               pattern "<.*>|$.*";
             }
             type uint32;
           }
         }
         leaf port-range-high {
           description "Port range high number";
           type union {
             type string {
               pattern "<.*>|$.*";
             }
             type uint32;
           }
         }
         uses apply-advanced;
       }
     }
     container fte {
       description "Ports configurable in 40G HIGIG mode";
       uses apply-advanced;
       list port {
         key port-number;
         ordered-by user;
         description "Attribute port";
         leaf port-number {
           description "Port number";
           type union {
             type string {
               pattern "<.*>|$.*";
             }
             type uint32;
           }
         }
         uses apply-advanced;
       }
       list port-range {
         key "port-range-low port-range-high";
         ordered-by user;
         description "Attribute port range";
         leaf port-range-low {
           description "Port range low number";
           type union {
             type string {
               pattern "<.*>|$.*";
             }
             type uint32;
           }
         }
         leaf port-range-high {
           description "Port range high number";
           type union {
             type string {
               pattern "<.*>|$.*";
             }
             type uint32;
           }
         }
         uses apply-advanced;
       }
     }
     list qsfp-port {
       key name;
       description "Qsfp port to configure";
       leaf name {
         description "Port-group 0:'0-3' 1:'4-7'";
         type union {
           type string {
             pattern "<.*>|$.*";
           }
           type uint32 {
             range "0 .. 1";
           }
         }
       }
       uses apply-advanced;
       leaf port-mode {
         description "Select mode for port-group";
         type enumeration {
           enum "40g" {
             description "40G mode";
           }
           enum "10g" {
             description "10G mode";
           }
         }
       }
     }
     container sfpplus {
       description "Sfpplus configuration option";
       uses apply-advanced;
       leaf pic-mode {
         description "PIC mode";
         type enumeration {
           enum "1g" {
             description "1G SFP mode";
           }
           enum "10g" {
             description "10G SFP+ mode";
           }
         }
       }
     }
     container hash-key {
       description "Select data used in the hash key";
       uses apply-advanced;
       container family {
         description "Protocol family";
         uses apply-advanced;
         container inet {
           description "IPv4 protocol family";
           uses apply-advanced;
           container layer-3 {
             presence "enable layer-3";
             description "Include Layer 3 (IP) data in the hash key";
             uses apply-advanced;
             leaf destination-address {
               description "Include IP destination address in the hash key";
               type empty;
             }
           }
           container layer-4 {
             presence "enable layer-4";
             description "Include Layer 4 (TCP or UDP) data in the hash key";
             uses apply-advanced;
           }
           container symmetric-hash {
             presence "enable symmetric-hash";
             description "Create symmetric hash-key with source & dest ports";
             uses apply-advanced;
             leaf complement {
               description "Create complement of symmetric hash-key";
               type empty;
             }
           }
         }
         container multiservice {
           description "Multiservice protocol family";
           uses apply-advanced;
           leaf source-mac {
             description "Include source MAC address in hash key";
             type empty;
           }
           leaf destination-mac {
             description "Include destination MAC address in hash key";
             type empty;
           }
           container payload {
             description "Include payload data in the hash key";
             uses apply-advanced;
             container ip {
               description "Include IPv4 payload data in the hash key";
               uses apply-advanced;
               container layer-3 {
                 presence "enable layer-3";
                 description "Include layer-3 ip info for VPLS/Bridge";
                 uses apply-advanced;
                 choice layer-3-options {
                   case case_1 {
                     leaf source-ip-only {
                       description "Include source IP only in hash-key";
                       type empty;
                     }
                   }
                   case case_2 {
                     leaf destination-ip-only {
                       description "Include desintation IP only in hash-key";
                       type empty;
                     }
                   }
                 }
               }
               leaf layer-4 {
                 description "Include layer-4 IP information for VPLS/Bridge";
                 type empty;
               }
             }
           }
           container symmetric-hash {
             presence "enable symmetric-hash";
             description "Create a/symmetric hash-key with any attributes";
             uses apply-advanced;
             leaf complement {
               description "Create complement of symmetric hash-key";
               type empty;
             }
           }
         }
       }
     }
     leaf ingress-policer-overhead {
       description "Number of policer overhead bytes in ingress";
       units "bytes";
       type union {
         type string {
           pattern "<.*>|$.*";
         }
         type uint32 {
           range "0 .. 255";
         }
       }
     }
     leaf egress-policer-overhead {
       description "Number of policer overhead bytes in egress";
       units "bytes";
       type union {
         type string {
           pattern "<.*>|$.*";
         }
         type uint32 {
           range "0 .. 255";
         }
       }
     }
     leaf account-layer2-overhead {
       description "Account Layer2 overhead in egress and ingress IFD/IFL stats";
       type empty;
     }
     container forwarding-mode {
       description "Set 100GE PIC packet distribution mode";
       uses apply-advanced;
       choice cap-fpga-packet-distribution-mode {
         case case_1 {
           leaf sa-multicast {
             description "Used for Juniper CGE to Juniper 100GE PIC back to back connection";
             type empty;
           }
         }
         case case_2 {
           container vlan-steering {
             presence "enable vlan-steering";
             description "Steer packet by VLAN id, interoperate with other vendors";
             uses apply-advanced;
             leaf vlan-rule {
               description "Set 100GE PIC forwarding VLAN rule";
               type enumeration {
                 enum "odd-even" {
                   description "Even number VLAN id processed by PFE0; odd number by PFE1";
                 }
                 enum "high-low" {
                   description "VLAN 1~2047 processed by PFE0; others by PFE1";
                 }
               }
             }
           }
         }
       }
     }
     leaf subscriber-aware-services {
       description "Enable subscriber aware services";
       type empty;
     }
     leaf ptp-mode {
       description "Set hardware to run PTP BC applications.";
       type empty;
     }
     leaf cpu-port-access {
       description "Configure MUX to select cpu-port";
       type empty;
     }
     list port-group {
       key name;
       description "Port group number";
       leaf name {
         description "Port group number";
         type union {
           type string {
             pattern "<.*>|$.*";
           }
           type uint32 {
             range "0 .. 3";
           }
         }
       }
       uses apply-advanced;
       leaf speed-group {
         description "Specify speed group";
         type enumeration {
           enum "high" {
             description "High speed group";
           }
           enum "low" {
             description "Low speed group";
           }
           enum "10g" {
             description "Supporting 10G/40G/4x10G with common speeds";
           }
         }
       }
     }
   }
   grouping ce1_channel_type {
     leaf name {
       description "E1 link number";
       type union {
         type string {
           pattern "<.*>|$.*";
         }
         type uint32 {
           range "0 .. 9";
         }
       }
     }
     uses apply-advanced;
     list channel-group {
       key name;
       description "Define channel group";
       leaf name {
         description "Channel group number";
         type union {
           type string {
             pattern "<.*>|$.*";
           }
           type uint32 {
             range "0 .. 23";
           }
         }
       }
       leaf timeslots {
         description "DS0 timeslots (1..31); for example, 1-3,4,9,22-24 (no spaces)";
         type string;
       }
     }
   }
   grouping chassis_fibre_channel_type {
     description "Fibre channel configuration option";
     uses apply-advanced;
     list port {
       key name;
       ordered-by user;
       description "Fibre channel port";
       leaf name {
         description "Port number for fibre channel mode";
         type union {
           type string {
             pattern "<.*>|$.*";
           }
           type uint32 {
             range "0 .. 47";
           }
         }
       }
       uses apply-advanced;
     }
     list port-range {
       key "port-range-low port-range-high";
       ordered-by user;
       description "Fibre channel port range";
       leaf port-range-low {
         description "Port range low number";
         type union {
           type string {
             pattern "<.*>|$.*";
           }
           type uint32 {
             range "0 .. 47";
           }
         }
       }
       leaf port-range-high {
         description "Port range high number";
         type union {
           type string {
             pattern "<.*>|$.*";
           }
           type uint32 {
             range "0 .. 47";
           }
         }
       }
       uses apply-advanced;
     }
   }
   grouping chassis_pic_port_framing {
     leaf name {
       description "Port number";
       type union {
         type string {
           pattern "<.*>|$.*";
         }
         type uint32;
       }
     }
     uses apply-advanced;
     leaf short-reach-mode {
       description "Short reach mode (For ports 0...47)";
       type enumeration {
         enum "disable" {
           description "Disable";
         }
         enum "enable" {
           description "Enable";
         }
       }
     }
     leaf framing {
       description "Framing mode";
       type enumeration {
         enum "sonet" {
           description "SONET mode";
         }
         enum "sdh" {
           description "SDH mode";
         }
         enum "t3" {
           description "T3 mode";
         }
         enum "e3" {
           description "E3 mode";
         }
         enum "t1" {
           description "T1 mode";
         }
         enum "e1" {
           description "E1 mode";
         }
       }
     }
     leaf number-of-sub-ports {
       description "Number of subports per physical port";
       type union {
         type string {
           pattern "<.*>|$.*";
         }
         type uint32;
       }
     }
     leaf unused {
       description "Keep the port unused.";
       type empty;
     }
     leaf speed {
       description "Port speed";
       type enumeration {
         enum "oc3-stm1" {
           description "OC3 or STM1";
         }
         enum "oc12-stm4" {
           description "OC12 or STM4";
         }
         enum "oc48-stm16" {
           description "OC48 or STM16";
         }
         enum "1g" {
           description "1GE-Gigabit Ethernet";
         }
         enum "10g" {
           description "Sets the interface mode to 10Gbps";
         }
         enum "25g" {
           description "Sets the interface mode to 25Gbps";
         }
         enum "40g" {
           description "Sets the interface mode to 40Gbps";
         }
         enum "100g" {
           description "Sets the interface mode to 100Gbps";
         }
         enum "50g" {
           description "Sets the interface mode to 50Gbps";
         }
         enum "200g" {
           description "Sets the interface mode to 200 Gbps";
         }
         enum "400g" {
           description "Sets the interface mode to 400Gbps";
         }
       }
     }
     leaf channel-speed {
       description "Port channel speed";
       type enumeration {
         enum "10g" {
           description "Set the port speed to 10G. This will restart PFE on some platforms.";
         }
         enum "25g" {
           description "Set the port speed to 25G.";
         }
         enum "50g" {
           description "Set the port speed to 50G.";
         }
         enum "disable-auto-speed-detection" {
           description "Disables automatic speed detection";
         }
       }
     }
     container forwarding-mode {
       description "PIC packet distribution mode - Brooklyn interop mode";
       uses apply-advanced;
       leaf sa-multicast {
         description "SA multicast mode - interop with 100G Brooklyn PIC";
         type empty;
       }
     }
     leaf no-mcast-replication {
       description "No multicast replication";
       type empty;
     }
     container traffic-manager {
       description "Configure per port traffic manager mode";
       uses apply-advanced;
       leaf mode {
         description "Configure port traffic manager mode as ingress-and-egress";
         type enumeration {
           enum "ingress-and-egress" {
             description "Enable the ingress and egress traffic managers";
           }
         }
       }
     }
     leaf no-temperature-monitoring {
       description "Disable empolicy";
       type empty;
     }
     leaf xcvr-power-off {
       description "Shutdown transceiver power";
       type empty;
     }
   }
   grouping chassis_port_type {
     leaf name {
       description "Port number for tunnel services";
       type union {
         type string {
           pattern "<.*>|$.*";
         }
         type uint32 {
           range "0 .. 47";
         }
       }
     }
     uses apply-advanced;
     leaf tunnel-services {
       description "Tunnel services configuration";
       type empty;
     }
   }
   grouping chassis_power_off_ports_on_no_master_re_type {
     choice power-off-ports-on-no-master-re {
       case case_1 {
         leaf disable {
           description "Disable powering off ports if no master RE present";
           type empty;
         }
       }
       case case_2 {
         leaf enable {
           description "Enable Powering of ports if no master RE present";
           type empty;
         }
       }
     }
   }
   grouping chassis_redundancy_type {
     uses apply-advanced;
     list routing-engine {
       key name;
       description "Redundancy options for Routing Engines";
       uses chassis_rdd_re_type;
     }
     list ssb {
       key name;
       description "Redundancy options for System Switch Boards";
       uses chassis_rdd_id_type;
     }
     list cfeb {
       key name;
       description "Redundancy options for Compact Forwarding Engine Boards";
       uses chassis_rdd_cfeb_id_type;
     }
     list sfm {
       key name;
       description "Redundancy options for Switching and Forwarding Modules";
       uses chassis_rdd_sfm_id_type;
     }
     container failover {
       description "Failover to other Routing Engine";
       presence "enable failover";
       uses chassis_rdd_failover_type;
     }
     leaf keepalive-time {
       description "Time before Routing Engine failover";
       units "seconds";
       type union {
         type string {
           pattern "<.*>|$.*";
         }
         type uint32 {
           range "2 .. 10000";
         }
       }
     }
     leaf mastership-refresh-timeout {
       description "Mastership refresh timeout";
       units "seconds";
       type union {
         type string {
           pattern "<.*>|$.*";
         }
         type uint32 {
           range "9 .. 30";
         }
       }
     }
     container graceful-switchover {
       description "Enable graceful switchover on supported hardware";
       presence "enable graceful-switchover";
       uses chassis_non_stop_forwarding_type;
     }
     leaf no-graceful-switchover {
       description "Disable graceful switchover on supported hardware";
       type empty;
     }
     container feb {
       description "Forwarding Engine Board redundancy configuration";
       uses apply-advanced;
       list redundancy-group {
         key name;
         leaf name {
           description "Name of FEB redundancy group";
           type string;
         }
         uses apply-advanced;
         leaf description {
           description "Text description of FEB redundancy group";
           type string;
         }
         list feb {
           key name;
           description "Redundancy settings for a Forwarding Engine Board";
           leaf name {
             description "Slot number";
             type union {
               type string {
                 pattern "<.*>|$.*";
               }
               type uint32;
             }
           }
           uses apply-advanced;
           choice redundancy-option {
             case case_1 {
               leaf primary {
                 description "FEB is default master in the redundancy group";
                 type empty;
               }
             }
             case case_2 {
               leaf backup {
                 description "FEB is backup in the redundancy group";
                 type empty;
               }
             }
           }
         }
         leaf no-auto-failover {
           description "Disable automatic FEB failover";
           type empty;
         }
       }
     }
   }
   grouping chassis_non_stop_forwarding_type {
     uses apply-advanced;
     container traceoptions {
       description "Graceful switchover trace options";
       status deprecated;
       uses apply-advanced;
       list flag {
         key name;
         ordered-by user;
         description "Tracing parameters";
         leaf name {
           type enumeration {
             enum "update" {
               description "Trace state updates";
             }
             enum "all" {
               description "Trace everything";
             }
           }
         }
       }
     }
   }
   grouping chassis_rdd_cfeb_id_type {
     leaf name {
       description "CFEB slot number";
       type union {
         type string {
           pattern "<.*>|$.*";
         }
         type uint32 {
           range "0 .. 1";
         }
       }
     }
     choice priority {
       case case_1 {
         leaf always {
           description "Sole device";
           type empty;
         }
       }
       case case_2 {
         leaf preferred {
           description "Preferred device";
           type empty;
         }
       }
     }
   }
   grouping chassis_rdd_failover_type {
     uses apply-advanced;
     container category {
       description "Failover category";
       presence "enable category";
       uses chassis_rdd_fail_cat_type;
     }
     leaf on-loss-of-keepalives {
       description "Failover on loss of keepalives";
       type empty;
     }
     leaf on-re-to-fpc-stale {
       description "Failover on loss of communication between the re and fpc";
       type empty;
     }
     leaf on-disk-failure {
       description "Failover on disk failure";
       type empty;
     }
     leaf not-on-disk-underperform {
       description "Prevent gstatd from initiating failovers in response to slow disks";
       type empty;
     }
     leaf disk-read-threshold {
       description "Read threshold (ms) on disk underperform monitoring";
       type union {
         type string {
           pattern "<.*>|$.*";
         }
         type uint32 {
           range "1000 .. 10000";
         }
       }
     }
     leaf disk-write-threshold {
       description "Write threshold (ms) on disk underperform monitoring";
       type union {
         type string {
           pattern "<.*>|$.*";
         }
         type uint32 {
           range "1000 .. 10000";
         }
       }
     }
     leaf on-loss-of-vm-host-connection {
       description "Failover on loss of vm host connection";
       type empty;
     }
     leaf on-mcontrol-slip {
       description "Failover on mastership control thread slip";
       type empty;
     }
   }
   grouping chassis_rdd_fail_cat_type {
     uses apply-advanced;
     container component-failure {
       description "Failover due to component failure";
       presence "enable component-failure";
       uses chassis_rdd_fail_cat_sev_type;
     }
     container software-failure {
       description "Failover due to software failure";
       presence "enable software-failure";
       uses chassis_rdd_fail_cat_sev_type;
     }
     container power-failure {
       description "Failover due to power failure";
       presence "enable power-failure";
       uses chassis_rdd_fail_cat_sev_type;
     }
     container clock-failure {
       description "Failover due to clock failure";
       presence "enable clock-failure";
       uses chassis_rdd_fail_cat_sev_type;
     }
     container link-failure {
       description "Failover due to link failure";
       presence "enable link-failure";
       uses chassis_rdd_fail_cat_sev_type;
     }
     container degraded-health {
       description "Failover due to degraded health";
       presence "enable degraded-health";
       uses chassis_rdd_fail_cat_sev_type;
     }
   }
   grouping chassis_rdd_fail_cat_sev_type {
     uses apply-advanced;
     container critical {
       description "Critical severity";
       presence "enable critical";
       uses chassis_rdd_fail_cat_sev_act_type;
     }
     container important {
       description "Important severity";
       presence "enable important";
       uses chassis_rdd_fail_cat_sev_act_type;
     }
   }
   grouping chassis_rdd_fail_cat_sev_act_type {
     uses apply-advanced;
     leaf disable {
       description "Disable action";
       type empty;
     }
   }
   grouping chassis_rdd_id_type {
     leaf name {
       description "SSB slot number";
       type union {
         type string {
           pattern "<.*>|$.*";
         }
         type uint32 {
           range "0 .. 1";
         }
       }
     }
     choice priority {
       case case_1 {
         leaf always {
           description "Sole device";
           type empty;
         }
       }
       case case_2 {
         leaf preferred {
           description "Preferred device";
           type empty;
         }
       }
     }
   }
   grouping chassis_rdd_re_type {
     leaf name {
       description "Routing Engine slot number";
       type union {
         type string {
           pattern "<.*>|$.*";
         }
         type uint32 {
           range "0 .. 1";
         }
       }
     }
     choice priority {
       case case_1 {
         leaf master {
           description "Master Routing Engine";
           type empty;
         }
       }
       case case_2 {
         leaf backup {
           description "Backup Routing Engine";
           type empty;
         }
       }
       case case_3 {
         leaf disabled {
           description "Routing Engine disabled";
           type empty;
         }
       }
     }
   }
   grouping chassis_rdd_sfm_id_type {
     leaf name {
       description "SFM slot number";
       type union {
         type string {
           pattern "<.*>|$.*";
         }
         type uint32;
       }
     }
     choice priority {
       case case_1 {
         leaf always {
           description "Sole device";
           type empty;
         }
       }
       case case_2 {
         leaf preferred {
           description "Preferred device";
           type empty;
         }
       }
     }
   }
   grouping chassis_routing_engine_type {
     uses apply-advanced;
     container on-disk-failure {
       description "Action to take when Routing Engine disk fails";
       uses chassis_re_on_disk_failure;
     }
     container control-interface {
       presence "enable control-interface";
       description "Configure recovery method and pause frame for control interface";
       uses apply-advanced;
       leaf recovery-method {
         description "Select the recovery method";
         type enumeration {
           enum "disable-recovery" {
             description "Don't enable recovery";
           }
           enum "socket" {
             description "Recovery by using socket";
           }
           enum "counter" {
             description "Recovery by using BCM-Counters";
           }
         }
       }
       leaf pause-frame {
         description "Enable or disable Pause frame generation";
         type empty;
       }
     }
     container bios {
       description "Routing Engine BIOS";
       uses apply-advanced;
       leaf no-auto-upgrade {
         description "Disable routing-engine BIOS auto-upgrade";
         type empty;
       }
       leaf uninterrupt {
         description "Set routing-engine BIOS uninterruptable";
         type empty;
       }
     }
     container disk {
       description "Action to take for Routing Engine disk";
       uses apply-advanced;
       leaf write-threshold-rate {
         description "Write threshold rate";
         default "4";
         units "MBPS";
         type union {
           type string {
             pattern "<.*>|$.*";
           }
           type uint32 {
             range "1 .. 20";
           }
         }
       }
       leaf write-threshold-duration {
         description "Write threshold duration";
         default "1000";
         units "seconds";
         type union {
           type string {
             pattern "<.*>|$.*";
           }
           type uint32 {
             range "300 .. 2592000";
           }
         }
       }
       leaf smart-check {
         description "Enable smart check command to disk";
         type empty;
       }
       list ssd-series {
         key name;
         ordered-by user;
         description "Specify the ssd vendor series";
         leaf name {
           description "SSD series name";
           type string {
             length "1 .. 40";
           }
         }
         uses apply-advanced;
         list id {
           key name;
           ordered-by user;
           description "Attribute ids to monitor of this series type";
           max-elements 30;
           leaf name {
             description "SSD smart attribute id";
             type union {
               type string {
                 pattern "<.*>|$.*";
               }
               type uint32 {
                 range "1 .. 255";
               }
             }
           }
           uses apply-advanced;
           leaf id-threshold {
             description "SSD smart attribute threshold";
             type union {
               type string {
                 pattern "<.*>|$.*";
               }
               type uint32 {
                 range "1 .. 4294967295";
               }
             }
           }
           leaf id-value {
             description "SSD attribute value";
             type enumeration {
               enum "raw" {
                 description "Raw value to be used for this smart id";
               }
               enum "norm" {
                 description "Normalised value to be used for this smart id";
               }
             }
           }
           leaf id-flag {
             description "SSD attribute flag";
             type enumeration {
               enum "low" {
                 description "Check if value is less than smart threshold";
               }
               enum "high" {
                 description "Check if value is greater than smart threshold";
               }
             }
           }
         }
       }
     }
     container usb-wwan {
       description "Enable WWAN (3G) access on the USB port";
       uses apply-advanced;
       leaf port {
         description "Select the port";
         type enumeration {
           enum "0" {
             description "Select port 0 to enable WWAN access";
           }
           enum "1" {
             description "Select port 1 to enable WWAN access";
           }
         }
       }
     }
   }
   grouping chassis_re_on_disk_failure {
     choice reboot_or_halt {
       case case_1 {
         leaf reboot {
           description "Reboot on disk failure";
           status deprecated;
           type empty;
         }
       }
       case case_2 {
         leaf disk-failure-action {
           type enumeration {
             enum "reboot" {
               description "Reboot on disk failure";
             }
             enum "halt" {
               description "Halt on disk failure";
             }
           }
         }
       }
     }
     leaf failover {
       description "Redundancy group 0 failover on disk failure";
       type empty;
     }
   }
   grouping chassis_sfb_type {
     leaf name {
       description "SFB slot number";
       type union {
         type string {
           pattern "<.*>|$.*";
         }
         type uint32;
       }
     }
     uses apply-advanced;
     leaf offline {
       description "Keep SFB offline";
       type empty;
     }
   }
   grouping chassis_sfm_type {
     leaf name {
       description "SFM slot number";
       type union {
         type string {
           pattern "<.*>|$.*";
         }
         type uint32;
       }
     }
     uses apply-advanced;
     choice cache {
     }
     leaf power {
       description "Power SFMs on or off";
       type enumeration {
         enum "off" {
           description "Do not provide power to SFMs";
         }
         enum "on" {
           description "Provide power to SFMs";
         }
       }
     }
     choice mode {
       case case_1 {
         leaf disable-power {
           description "Do not enable power to the card";
           status deprecated;
           type empty;
         }
       }
     }
   }
   grouping chassis_sib_scope_category {
     description "Chassis SIB Error Category";
     uses apply-advanced;
     container category {
       description "SIB error category";
       uses chassis_sib_scope_category_type;
     }
   }
   grouping chassis_sib_scope_category_type {
     description "Chassis SIB Category level";
     uses apply-advanced;
     container functional {
       description "SIB functional category";
       uses chassis_sib_scope_category_error_type;
     }
     container memory {
       description "SIB memory category";
       uses chassis_sib_scope_category_error_type;
     }
     container io {
       description "SIB input-output category";
       uses chassis_sib_scope_category_error_type;
     }
     container storage {
       description "SIB storage category";
       uses chassis_sib_scope_category_error_type;
     }
     container switch {
       description "SIB switch category";
       uses chassis_sib_scope_category_error_type;
     }
     container processing {
       description "SIB processing category";
       uses chassis_sib_scope_category_error_type;
     }
   }
   grouping chassis_sib_scope_category_error_type {
     description "Chassis SIB Error level";
     uses apply-advanced;
     container fatal {
       description "SIB Fatal errors (default threshold = 1)";
       uses chassis_sib_error_level_type;
     }
     container major {
       description "SIB Major Level errors (default threshold = 1)";
       uses chassis_sib_error_level_type;
     }
     container minor {
       description "SIB Minor Level errors (default threshold = 10)";
       uses chassis_sib_error_level_type;
     }
   }
   grouping chassis_sib_error_level_type {
     uses apply-advanced;
     leaf threshold {
       description "Error count at which to take the action (0 - valid for minor only)";
       type union {
         type string {
           pattern "<.*>|$.*";
         }
         type uint32 {
           range "0 .. 1024";
         }
       }
     }
     list action {
       key name;
       ordered-by user;
       description "Configure the action for this level";
       leaf name {
         type enumeration {
           enum "reset" {
             description "Reset device";
           }
           enum "offline" {
             description "Offline device";
           }
           enum "alarm" {
             description "Raise chassis alarm";
           }
           enum "get-state" {
             description "Retreive device state for debugging";
           }
           enum "log" {
             description "Log occurence to system log file";
           }
           enum "trap" {
             description "Raise trap";
           }
         }
       }
       uses apply-advanced;
     }
   }
   grouping chassis_sib_type {
     uses apply-advanced;
     list slot {
       key name;
       description "SIB slot number";
       leaf name {
         description "SIB slot number";
         type union {
           type string {
             pattern "<.*>|$.*";
           }
           type uint32;
         }
       }
       uses apply-advanced;
       container error {
         description "Error level configuration for SIB";
         uses chassis_sib_error_type;
       }
       leaf power {
         description "Power SIBs on or off";
         type enumeration {
           enum "off" {
             description "Do not provide power to SIBs";
           }
           enum "on" {
             description "Provide power to SIBs";
           }
         }
       }
     }
     leaf minimum {
       description "Minimum number of Switch Interface Boards required for normal operation";
       type union {
         type string {
           pattern "<.*>|$.*";
         }
         type uint32 {
           range "2 .. 4";
         }
       }
     }
     container power-off {
       description "Power off the SIB slot";
       uses apply-advanced;
       list slot {
         key name;
         ordered-by user;
         description "SIB slot number to be powered off";
         leaf name {
           description "SIB slot number to be offlined";
           type union {
             type string {
               pattern "<.*>|$.*";
             }
             type uint32;
           }
         }
         uses apply-advanced;
       }
     }
   }
   grouping chassis_sib_error_type {
     description "Chassis SIB Error level";
     uses apply-advanced;
     container fatal {
       description "SIB Fatal errors (default threshold = 1)";
       uses chassis_sib_error_level_major_fatal;
     }
     container major {
       description "SIB Major Level errors (default threshold = 1)";
       uses chassis_sib_error_level_major_fatal;
     }
     container minor {
       description "SIB Minor Level errors (default threshold = 10)";
       uses chassis_sib_error_level_minor;
     }
     list override-cmerror {
       key name;
       ordered-by user;
       description "Error configuration override";
       max-elements 100;
       uses chassis_sib_cmerror_override_type;
     }
     container scope {
       description "Error scope";
       uses chassis_sib_scope_type;
     }
   }
   grouping chassis_sib_cmerror_override_type {
     description "Chassis SIB Error override";
     leaf name {
       description "Error identifier";
       type string {
         length "1 .. 255";
       }
     }
     uses apply-advanced;
     leaf state {
       description "State";
       type enumeration {
         enum "disable" {
           description "Disable error";
         }
       }
     }
     leaf severity {
       description "Severity";
       type enumeration {
         enum "minor" {
           description "Minor Severity";
         }
         enum "major" {
           description "Major Severity";
         }
         enum "fatal" {
           description "Fatal Severity";
         }
       }
     }
   }
   grouping chassis_sib_error_level_major_fatal {
     uses apply-advanced;
     leaf threshold {
       description "Error count at which to take the action";
       type union {
         type string {
           pattern "<.*>|$.*";
         }
         type uint32 {
           range "1 .. 1024";
         }
       }
     }
     list action {
       key name;
       ordered-by user;
       description "Configure the action for this level";
       leaf name {
         type enumeration {
           enum "reset" {
             description "Reset SIB";
           }
           enum "offline" {
             description "Offline SIB";
           }
           enum "alarm" {
             description "Raise SIB alarm";
           }
           enum "get-state" {
             description "Retreive SIB state for debugging";
           }
           enum "log" {
             description "Log occurence to system log file";
           }
           enum "trap" {
             description "Raise SIB trap";
           }
         }
       }
       uses apply-advanced;
     }
   }
   grouping chassis_sib_error_level_minor {
     uses apply-advanced;
     leaf threshold {
       description "Error count at which to take the action";
       type union {
         type string {
           pattern "<.*>|$.*";
         }
         type uint32 {
           range "0 .. 1024";
         }
       }
     }
     list action {
       key name;
       ordered-by user;
       description "Configure the action for this level";
       leaf name {
         type enumeration {
           enum "reset" {
             description "Reset SIB";
           }
           enum "offline" {
             description "Offline SIB";
           }
           enum "alarm" {
             description "Raise SIB alarm";
           }
           enum "get-state" {
             description "Retreive SIB state for debugging";
           }
           enum "log" {
             description "Log occurence to system log file";
           }
           enum "trap" {
             description "Raise SIB trap";
           }
         }
       }
       uses apply-advanced;
     }
   }
   grouping chassis_sib_scope_type {
     description "Chassis SIB Error Scope";
     uses apply-advanced;
     container board {
       description "Board level scope";
       uses chassis_sib_scope_category;
     }
     container switch {
       description "SIB scope ";
       uses chassis_sib_scope_category;
     }
   }
   grouping chassis_slc_type {
     leaf name {
       description "SLC id";
       type union {
         type string {
           pattern "<.*>|$.*";
         }
         type uint32 {
           range "1 .. 2";
         }
       }
     }
     uses apply-advanced;
     leaf power {
       description "Power SLCs on or off";
       type enumeration {
         enum "off" {
           description "Do not provide power to SLC";
         }
         enum "on" {
           description "Provide power to SLC";
         }
       }
     }
   }
   grouping chassis_tunnel_services_type {
     uses apply-advanced;
     leaf bandwidth {
       description "Bandwidth reserved for tunnel service";
       type string;
     }
     leaf multicast {
       description "Multicast tunnel";
       type empty;
     }
   }
   grouping chassisd-redundancy-group-type {
     uses apply-advanced;
     container interface-type {
       uses apply-advanced;
       container redundant-logical-tunnel {
         description "Redundant logical tunnel interface group";
         uses apply-advanced;
         leaf device-count {
           description "Number of devices";
           type union {
             type string {
               pattern "<.*>|$.*";
             }
             type uint32 {
               range "1 .. 255";
             }
           }
         }
       }
       container redundant-virtual-tunnel {
         description "Redundant virtual tunnel interface group";
         uses apply-advanced;
         leaf device-count {
           description "Number of devices";
           type union {
             type string {
               pattern "<.*>|$.*";
             }
             type uint32 {
               range "1 .. 16";
             }
           }
         }
       }
     }
   }
   grouping chassisd_agg_container_type {
     uses apply-advanced;
     leaf device-count {
       description "Number of container devices";
       type union {
         type string {
           pattern "<.*>|$.*";
         }
         type uint32 {
           range "1 .. 128";
         }
       }
     }
   }
   grouping chassisd_agg_enet_type {
     uses apply-advanced;
     leaf device-count {
       description "Number of aggregated Ethernet devices";
       type union {
         type string {
           pattern "<.*>|$.*";
         }
         type uint32;
       }
     }
     container lacp {
       description "Global Link Aggregation Control Protocol configuration";
       uses apply-advanced;
       leaf system-priority {
         description "Priority of the system (0 ... 65535)";
         type string;
       }
       container link-protection {
         presence "enable link-protection";
         uses apply-advanced;
         leaf non-revertive {
           description "Don't revert links when better priority link comes up";
           type empty;
         }
       }
     }
   }
   grouping chassisd_agg_pos_type {
     uses apply-advanced;
     leaf device-count {
       description "Number of aggregated SONET devices";
       type union {
         type string {
           pattern "<.*>|$.*";
         }
         type uint32 {
           range "1 .. 64";
         }
       }
     }
   }
   grouping chassisd_provider_instance_type {
     uses apply-advanced;
     leaf device-count {
       description "Number of provider instance port devices";
       type union {
         type string {
           pattern "<.*>|$.*";
         }
         type uint32 {
           range "1 .. 16";
         }
       }
     }
   }
   grouping ct3_port_type {
     leaf name {
       description "CT3  L2NG_PRODUCTSport number";
       type union {
         type string {
           pattern "<.*>|$.*";
         }
         type int32 {
           range "0 .. 1";
         }
       }
     }
     uses apply-advanced;
     list t1 {
       key name;
       description "T1 link";
       uses ct3_channel_type;
     }
   }
   grouping ct3_channel_type {
     leaf name {
       description "T1 link number";
       type union {
         type string {
           pattern "<.*>|$.*";
         }
         type int32 {
           range "0 .. 27";
         }
       }
     }
     uses apply-advanced;
     list channel-group {
       key name;
       description "Define channel group";
       leaf name {
         description "Channel group number";
         type union {
           type string {
             pattern "<.*>|$.*";
           }
           type uint32 {
             range "0 .. 7";
           }
         }
       }
       leaf timeslots {
         description "DS0 timeslots (1..24); for example, 1-3,4,9,22-24 (no spaces)";
         type string;
       }
     }
   }
   grouping ip-monitoring-address-type {
     description "Define IP address related parameters";
     leaf name {
       description "Define IPv4 address to be monitored";
       type jt:ipv4addr;
     }
     uses apply-advanced;
     leaf weight {
       description "Define weight for this IP address";
       type union {
         type string {
           pattern "<.*>|$.*";
         }
         type uint16 {
           range "0 .. 255";
         }
       }
     }
     list interface {
       key name;
       ordered-by user;
       description "Logical interface through which to monitor this IP address";
       max-elements 1;
       leaf name {
         description "Logical interface name";
         type union {
           type jt:interface-name;
           type string {
             pattern "<.*>|$.*";
           }
         }
       }
       uses apply-advanced;
       leaf secondary-ip-address {
         description "Define source address for monitoring packets on secondary link";
         type jt:ipv4addr;
       }
     }
   }
   grouping juniper-gnf {
     leaf name {
       description "GNF slot number";
       type union {
         type string {
           pattern "<.*>|$.*";
         }
         type uint32 {
           range "1 .. 10";
         }
       }
     }
     uses apply-advanced;
     leaf description {
       description "Description of guest network function";
       type string {
         length "1 .. 256";
       }
     }
     leaf control-plane-bandwidth-percent {
       description "Percentage of control plane bandwidth";
       units "percent";
       type union {
         type string {
           pattern "<.*>|$.*";
         }
         type uint32 {
           range "0 .. 100";
         }
       }
     }
     leaf-list fpcs {
       description "FPC associated with guest network function";
       type union {
         type string {
           pattern "<.*>|$.*";
         }
         type uint32;
       }
     }
     container fpc-slice {
       description "FPC sub-line cards (SLCs) associated with guest network function";
       uses apply-advanced;
       list fpc {
         key name;
         description "FPC resource parameters for SLC";
         leaf name {
           description "FPC slot";
           type union {
             type string {
               pattern "<.*>|$.*";
             }
             type uint32;
           }
         }
         uses apply-advanced;
         list slc {
           key name;
           description "Sub-line card configuration";
           leaf name {
             description "SLC id";
             type union {
               type string {
                 pattern "<.*>|$.*";
               }
               type uint32 {
                 range "1 .. 2";
               }
             }
           }
           uses apply-advanced;
           leaf-list pfe-id-list {
             description "List of pfe of FPC to be assigned to SLC";
             type string;
           }
           leaf cores {
             description "Number of cpu cores of FPC to be assigned to SLC (2, 4, 6, 8)";
             type union {
               type uint32;
               type string {
                 pattern "<.*>|$.*";
               }
             }
           }
           leaf dram {
             description "Amount of DRAM (in GB) of FPC to be assigned to SLC";
             type union {
               type string {
                 pattern "<.*>|$.*";
               }
               type uint32 {
                 range "5 .. 26";
               }
             }
           }
         }
       }
     }
     list abstract-interface {
       key name;
       uses abstract_interface_type;
     }
   }
   grouping abstract_interface_type {
     description "Abstract-interface";
     leaf name {
       description "Interface name of af";
       type string {
         length "1 .. 3";
       }
     }
     uses apply-advanced;
     leaf description {
       description "Description of AF interface";
       type string {
         length "1 .. 516";
       }
     }
     container peer-gnf {
       presence "enable peer-gnf";
       description "Peer gnf";
       leaf id {
         description "Peer-gnf id";
         type union {
           type string {
             pattern "<.*>|$.*";
           }
           type uint32 {
             range "1 .. 10";
           }
         }
       }
       leaf remote-af-name {
         description "Remote af interface name";
         type string {
           length "1 .. 3";
         }
       }
     }
     container collapsed-forward {
       presence "enable collapsed-forward";
       description "Enable/disable collapsed forwarding";
       choice cfwd_mode {
         case case_1 {
           leaf monitor {
             description "Monitor mode";
             type empty;
           }
         }
         case case_2 {
           leaf optimize {
             description "Optimize mode";
             type empty;
           }
         }
       }
     }
   }
   grouping juniper-protected-system-domain {
     description "Protected system domain configuration";
     leaf name {
       description "Name of protected system domain (psd[1-31], ex. psd2)";
       type string {
       }
     }
     uses apply-advanced;
     leaf description {
       description "Description of protected system domain";
       type string;
     }
     leaf-list fpcs {
       description "FPC associated with protected system domain";
       type union {
         type string {
           pattern "<.*>|$.*";
         }
         type uint32;
       }
     }
     list lcc {
       key name;
       leaf name {
         description "Specific LCC";
         type union {
           type string {
             pattern "<.*>|$.*";
           }
           type uint32;
         }
       }
       uses apply-advanced;
       leaf-list fpcs {
         description "FPC associated with protected system domain";
         type union {
           type string {
             pattern "<.*>|$.*";
           }
           type uint32;
         }
       }
     }
     leaf control-system-id {
       description "Control system identifier";
       type union {
         type string {
           pattern "<.*>|$.*";
         }
         type uint32 {
           range "1 .. 4";
         }
       }
     }
     leaf-list control-slot-numbers {
       ordered-by user;
       description "Slots associated with protected system domain";
       type union {
         type string {
           pattern "<.*>|$.*";
         }
         type uint32 {
           range "1 .. 12";
         }
       }
       max-elements 2;
     }
     leaf control-plane-bandwidth-percent {
       description "Percentage of control plane bandwidth";
       units "percent";
       type union {
         type string {
           pattern "<.*>|$.*";
         }
         type uint32 {
           range "0 .. 100";
         }
       }
     }
   }
   grouping juniper-protected-system-domain-traceoptions {
     description "Protected system domain traceoptions";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         units "bytes";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "configuration" {
             description "Trace configuration events";
           }
           enum "rtsock" {
             description "Trace rtsock messages";
           }
           enum "ipc" {
             description "Trace IPC messages";
           }
           enum "init" {
             description "Trace intialization messages";
           }
           enum "psd" {
             description "Trace psd messages";
           }
           enum "all" {
             description "Trace everything";
           }
         }
       }
     }
   }
   grouping macro-data-type {
     leaf name {
       description "Keyword part of the keyword-value pair";
       type string;
     }
     leaf value {
       description "Value part of the keyword-value pair";
       type string;
     }
   }
   grouping redundancy-group-type {
     description "Redundancy-group provisioning";
     leaf name {
       description "Redundancy-group name";
       type string {
         length "2 .. 64";
       }
     }
     uses apply-advanced;
     leaf redundancy-group-id {
       description "Redundancy Group ID";
       type union {
         type string {
           pattern "<.*>|$.*";
         }
         type uint32 {
           range "1 .. 255";
         }
       }
     }
     container protocol {
       description "Redundancy-group Protocol";
       uses apply-advanced;
       container evpn {
         description "EVPN Redundancy Group";
         uses apply-advanced;
         leaf-list peer-ip {
           ordered-by user;
           description "Peer chassis IPs for EVPN Cluster";
           type jt:ipv4addr;
         }
         leaf local-ip {
           description "Local chassis IP for EVPN Cluster";
           type jt:ipv4addr;
         }
         leaf routing-instance {
           description "Name of routing instance for EVPN Cluster";
           type string;
         }
       }
     }
     list peer-chassis-id {
       key name;
       ordered-by user;
       description "Peer Chassis ID";
       leaf name {
         description "Peer chassis identifier";
         type union {
           type string {
             pattern "<.*>|$.*";
           }
           type uint32 {
             range "1 .. 4";
           }
         }
       }
       uses apply-advanced;
       leaf no-auto-vlan-provisioning {
         description "Disable auto VLAN provisioning on inter-chassis-link";
         type empty;
       }
       leaf inter-chassis-link {
         description "ICL interface name";
         type union {
           type jt:interface-device;
           type string {
             pattern "<.*>|$.*";
           }
         }
       }
       leaf no-auto-iccp-provisioning {
         description "Disable auto ICCP provisioning";
         type empty;
       }
       leaf session-establishment-hold-time {
         description "Time within which connection must succeed with this peer";
         units "seconds";
         type union {
           type string {
             pattern "<.*>|$.*";
           }
           type uint32 {
             range "45 .. 600";
           }
         }
       }
       container liveness-detection {
         presence "enable liveness-detection";
         description "Bidirectional Forwarding Detection options for the peer";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         leaf inline-disable {
           description "Disable inline mode for this BFD session";
           type empty;
         }
         leaf pdu-size {
           description "BFD transport protocol payload size";
           default "24";
           type union {
             type string {
               pattern "<.*>|$.*";
             }
             type uint32 {
               range "24 .. 16000";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
       }
       leaf authentication-key {
         description "MD5 authentication key";
         type string {
           length "1 .. 126";
         }
       }
       container traceoptions {
         description "Trace options for ICCP";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             units "bytes";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Trace flag information";
           leaf name {
             type enumeration {
               enum "error" {
                 description "Trace all errors";
               }
               enum "event" {
                 description "Trace all events";
               }
               enum "packet" {
                 description "Trace all packets";
               }
               enum "pipe" {
                 description "Trace pipe messages";
               }
               enum "pipe-detail" {
                 description "Trace pipe messages in detail";
               }
               enum "all" {
                 description "Trace everything";
               }
             }
           }
         }
       }
     }
     leaf-list satellite {
       ordered-by user;
       description "Satellite slot-id or range or all";
       type string {
         length "1 .. 100";
       }
     }
     leaf system-mac-address {
       description "System MAC address";
       type jt:mac-unicast;
     }
     list cluster {
       key name;
       description "Cluster member of redundancy-group";
       leaf name {
         description "Cluster name";
         type string;
       }
       uses apply-advanced;
     }
   }
   grouping satellite-bridge-filter {
     leaf name {
       description "Filter name";
       type string {
       }
     }
     uses apply-advanced;
     list term {
       key name;
       ordered-by user;
       description "Define a firewall term";
       leaf name {
         description "Term name";
         type string {
         }
       }
       uses apply-advanced;
       container from {
         description "Define match criteria";
         uses apply-advanced;
         list source-mac-address {
           key name;
           ordered-by user;
           description "Match MAC source address";
           uses firewall_mac_addr_object;
         }
         list destination-mac-address {
           key name;
           ordered-by user;
           description "Match MAC destination address";
           uses firewall_mac_addr_object;
         }
         list ip-source-address {
           key name;
           ordered-by user;
           description "Match IP source address";
           uses firewall_addr_object;
         }
         list ip-destination-address {
           key name;
           ordered-by user;
           description "Match IP destination address";
           uses firewall_addr_object;
         }
         choice ip-protocol_choice {
           case case_1 {
             leaf-list ip-protocol {
               ordered-by user;
               type string;
             }
           }
           case case_2 {
             leaf-list ip-protocol-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice user-vlan-id_choice {
           case case_1 {
             leaf-list user-vlan-id {
               ordered-by user;
               description "Range of values";
               type string;
             }
           }
           case case_2 {
             leaf-list user-vlan-id-except {
               ordered-by user;
               description "Range of values";
               type string;
             }
           }
         }
       }
       container then {
         description "Action to take if the 'from' condition is matched";
         uses apply-advanced;
         choice designation {
           case case_1 {
             leaf accept {
               description "Accept the packet";
               type empty;
             }
           }
           case case_2 {
             leaf discard {
               description "Discard the packets";
               type empty;
             }
           }
         }
         leaf next-hop-group {
           description "Use specified next-hop group";
           type string;
         }
       }
     }
   }
   grouping firewall_addr_object {
     leaf name {
       description "Prefix to match";
       type jt:ipv4prefix;
     }
     leaf except {
       description "Match address not in this prefix";
       type empty;
     }
   }
   grouping firewall_mac_addr_object {
     leaf name {
       description "MAC address to match";
       type jt:mac-addr-prefix;
     }
     leaf except {
       description "Match MAC address not in this range";
       type empty;
     }
   }
   grouping upgrade-group-fpcs {
     description "Upgrade group fpcs";
     leaf name {
       description "Member identifier";
       type union {
         type string {
           pattern "<.*>|$.*";
         }
         type int32;
       }
     }
     uses apply-advanced;
     leaf-list fpcs {
       description "FPCs to be upgraded as a group in this member";
       type union {
         type string {
           pattern "<.*>|$.*";
         }
         type uint32;
       }
     }
   }
   grouping upgrade-group-type {
     description "Upgrade group";
     leaf name {
       description "Upgrade group name";
       type string {
         length "2 .. 64";
       }
     }
     uses apply-advanced;
     leaf-list satellite {
       ordered-by user;
       description "Satellite slot-id or range or all";
       type string {
         length "1 .. 100";
       }
     }
   }
 }
