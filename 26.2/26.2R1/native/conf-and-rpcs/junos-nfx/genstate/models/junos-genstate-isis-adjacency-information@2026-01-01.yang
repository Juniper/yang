module junos-genstate-isis-adjacency-information {
   yang-version 1;
   namespace "http://yang.juniper.net/junos/genstate/isis-adjacency-information";
   prefix jgiai;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for isis-adjacency-information.

      Copyright (c) 2026 Juniper Networks, Inc.
      All rights reserved.";

   revision 2026-01-01 {
     description "Junos: 26.2R1.7";
   }

   grouping isis-adjacency-information-top {
     description
       "Top-level grouping";
     container isis-adjacency-information {
       description
         "Top-level container";
       list isis-adjacency {
         key "interface-name system-name";
         leaf interface-name {
           type string;
           description
             "Name of interface";
         }
         leaf system-name {
           type string;
           description
             "Hostname for a system";
         }
         leaf not-remote-address {
           type empty;
         }
         leaf level {
           type int32;
           description
             "IS-IS Level";
         }
         leaf adjacency-state {
           type string;
           description
             "State of the adjacency";
         }
         leaf holdtime {
           type int32;
           description
             "Delay before timing out the adjacency (default is 180 seconds)";
         }
         list srv6-micro-adjacency-segment-information {
           key "srv6-micro-adjacency-segment-level";
           leaf srv6-micro-adjacency-segment-level {
             type int32;
             description
               "Micro adjacency Level";
           }
           leaf srv6-protected-micro-adjacency-segment {
             type jt:ipv6addr;
             description
               "SRv6 protected micro-adjacency-SID";
           }
           leaf srv6-unprotected-micro-adjacency-segment {
             type jt:ipv6addr;
             description
               "SRv6 unprotected micro-adjacency-SID";
           }
           leaf srv6-micro-adjacency-segment-end-point-func {
             type string;
             description
               "SRv6 micro-adjacency-SID Function";
           }
           leaf srv6-micro-adjacency-segment-flags {
             type string;
             description
               "SRv6 micro adjacency flags";
           }
           leaf srv6-micro-adjacency-segment-algorithm {
             type uint32;
             description
               "SRv6 micro adjacency algorithm";
           }
         }
         container isis-bfd-nlpid-stats {
           description
             "Nlpid state of bfd tlvs";
           container isis-bfd-tlv-mtids {
             description
               "Received bfd tlv mtids";
             leaf isis-bfd-tlv-mtid {
               type int32;
             }
             leaf isis-bfd-mtid-v4nlpid-state {
               type string;
             }
             leaf isis-bfd-mtid-v6nlpid-state {
               type string;
             }
           }
         }
         leaf interface-priority {
           type int32;
         }
         leaf transition-count {
           type int32;
         }
         leaf last-transition-time {
           type string;
         }
         leaf circuit-type {
           type int32;
         }
         leaf adjacency-flag {
           type string;
         }
         leaf mac-address {
           type jt:mac-addr;
         }
         leaf adjacency-topologies {
           type string;
         }
         leaf adjacency-restart-capable {
           type string;
           description
             "Restart capability of the adjacency";
         }
         leaf adjacency-advertisement {
           type string;
           description
             "State of the adjacency advertisment";
         }
         leaf lan-id {
           type string;
         }
         leaf ip-address {
           type jt:ipaddr;
         }
         leaf ipv6-address {
           type jt:ipv6addr;
         }
         leaf global-ipv6-address {
           type jt:ipv6addr;
         }
         list adjacency-segment-information {
           key "adjacency-segment-level";
           leaf adjacency-segment-level {
             type int32;
           }
           leaf ipv4-protected-adjacency-segment-id {
             type int32;
           }
           leaf ipv4-unprotected-adjacency-segment-id {
             type int32;
           }
           leaf ipv6-protected-adjacency-segment-id {
             type int32;
           }
           leaf ipv6-unprotected-adjacency-segment-id {
             type int32;
           }
           leaf adjacency-segment-flags {
             type string;
           }
         }
         list srv6-adjacency-segment-information {
           key "srv6-adjacency-segment-level";
           leaf srv6-adjacency-segment-level {
             type int32;
             description
               "Adjacency Level";
           }
           leaf srv6-protected-adjacency-segment {
             type jt:ipv6addr;
             description
               "SRv6 Protected END-X-SID";
           }
           leaf srv6-unprotected-adjacency-segment {
             type jt:ipv6addr;
             description
               "SRv6 UnProtected END-X-SID";
           }
           leaf srv6-adjacency-segment-end-point-func {
             type string;
             description
               "SRv6 END-X-SID Function";
           }
           leaf srv6-adjacency-segment-flags {
             type string;
             description
               "SRv6 Adjacency Flags";
           }
           leaf srv6-adjacency-segment-algorithm {
             type uint32;
             description
               "SRv6 Adjacency Algorithm";
           }
         }
         container bfd-tlv-information {
           description
             "Received bfd tlv in hello";
           leaf bfd-tlv-info-level {
             type string;
           }
         }
         container isis-adj-bfd-state-info {
           description
             "Adjacency bfd state information";
           leaf isis-bfd-v4-sess-state {
             type string;
           }
           leaf isis-bfd-v6-sess-state {
             type string;
           }
           leaf isis-bfd-req-state {
             type string;
           }
           leaf isis-bfd-adj-usable {
             type string;
           }
         }
         list isis-adjacency-log {
           key "adjacency-when";
           description
             "Entry describing adjacency transition";
           leaf adjacency-when {
             type string;
             description
               "Time at which the transition occurred";
           }
           leaf adjacency-state {
             type string;
             description
               "State of the adjacency";
           }
           leaf adjacency-event {
             type string;
             description
               "Event which triggered the transition";
           }
           leaf adjacency-down-reason {
             type string;
             description
               "Reason for the down transition event";
           }
         }
       }
     }
   }
   augment "/jgs:genstate" {
     description
       "Adds isis-adjacency-information container to top-level genstate 
       container";
     uses isis-adjacency-information-top;
   }
 }
