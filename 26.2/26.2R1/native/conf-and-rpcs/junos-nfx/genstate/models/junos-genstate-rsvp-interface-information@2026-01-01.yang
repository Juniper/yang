module junos-genstate-rsvp-interface-information {
   yang-version 1;
   namespace "http://yang.juniper.net/junos/genstate/rsvp-interface-information";
   prefix jgrii;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for rsvp-interface-information.

      Copyright (c) 2026 Juniper Networks, Inc.
      All rights reserved.";

   revision 2026-01-01 {
     description "Junos: 26.2R1.7";
   }

   grouping rsvp-interface-information-top {
     description
       "Top-level grouping";
     container rsvp-interface-information {
       description
         "Top-level container";
       leaf active-count {
         type int32;
         description
           "Number of active RSVP interfaces";
       }
       list rsvp-interface {
         key "interface-name";
         leaf interface-name {
           type string;
           description
             "Name of interface";
         }
         leaf rsvp-status {
           type string;
           description
             "Administrative or per-interface status of RSVP";
         }
         container rsvp-telink {
           leaf active-reservation {
             type int32;
             description
               "Number of active reservations";
           }
           leaf subscription {
             type int32;
             description
               "Percentage of link capacity available for bandwidth 
               reservations";
           }
           leaf static-bandwidth {
             type string;
             description
               "Static bandwidth capacity of the link with units appended";
           }
           leaf available-bandwidth {
             type string;
             description
               "Amount of bandwidth available for reservations with units 
               appended";
           }
           leaf total-reserved-bandwidth {
             type string;
             description
               "Total amount of bandwidth currently reserved with units 
               appended";
           }
           leaf high-watermark {
             type string;
             description
               "Maximum bandwidth that was ever reserved with units appended";
           }
           leaf static-bandwidth-bps {
             type uint64;
             description
               "Static bandwidth capacity of the link in bits per second";
           }
           leaf available-bandwidth-bps {
             type uint64;
             description
               "Amount of bandwidth available for reservations in bits per 
               second";
           }
           leaf total-reserved-bandwidth-bps {
             type uint64;
             description
               "Total amount of bandwidth currently reserved in bits per 
               second";
           }
           leaf high-watermark-bps {
             type uint64;
             description
               "Maximum bandwidth that was ever reserved in bps";
           }
           leaf update-threshold-value-bps {
             type uint64;
             description
               "Change in reserved bandwidth to trigger IGP update in bits 
               per second";
           }
           leaf update-threshold-max-reservable-bps {
             type uint64;
             description
               "Change in non-rsvp bandwidth to trigger IGP update in bits 
               per second";
           }
           container priority-subscription {
             list priority-subscription-pair {
               key "priority-value";
               leaf priority-value {
                 type int32;
                 description
                   "Priority value corresponding to bandwidth subscription 
                   reserved";
               }
               leaf priority-subscription-percent {
                 type int32;
                 description
                   "Percentage of link capacity available for specific 
                   priority";
               }
             }
           }
           list reserved-bandwidth {
             key "bandwidth-priority";
             description
               "Bandwidth reserved at different priority levels";
             leaf total-reserved-bandwidth-bps {
               type uint64;
               description
                 "Total amount of bandwidth currently reserved in bits per 
                 second";
             }
             leaf bandwidth-priority {
               type int32;
             }
             leaf total-reserved-bandwidth {
               type string;
               description
                 "Total amount of bandwidth currently reserved with units 
                 appended";
             }
           }
           list overbooked-bandwidth {
             key "bandwidth-priority";
             description
               "Bandwidth overbooked at different priority levels";
             leaf total-reserved-bandwidth-bps {
               type uint64;
               description
                 "Total amount of bandwidth currently reserved in bits per 
                 second";
             }
             leaf bandwidth-priority {
               type int32;
             }
             leaf total-reserved-bandwidth {
               type string;
               description
                 "Total amount of bandwidth currently reserved with units 
                 appended";
             }
           }
           leaf preemption-count {
             type int32;
             description
               "Number of preemptions that occurred on an interface";
           }
           leaf soft-preemption-count {
             type int32;
             description
               "Number of soft preemptions that occurred on an interface";
           }
           leaf update-threshold-max-reservable {
             type string;
             description
               "Change in non-rsvp bandwidth to trigger IGP update with 
               units appended";
           }
           leaf update-threshold-max-reservable-percent {
             type int32;
             description
               "Percentage change in max-reservable bandwidth to trigger IGP
               update";
           }
           leaf update-threshold {
             type jt:unsigned-float;
             description
               "Percentage change in reserved bandwidth to trigger IGP 
               update";
           }
           leaf update-threshold-value {
             type string;
             description
               "Change in reserved bandwidth to trigger IGP update with 
               appended units";
           }
           leaf sr-subscription {
             type int32;
             description
               "Percentage of link capacity available after spring traffic";
           }
           leaf soft-preemption-pending {
             type int32;
             description
               "Number of soft preemptions pending on an interface";
           }
         }
         leaf index {
           type int32;
         }
         leaf authentication-flag {
           type string;
         }
         leaf aggregate-flag {
           type string;
         }
         leaf ack-flag {
           type string;
         }
         leaf protect-flag {
           type string;
         }
         leaf hello-interval {
           type int32;
           description
             "Interval between two successive hellos";
         }
         leaf forward-rsvp {
           type empty;
           description
             "Forward RSVP packets coming on RSVP-disabled interface";
         }
         leaf interface-address {
           type jt:ipaddr;
         }
         leaf-list loopback-address {
           type jt:ipaddr;
         }
         list rsvp-interface-statistics {
           key "interface-event-name";
           description
             "Statistics per RSVP interface";
           leaf interface-event-name {
             type string;
           }
           leaf interface-event-count {
             type uint32;
           }
         }
         list message-statistics {
           key "rsvp-message";
           description
             "Statistics per RSVP message type";
           leaf rsvp-message {
             type string;
           }
           leaf messages-sent {
             type int32;
             description
               "Total number of messages sent";
           }
           leaf messages-received {
             type int32;
             description
               "Total number of messages received";
           }
           leaf messages-sent-5seconds {
             type int32;
             description
               "Number of messages sent in the last 5 seconds";
           }
           leaf messages-received-5seconds {
             type int32;
             description
               "Number of messages received in the last 5 seconds";
           }
         }
       }
     }
   }
   augment "/jgs:genstate" {
     description
       "Adds rsvp-interface-information container to top-level genstate 
       container";
     uses rsvp-interface-information-top;
   }
 }
