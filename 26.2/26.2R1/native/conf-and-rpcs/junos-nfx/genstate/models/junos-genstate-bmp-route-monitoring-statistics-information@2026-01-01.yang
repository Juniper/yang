module junos-genstate-bmp-route-monitoring-statistics-information {
   yang-version 1;
   namespace "http://yang.juniper.net/junos/genstate/bmp-route-monitoring-statistics-information";
   prefix jgbrmsi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for bmp-route-monitoring-statistics-information.

      Copyright (c) 2026 Juniper Networks, Inc.
      All rights reserved.";

   revision 2026-01-01 {
     description "Junos: 26.2R1.7";
   }

   grouping bmp-route-monitoring-statistics-information-top {
     description
       "Top-level grouping";
     container bmp-route-monitoring-statistics-information {
       description
         "BGP Monitoring Protocol statistics information";
       list bmp-station {
         key "bmp-station-name";
         leaf bmp-station-name {
           type string;
         }
         container bmp-station-rib-in-pre-statistics {
           leaf bmp-monitor-name {
             type string;
             description
               "BGP Monitoring type name";
           }
           leaf bmp-advertised-prefix-count {
             type int32;
             description
               "Total advertised prefix count";
           }
           leaf bmp-withdrawn-prefix-count {
             type int32;
             description
               "Total withdraw prefix count";
           }
         }
         container bmp-station-rib-in-post-statistics {
           leaf bmp-monitor-name {
             type string;
             description
               "BGP Monitoring type name";
           }
           leaf bmp-advertised-prefix-count {
             type int32;
             description
               "Total advertised prefix count";
           }
           leaf bmp-withdrawn-prefix-count {
             type int32;
             description
               "Total withdraw prefix count";
           }
         }
         list bmp-station-rib-local-statistics {
           key "bmp-monitor-name";
           leaf bmp-monitor-name {
             type string;
             description
               "BGP Monitoring type name";
           }
           leaf bmp-advertised-prefix-count {
             type int32;
             description
               "Total advertised prefix count";
           }
           leaf bmp-withdrawn-prefix-count {
             type int32;
             description
               "Total withdraw prefix count";
           }
         }
         container bmp-station-rib-out-pre-statistics {
           leaf bmp-monitor-name {
             type string;
             description
               "BGP Monitoring type name";
           }
           leaf bmp-advertised-prefix-count {
             type int32;
             description
               "Total advertised prefix count";
           }
           leaf bmp-withdrawn-prefix-count {
             type int32;
             description
               "Total withdraw prefix count";
           }
         }
         container bmp-station-rib-out-post-statistics {
           leaf bmp-monitor-name {
             type string;
             description
               "BGP Monitoring type name";
           }
           leaf bmp-advertised-prefix-count {
             type int32;
             description
               "Total advertised prefix count";
           }
           leaf bmp-withdrawn-prefix-count {
             type int32;
             description
               "Total withdraw prefix count";
           }
         }
       }
     }
   }
   augment "/jgs:genstate" {
     description
       "Adds bmp-route-monitoring-statistics-information container to 
       top-level genstate container";
     uses bmp-route-monitoring-statistics-information-top;
   }
 }
