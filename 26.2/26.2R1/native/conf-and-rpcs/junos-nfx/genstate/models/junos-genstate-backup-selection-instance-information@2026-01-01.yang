module junos-genstate-backup-selection-instance-information {
   yang-version 1;
   namespace "http://yang.juniper.net/junos/genstate/backup-selection-instance-information";
   prefix jgbsii;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for backup-selection-instance-information.

      Copyright (c) 2026 Juniper Networks, Inc.
      All rights reserved.";

   revision 2026-01-01 {
     description "Junos: 26.2R1.7";
   }

   grouping backup-selection-instance-information-top {
     description
       "Top-level grouping";
     container backup-selection-instance-information {
       description
         "Backup selection policy information for the instance";
       list backup-selection-routing-instance {
         key "routing-instance";
         leaf routing-instance {
           type string;
         }
         list backup-selection-policy-dest {
           key "address-prefix";
           leaf address-prefix {
             type jt:ipaddr;
           }
           list backup-selection-policy-intf {
             key "interface-name";
             leaf backup-selection-protection-type {
               type string;
             }
             leaf backup-selection-downstream-paths-only {
               type string;
             }
             leaf backup-selection-srlg-type {
               type string;
             }
             leaf backup-selection-bw-ge-primary {
               type string;
             }
             leaf backup-selection-root-metric {
               type string;
             }
             leaf backup-selection-dest-metric {
               type string;
             }
             leaf interface-name {
               type string;
               description
                 "Name of interface";
             }
             container backup-selection-admin-group-exclude {
               leaf-list admin-group-exclude-name {
                 type string;
               }
             }
             container backup-selection-admin-group-incall {
               leaf-list admin-group-incall-name {
                 type string;
               }
             }
             container backup-selection-admin-group-incany {
               leaf-list admin-group-incany-name {
                 type string;
               }
             }
             container backup-selection-admin-group-preference {
               leaf-list admin-group-preference-name {
                 type string;
               }
             }
             container backup-selection-backup-neighbor-exclude {
               leaf-list address-prefix {
                 type jt:ipaddr;
               }
             }
             container backup-selection-backup-neighbor-preference {
               leaf-list address-prefix {
                 type jt:ipaddr;
               }
             }
             container backup-selection-neighbor-exclude {
               leaf-list address-prefix {
                 type jt:ipaddr;
               }
             }
             container backup-selection-neighbor-preference {
               leaf-list address-prefix {
                 type jt:ipaddr;
               }
             }
             container backup-selection-neighbor-tag-exclude {
               leaf-list neighbor-tag-value {
                 type int32;
               }
             }
             container backup-selection-neighbor-tag-preference {
               leaf-list neighbor-tag-value {
                 type int32;
               }
             }
             container backup-selection-metric-order {
               leaf-list backup-selection-metric-type {
                 type string;
               }
             }
             container backup-selection-eval-order {
               leaf-list backup-selection-eval-type {
                 type string;
               }
             }
           }
         }
         leaf simple-int {
           type int32;
         }
         list backup-selection-policy-destination {
           key "address-prefix";
           leaf address-prefix {
             type string;
           }
           leaf simple-int {
             type int32;
           }
           list backup-selection-policy-intf {
             key "interface-name-1";
             leaf interface-name-1 {
               type jt:interface-device;
             }
             leaf simple-int {
               type int32;
             }
             container backup-selection-policy-intf-level {
             }
           }
         }
       }
     }
   }
   augment "/jgs:genstate" {
     description
       "Adds backup-selection-instance-information container to top-level 
       genstate container";
     uses backup-selection-instance-information-top;
   }
 }
