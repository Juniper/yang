module junos-genstate-mpls-interface-information {
   yang-version 1;
   namespace "http://yang.juniper.net/junos/genstate/mpls-interface-information";
   prefix jgmii;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for mpls-interface-information.

      Copyright (c) 2026 Juniper Networks, Inc.
      All rights reserved.";

   revision 2026-01-01 {
     description "Junos: 26.2R1.7";
   }

   grouping mpls-interface-information-top {
     description
       "Top-level grouping";
     container mpls-interface-information {
       description
         "Top-level container";
       list mpls-interface-detail {
         key "interface-name";
         leaf interface-name {
           type string;
           description
             "Name of interface";
         }
         leaf mpls-interface-state {
           type string;
         }
         leaf no-group-flag {
           type empty;
         }
         leaf-list admin-group-name {
           type string;
           description
             "Name of the admin group";
         }
         leaf-list srlg-name {
           type string;
           description
             "Name of the srlg";
         }
         leaf maximum-labels {
           type string;
           description
             "Maximum label";
         }
         leaf static-revert-time {
           type string;
           description
             "Static LSP revert wait time";
         }
         leaf always-mark-connection-protection-tlv {
           type string;
           description
             "Always-mark-connection-protection-tlv status on a MPLS 
             interface";
         }
         leaf mpls-interface-switch-away-lsps {
           type string;
           description
             "Switch-away-lsps knob status of a MPLS interface";
         }
       }
     }
   }
   augment "/jgs:genstate" {
     description
       "Adds mpls-interface-information container to top-level genstate 
       container";
     uses mpls-interface-information-top;
   }
 }
