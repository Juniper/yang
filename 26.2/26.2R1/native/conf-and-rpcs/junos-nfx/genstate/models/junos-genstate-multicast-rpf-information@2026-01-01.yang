module junos-genstate-multicast-rpf-information {
   yang-version 1;
   namespace "http://yang.juniper.net/junos/genstate/multicast-rpf-information";
   prefix jgmri;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for multicast-rpf-information.

      Copyright (c) 2026 Juniper Networks, Inc.
      All rights reserved.";

   revision 2026-01-01 {
     description "Junos: 26.2R1.7";
   }

   grouping multicast-rpf-information-top {
     description
       "Top-level grouping";
     container multicast-rpf-information {
       description
         "Top-level container";
       list rpf-family {
         key "address-family";
         leaf rpf-table-name {
           type string;
         }
         leaf rpf-table-entry-count {
           type uint32;
         }
         leaf address-family {
           type string;
         }
         list rpf-route {
           key "prefix";
           leaf prefix {
             type jt:ipaddr;
           }
           leaf rpf-route-protocol {
             type string;
           }
           leaf interface-name {
             type string;
             description
               "Name of interface";
           }
           leaf rpf-route-neighbor {
             type jt:ipaddr;
           }
         }
       }
     }
   }
   augment "/jgs:genstate" {
     description
       "Adds multicast-rpf-information container to top-level genstate 
       container";
     uses multicast-rpf-information-top;
   }
 }
