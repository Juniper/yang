module junos-genstate-lldp-statistics {
   yang-version 1;
   namespace "http://yang.juniper.net/junos/genstate/lldp-statistics";
   prefix jgls;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for lldp-statistics.

      Copyright (c) 2026 Juniper Networks, Inc.
      All rights reserved.";

   revision 2026-01-01 {
     description "Junos: 26.2R1.7";
   }

   grouping lldp-statistics-top {
     description
       "Top-level grouping";
     container lldp-statistics {
       description
         "Top-level container";
       list lldp-interface-statistics {
         key "lldp-statistics-interface-name";
         description
           "Interface statistics";
         leaf lldp-statistics-interface-name {
           type string;
         }
         leaf lldp-parent-intf-name {
           type string;
           description
             "Parent interface for which statistics are shown";
         }
         leaf lldp-receive-packet-count {
           type uint32;
         }
         leaf lldp-receive-packet-unknown-tlvs {
           type uint32;
           description
             "Number of received LLDP packets with unknown TLVs";
         }
         leaf lldp-receive-packet-error-count {
           type uint32;
         }
         leaf lldp-receive-tlv-discard-count {
           type uint32;
         }
         leaf lldp-transmit-packet-count {
           type uint32;
         }
         leaf lldp-transmit-packet-error-count {
           type uint32;
         }
       }
     }
   }
   augment "/jgs:genstate" {
     description
       "Adds lldp-statistics container to top-level genstate container";
     uses lldp-statistics-top;
   }
 }
