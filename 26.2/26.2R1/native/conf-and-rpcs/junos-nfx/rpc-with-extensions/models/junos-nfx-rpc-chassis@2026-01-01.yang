/*
 * Copyright (c) 2026 Juniper Networks, Inc.
 * All rights reserved.
 */
 module junos-nfx-rpc-chassis {
   namespace "http://yang.juniper.net/junos-nfx/rpc/chassis";

   prefix chassis;

   import junos-common-ddl-extensions {
     prefix junos;
     revision-date 2026-01-01;
   }

   import junos-common-types {
     prefix jt;
     revision-date 2026-01-01;
   }

   organization "Juniper Networks, Inc.";

   contact "yang-support@juniper.net";

   description "Junos RPC YANG module for chassis command(s)";

   revision 2026-01-01 {
     description "Junos: 26.2R1.7";
   }

   rpc get-personality-information {
     description "Show chassis's current personality";
     junos:command "show chassis personality";
     output {
       choice output-tags {
         case output-tag {
           leaf output {
             type string;
           }
         }
         case actual-tag {
           anyxml personality-information;
         }
         case multichassis-tag {
           anyxml multi-routing-engine-results;
         }
       }
     }
   }
   rpc get-scb-ha-port-statistics-information {
     description "Show Switch Control Board HA port statistics";
     junos:command "show chassis scb-ha-port statistics";
     output {
       choice output-tags {
         case actual-tag {
           container chassis-scb-ha-port {
             uses chassis-scb-ha-port-block;
           }
         }
         case multichassis-tag {
           container multi-routing-engine-results {
             list multi-routing-engine-item {
               leaf re-name {
                 type string;
               }
               choice output-tags {
                 case actual-tag {
                   container chassis-scb-ha-port {
                     uses chassis-scb-ha-port-block;
                   }
                 }
               }
             }
           }
         }
       }
     }
   }
   rpc get-uft-information {
     description "Show member's current UFT configuration";
     junos:command "show chassis forwarding-options";
     input {
       uses command-forwarding;
     }
     output {
       choice output-tags {
         case actual-tag {
           container uft-information {
             uses uft-information-block;
           }
         }
         case multichassis-tag {
           container multi-routing-engine-results {
             list multi-routing-engine-item {
               leaf re-name {
                 type string;
               }
               choice output-tags {
                 case actual-tag {
                   container uft-information {
                     uses uft-information-block;
                   }
                 }
               }
             }
           }
         }
       }
     }
   }
   rpc get-system-mode-information {
     description "Show member's current system-mode configuration";
     junos:command "show chassis system-mode";
     input {
       uses command-forwarding;
     }
     output {
       choice output-tags {
         case actual-tag {
           container system-mode-information {
             uses system-mode-information-block;
           }
         }
         case multichassis-tag {
           container multi-routing-engine-results {
             list multi-routing-engine-item {
               leaf re-name {
                 type string;
               }
               choice output-tags {
                 case actual-tag {
                   container system-mode-information {
                     uses system-mode-information-block;
                   }
                 }
               }
             }
           }
         }
       }
     }
   }
   rpc get-power-usage-information {
     description "Show Chassis Power Usages";
     junos:command "show chassis power";
     input {
       uses command-forwarding;
     }
     output {
       choice output-tags {
         case actual-tag {
           container power-usage-information {
             uses power-usage-information-block;
           }
         }
         case multichassis-tag {
           container multi-routing-engine-results {
             list multi-routing-engine-item {
               leaf re-name {
                 type string;
               }
               choice output-tags {
                 case actual-tag {
                   container power-usage-information {
                     uses power-usage-information-block;
                   }
                 }
               }
             }
           }
         }
       }
     }
   }
   rpc get-power-usage-information-detail {
     description "Show chassis power usage detail";
     junos:command "show chassis power detail";
     input {
       uses command-forwarding;
     }
     output {
       choice output-tags {
         case actual-tag {
           container power-usage-information {
             uses power-usage-information-block;
           }
         }
         case multichassis-tag {
           container multi-routing-engine-results {
             list multi-routing-engine-item {
               leaf re-name {
                 type string;
               }
               choice output-tags {
                 case actual-tag {
                   container power-usage-information {
                     uses power-usage-information-block;
                   }
                 }
               }
             }
           }
         }
       }
     }
   }
   rpc get-power-usage-information-extensive {
     description "Show chassis power usage extensive";
     junos:command "show chassis power extensive";
     input {
       uses command-forwarding;
     }
     output {
       choice output-tags {
         case actual-tag {
           container power-usage-information {
             uses power-usage-information-block;
           }
         }
         case multichassis-tag {
           container multi-routing-engine-results {
             list multi-routing-engine-item {
               leaf re-name {
                 type string;
               }
               choice output-tags {
                 case actual-tag {
                   container power-usage-information {
                     uses power-usage-information-block;
                   }
                 }
               }
             }
           }
         }
       }
     }
   }
   rpc get-fru-power-on-sequence {
     description "Show chassis fru power on sequence";
     junos:command "show chassis power sequence";
     input {
       uses command-forwarding;
     }
     output {
       choice output-tags {
         case actual-tag {
           container fru-power-on-sequence {
             uses fru-power-on-sequence-block;
           }
         }
         case multichassis-tag {
           container multi-routing-engine-results {
             list multi-routing-engine-item {
               leaf re-name {
                 type string;
               }
               choice output-tags {
                 case actual-tag {
                   container fru-power-on-sequence {
                     uses fru-power-on-sequence-block;
                   }
                 }
               }
             }
           }
         }
       }
     }
   }
   rpc get-alarm-information {
     description "Show alarm status";
     junos:command "show chassis alarms";
     input {
       uses command-forwarding;
     }
     output {
       choice output-tags {
         case actual-tag {
           container alarm-information {
             uses alarm-information-block;
           }
         }
         case multichassis-tag {
           container multi-routing-engine-results {
             list multi-routing-engine-item {
               leaf re-name {
                 type string;
               }
               choice output-tags {
                 case actual-tag {
                   container alarm-information {
                     uses alarm-information-block;
                   }
                 }
               }
             }
           }
         }
       }
     }
   }
   rpc get-fpc-alarm-information {
     description "Show alarm status for a FPC";
     junos:command "show chassis alarms fpc";
     input {
       leaf fpc-slot {
         description "Flexible PIC Controller slot number";
         junos:cli-feature "nokeyword";
         type union {
           type string {
             pattern "<.*>|$.*";
           }
           type uint32;
         }
         mandatory true;
       }
     }
     output {
       choice output-tags {
         case actual-tag {
           container alarm-information {
             uses alarm-information-block;
           }
         }
         case multichassis-tag {
           container multi-routing-engine-results {
             list multi-routing-engine-item {
               leaf re-name {
                 type string;
               }
               choice output-tags {
                 case actual-tag {
                   container alarm-information {
                     uses alarm-information-block;
                   }
                 }
               }
             }
           }
         }
       }
     }
   }
   rpc get-chassis-alarm-satellite-information {
     description "Show alarm status for satellite devices";
     junos:command "show chassis alarms satellite";
     input {
       leaf fpc-slot {
         description "Satellite slot number";
         type union {
           type string {
             pattern "<.*>|$.*";
           }
           type uint16 {
             range "65 .. 254";
           }
         }
       }
     }
     output {
       choice output-tags {
         case output-tag {
           leaf output {
             type string;
           }
         }
         case actual-tag {
           anyxml chassis-alarm-satellite-information;
         }
         case multichassis-tag {
           anyxml multi-routing-engine-results;
         }
       }
     }
   }
   rpc get-jam-test-information {
     description "Show Jam API test result";
     junos:command "show chassis jam-test";
     input {
       leaf detail {
         description "Display detailed output";
         type empty;
       }
       leaf fpc-slot {
         description "FPC slot number";
         junos:cli-feature "nokeyword";
         type union {
           type string {
             pattern "<.*>|$.*";
           }
           type uint32;
         }
       }
     }
     output {
       choice output-tags {
         case output-tag {
           leaf output {
             type string;
           }
         }
         case actual-tag {
           anyxml jam-test-information;
         }
         case multichassis-tag {
           anyxml multi-routing-engine-results;
         }
       }
     }
   }
   rpc get-chassis-errors {
     description "Show chassis errors";
     junos:command "show chassis errors";
     input {
       leaf error-id {
         description "Error identifier for the error to be cleared";
         type string {
           length "1 .. 255";
           junos:posix-pattern "^(/[^/ ]+/[0-9:]+){4}/[^/ ]+$";
           junos:pattern-message "Invalid error identifier format";
         }
         mandatory true;
       }
       leaf fpc-slot {
         description "Slot number of FPC";
         type union {
           type string {
             pattern "<.*>|$.*";
           }
           type uint32;
         }
         mandatory true;
       }
     }
     output {
       choice output-tags {
         case output-tag {
           leaf output {
             type string;
           }
         }
         case actual-tag {
           anyxml chassis-error-information;
         }
         case multichassis-tag {
           anyxml multi-routing-engine-results;
         }
       }
     }
   }
   rpc get-chassis-active-errors {
     description "Show active errors";
     junos:command "show chassis errors active";
     input {
       leaf fpc-slot {
         description "Slot number of FPC";
         type union {
           type string {
             pattern "<.*>|$.*";
           }
           type uint32;
         }
       }
     }
     output {
       choice output-tags {
         case output-tag {
           leaf output {
             type string;
           }
         }
         case actual-tag {
           anyxml chassis-active-error-information;
         }
         case multichassis-tag {
           anyxml multi-routing-engine-results;
         }
       }
     }
   }
   rpc get-active-error-information-detail {
     description "Show detailed output";
     junos:command "show chassis errors active detail";
     input {
       leaf fpc-slot {
         description "Slot number of FPC";
         type union {
           type string {
             pattern "<.*>|$.*";
           }
           type uint32;
         }
       }
     }
     output {
       choice output-tags {
         case output-tag {
           leaf output {
             type string;
           }
         }
         case actual-tag {
           anyxml chassis-errors-detail-information;
         }
         case multichassis-tag {
           anyxml multi-routing-engine-results;
         }
       }
     }
   }
   rpc get-chassis-beacon-information {
     description "Show beacon status";
     junos:command "show chassis beacon";
     input {
       choice which-arg {
         case all {
           leaf all {
             description "Beacons in ON/OFF state";
             type enumeration {
               enum "off" {
                 description "Beacons in OFF state";
               }
               enum "on" {
                 description "Beacons in ON state";
               }
             }
           }
         }
         case fpc {
           leaf fpc {
             description "Flexible PIC Controller slot number";
             type union {
               type string {
                 pattern "<.*>|$.*";
               }
               type uint32;
             }
           }
         }
         case cb {
           leaf cb {
             description "Control Board slot number";
             type union {
               type string {
                 pattern "<.*>|$.*";
               }
               type uint32;
             }
           }
         }
         case service-node {
           leaf service-node {
             description "Service Node slot number";
             type union {
               type string {
                 pattern "<.*>|$.*";
               }
               type uint32 {
                 range "0 .. 1";
               }
             }
           }
         }
       }
       leaf pic-slot {
         description "PIC slot number";
         type union {
           type string {
             pattern "<.*>|$.*";
           }
           type uint32;
         }
       }
       choice port-num {
         case port {
           leaf port {
             description "Port number";
             type union {
               type string {
                 pattern "<.*>|$.*";
               }
               type uint32;
             }
           }
         }
         case port-range {
           leaf port-range {
             description "Port range";
             type empty;
           }
         }
       }
       leaf lower-limit {
         description "Port range lower limit";
         type union {
           type string {
             pattern "<.*>|$.*";
           }
           type uint32;
         }
       }
       leaf upper-limit {
         description "Port range upper limit";
         type union {
           type string {
             pattern "<.*>|$.*";
           }
           type uint32;
         }
       }
     }
     output {
       choice output-tags {
         case actual-tag {
           container chassis-beacon-information {
             uses chassis-beacon-information-block;
           }
         }
         case multichassis-tag {
           container multi-routing-engine-results {
             list multi-routing-engine-item {
               leaf re-name {
                 type string;
               }
               choice output-tags {
                 case actual-tag {
                   container chassis-beacon-information {
                     uses chassis-beacon-information-block;
                   }
                 }
               }
             }
           }
         }
       }
     }
   }
   rpc get-chassis-interoperability {
     description "Show chassis interoperability mode";
     junos:command "show chassis interoperability";
     output {
       choice output-tags {
         case actual-tag {
           container get-chassis-interoperability {
             uses get-chassis-interoperability-block;
           }
         }
         case multichassis-tag {
           container multi-routing-engine-results {
             list multi-routing-engine-item {
               leaf re-name {
                 type string;
               }
               choice output-tags {
                 case actual-tag {
                   container get-chassis-interoperability {
                     uses get-chassis-interoperability-block;
                   }
                 }
               }
             }
           }
         }
       }
     }
   }
   rpc network-services {
     description "Show chassis network services";
     junos:command "show chassis network-services";
     output {
       choice output-tags {
         case actual-tag {
           container network-services {
             uses network-services-block;
           }
         }
         case multichassis-tag {
           container multi-routing-engine-results {
             list multi-routing-engine-item {
               leaf re-name {
                 type string;
               }
               choice output-tags {
                 case actual-tag {
                   container network-services {
                     uses network-services-block;
                   }
                 }
               }
             }
           }
         }
       }
     }
   }
   rpc ambient-temperature {
     description "Show chassis ambient temperature";
     junos:command "show chassis ambient-temperature";
     output {
       choice output-tags {
         case actual-tag {
           container ambient-temperature {
             uses ambient-temperature-block;
           }
         }
         case multichassis-tag {
           container multi-routing-engine-results {
             list multi-routing-engine-item {
               leaf re-name {
                 type string;
               }
               choice output-tags {
                 case actual-tag {
                   container ambient-temperature {
                     uses ambient-temperature-block;
                   }
                 }
               }
             }
           }
         }
       }
     }
   }
   rpc get-satellite-device-list {
     description "Displays active satellite devices";
     junos:command "show chassis port-extender";
     output {
       choice output-tags {
         case actual-tag {
           container satellite-device-list {
             uses satellite-device-list-block;
           }
         }
         case multichassis-tag {
           container multi-routing-engine-results {
             list multi-routing-engine-item {
               leaf re-name {
                 type string;
               }
               choice output-tags {
                 case actual-tag {
                   container satellite-device-list {
                     uses satellite-device-list-block;
                   }
                 }
               }
             }
           }
         }
       }
     }
   }
   rpc get-clock-synchronization {
     description "Show clock synchronization information";
     junos:command "show chassis synchronization";
     input {
       uses command-forwarding;
       leaf interface {
         description "Name of physical interface";
         type string;
       }
       leaf extensive {
         description "Show clock synchronization information in detail";
         type empty;
       }
     }
     output {
       choice output-tags {
         case actual-tag {
           container clock-synchronization {
             uses clock-synchronization-block;
           }
         }
         case multichassis-tag {
           container multi-routing-engine-results {
             list multi-routing-engine-item {
               leaf re-name {
                 type string;
               }
               choice output-tags {
                 case actual-tag {
                   container clock-synchronization {
                     uses clock-synchronization-block;
                   }
                 }
               }
             }
           }
         }
       }
     }
   }
   rpc get-chassis-clock-synchronization-gnss-receiver {
     description "Show GNSS receiver related parameters";
     junos:command "show chassis synchronization gnss-receiver";
     input {
       leaf extensive {
         description "Show detailed GNSS receiver information";
         type empty;
       }
       leaf time {
         description "Show GNSS receiver time information";
         type empty;
       }
     }
     output {
       choice output-tags {
         case output-tag {
           leaf output {
             type string;
           }
         }
         case actual-tag {
           anyxml clock-synchronization-gnss-receiver;
         }
         case multichassis-tag {
           anyxml multi-routing-engine-results;
         }
       }
     }
   }
   rpc get-clksyncd-in-memory-debug-summary {
     description "Display memory logs buffer summary";
     junos:command "show chassis synchronization memory-logging summary";
     output {
       choice output-tags {
         case actual-tag {
           container clksyncd-in-memory-debug-information-summary {
             uses clksyncd-in-memory-debug-information-summary-block;
           }
         }
         case multichassis-tag {
           container multi-routing-engine-results {
             list multi-routing-engine-item {
               leaf re-name {
                 type string;
               }
               choice output-tags {
                 case actual-tag {
                   container clksyncd-in-memory-debug-information-summary {
                     uses clksyncd-in-memory-debug-information-summary-block;
                   }
                 }
               }
             }
           }
         }
       }
     }
   }
   rpc clksyncd-in-memory-debug-show-trace {
     description "Display memory logs buffer traces";
     junos:command "show chassis synchronization memory-logging messages";
     output {
       choice output-tags {
         case actual-tag {
           container clksyncd-in-memory-debug-information-trace {
             uses clksyncd-in-memory-debug-information-trace-block;
           }
         }
         case multichassis-tag {
           container multi-routing-engine-results {
             list multi-routing-engine-item {
               leaf re-name {
                 type string;
               }
               choice output-tags {
                 case actual-tag {
                   container clksyncd-in-memory-debug-information-trace {
                     uses clksyncd-in-memory-debug-information-trace-block;
                   }
                 }
               }
             }
           }
         }
       }
     }
   }
   rpc clksyncd-memory-socket-logs {
     description "Display clksyncd socket logs";
     junos:command "show chassis synchronization memory-logging messages socket";
     output {
       choice output-tags {
         case output-tag {
           leaf output {
             type string;
           }
         }
         case actual-tag {
           anyxml clksyncd-memory-socket-logs;
         }
         case multichassis-tag {
           anyxml multi-routing-engine-results;
         }
       }
     }
   }
   rpc clksyncd-memory-ipc-logs {
     description "Display clksyncd ipc logs";
     junos:command "show chassis synchronization memory-logging messages ipc";
     output {
       choice output-tags {
         case output-tag {
           leaf output {
             type string;
           }
         }
         case actual-tag {
           anyxml clksyncd-memory-ipc-logs;
         }
         case multichassis-tag {
           anyxml multi-routing-engine-results;
         }
       }
     }
   }
   rpc clksyncd-memory-spi-logs {
     description "Display clksyncd spi logs";
     junos:command "show chassis synchronization memory-logging messages spi";
     output {
       choice output-tags {
         case output-tag {
           leaf output {
             type string;
           }
         }
         case actual-tag {
           anyxml clksyncd-memory-spi-logs;
         }
         case multichassis-tag {
           anyxml multi-routing-engine-results;
         }
       }
     }
   }
   rpc clksyncd-memory-pll-logs {
     description "Display clksyncd pll logs";
     junos:command "show chassis synchronization memory-logging messages pll";
     output {
       choice output-tags {
         case output-tag {
           leaf output {
             type string;
           }
         }
         case actual-tag {
           anyxml clksyncd-memory-pll-logs;
         }
         case multichassis-tag {
           anyxml multi-routing-engine-results;
         }
       }
     }
   }
   rpc clksyncd-memory-fpga-logs {
     description "Display clksyncd fpga logs";
     junos:command "show chassis synchronization memory-logging messages fpga";
     output {
       choice output-tags {
         case output-tag {
           leaf output {
             type string;
           }
         }
         case actual-tag {
           anyxml clksyncd-memory-fpga-logs;
         }
         case multichassis-tag {
           anyxml multi-routing-engine-results;
         }
       }
     }
   }
   rpc clksyncd-memory-init-logs {
     description "Display clksyncd init logs";
     junos:command "show chassis synchronization memory-logging messages init";
     output {
       choice output-tags {
         case output-tag {
           leaf output {
             type string;
           }
         }
         case actual-tag {
           anyxml clksyncd-memory-init-logs;
         }
         case multichassis-tag {
           anyxml multi-routing-engine-results;
         }
       }
     }
   }
   rpc clksyncd-memory-memory-logs {
     description "Display clksyncd memory logs";
     junos:command "show chassis synchronization memory-logging messages memory";
     output {
       choice output-tags {
         case output-tag {
           leaf output {
             type string;
           }
         }
         case actual-tag {
           anyxml clksyncd-memory-memory-logs;
         }
         case multichassis-tag {
           anyxml multi-routing-engine-results;
         }
       }
     }
   }
   rpc clksyncd-memory-system-logs {
     description "Display clksyncd system call logs";
     junos:command "show chassis synchronization memory-logging messages system";
     output {
       choice output-tags {
         case output-tag {
           leaf output {
             type string;
           }
         }
         case actual-tag {
           anyxml clksyncd-memory-system-logs;
         }
         case multichassis-tag {
           anyxml multi-routing-engine-results;
         }
       }
     }
   }
   rpc clksyncd-memory-gencfg-logs {
     description "Display clksyncd gencfg logs";
     junos:command "show chassis synchronization memory-logging messages gencfg";
     output {
       choice output-tags {
         case output-tag {
           leaf output {
             type string;
           }
         }
         case actual-tag {
           anyxml clksyncd-memory-gencfg-logs;
         }
         case multichassis-tag {
           anyxml multi-routing-engine-results;
         }
       }
     }
   }
   rpc clksyncd-memory-kernel-logs {
     description "Display clksyncd kernel logs";
     junos:command "show chassis synchronization memory-logging messages kernel";
     output {
       choice output-tags {
         case output-tag {
           leaf output {
             type string;
           }
         }
         case actual-tag {
           anyxml clksyncd-memory-kernel-logs;
         }
         case multichassis-tag {
           anyxml multi-routing-engine-results;
         }
       }
     }
   }
   rpc clksyncd-memory-fsm-logs {
     description "Display clksyncd fsm logs";
     junos:command "show chassis synchronization memory-logging messages fsm";
     output {
       choice output-tags {
         case output-tag {
           leaf output {
             type string;
           }
         }
         case actual-tag {
           anyxml clksyncd-memory-fsm-logs;
         }
         case multichassis-tag {
           anyxml multi-routing-engine-results;
         }
       }
     }
   }
   rpc clksyncd-in-memory-config-logs {
     description "Display clksyncd config logs";
     junos:command "show chassis synchronization memory-logging messages config";
     output {
       choice output-tags {
         case output-tag {
           leaf output {
             type string;
           }
         }
         case actual-tag {
           anyxml clksyncd-in-memory-config-logs;
         }
         case multichassis-tag {
           anyxml multi-routing-engine-results;
         }
       }
     }
   }
   rpc clksyncd-memory-bmca-synce-logs {
     description "Display clksyncd sycne bmca logs";
     junos:command "show chassis synchronization memory-logging messages synce-bmca";
     output {
       choice output-tags {
         case output-tag {
           leaf output {
             type string;
           }
         }
         case actual-tag {
           anyxml clksyncd-memory-bmca-synce-logs;
         }
         case multichassis-tag {
           anyxml multi-routing-engine-results;
         }
       }
     }
   }
   rpc clksyncd-memory-timer-logs {
     description "Display clksyncd timer logs";
     junos:command "show chassis synchronization memory-logging messages timer";
     output {
       choice output-tags {
         case output-tag {
           leaf output {
             type string;
           }
         }
         case actual-tag {
           anyxml clksyncd-memory-timer-logs;
         }
         case multichassis-tag {
           anyxml multi-routing-engine-results;
         }
       }
     }
   }
   rpc clksyncd-memory-synce-logs {
     description "Display clksyncd synce logs";
     junos:command "show chassis synchronization memory-logging messages synce";
     output {
       choice output-tags {
         case output-tag {
           leaf output {
             type string;
           }
         }
         case actual-tag {
           anyxml clksyncd-memory-synce-logs;
         }
         case multichassis-tag {
           anyxml multi-routing-engine-results;
         }
       }
     }
   }
   rpc clksyncd-memory-ptp-logs {
     description "Display clksyncd ptp logs";
     junos:command "show chassis synchronization memory-logging messages ptp";
     output {
       choice output-tags {
         case output-tag {
           leaf output {
             type string;
           }
         }
         case actual-tag {
           anyxml clksyncd-memory-ptp-logs;
         }
         case multichassis-tag {
           anyxml multi-routing-engine-results;
         }
       }
     }
   }
   rpc get-craft-information {
     description "Show craft interface status";
     junos:command "show chassis craft-interface";
     input {
       uses command-forwarding;
     }
     output {
       choice output-tags {
         case actual-tag {
           container craft-information {
             uses craft-information-block;
           }
         }
         case multichassis-tag {
           container multi-routing-engine-results {
             list multi-routing-engine-item {
               leaf re-name {
                 type string;
               }
               choice output-tags {
                 case actual-tag {
                   container craft-information {
                     uses craft-information-block;
                   }
                 }
               }
             }
           }
         }
       }
     }
   }
   rpc get-ethernet-switch-information {
     description "Show Ethernet switch information";
     junos:command "show chassis ethernet-switch";
     input {
       uses command-forwarding;
       leaf ethernet-switch-type {
         description "Show Ethernet switch information";
         junos:cli-feature "nokeyword";
         type enumeration {
           enum "get-ethernet-switch-cb-information" {
             description "Show Ethernet switch Control Board information";
           }
           enum "get-ethernet-switch-fpc-information" {
             description "Show Ethernet switch Front Card information";
           }
         }
         mandatory true;
       }
       leaf detail {
         description "Show Ethernet switch traffic statistics";
         type empty;
       }
       leaf port {
         description "Port number";
         type union {
           type string {
             pattern "<.*>|$.*";
           }
           type uint32 {
             range "1 .. 28";
           }
         }
       }
       leaf slot {
         description "Front card FPC slot number";
         junos:cli-feature "nokeyword";
         type union {
           type string {
             pattern "<.*>|$.*";
           }
           type uint32 {
             range "0 .. 7";
           }
         }
       }
     }
     output {
       choice output-tags {
         case actual-tag {
           container ethernet-switch-information {
             uses ethernet-switch-information-block;
           }
         }
         case multichassis-tag {
           container multi-routing-engine-results {
             list multi-routing-engine-item {
               leaf re-name {
                 type string;
               }
               choice output-tags {
                 case actual-tag {
                   container ethernet-switch-information {
                     uses ethernet-switch-information-block;
                   }
                 }
               }
             }
           }
         }
       }
     }
   }
   rpc get-ethernet-switch-statistics-information {
     description "Show Ethernet switch traffic statistics";
     junos:command "show chassis ethernet-switch statistics";
     input {
       uses command-forwarding;
       leaf switch {
         description "Switch number";
         type union {
           type string {
             pattern "<.*>|$.*";
           }
           type uint32;
         }
       }
       leaf port {
         description "Port number";
         junos:cli-feature "nokeyword";
         type union {
           type string {
             pattern "<.*>|$.*";
           }
           type uint32;
         }
       }
     }
     output {
       choice output-tags {
         case actual-tag {
           container ethernet-switch-statistics-information {
             uses ethernet-switch-statistics-information-block;
           }
         }
         case multichassis-tag {
           container multi-routing-engine-results {
             list multi-routing-engine-item {
               leaf re-name {
                 type string;
               }
               choice output-tags {
                 case actual-tag {
                   container ethernet-switch-statistics-information {
                     uses ethernet-switch-statistics-information-block;
                   }
                 }
               }
             }
           }
         }
       }
     }
   }
   rpc get-ethernet-switch-error-information {
     description "Show accumulated Ethernet switch errors";
     junos:command "show chassis ethernet-switch errors";
     input {
       uses command-forwarding;
       leaf switch {
         description "Switch number";
         type union {
           type string {
             pattern "<.*>|$.*";
           }
           type uint32;
         }
       }
       leaf port {
         description "Port number";
         junos:cli-feature "nokeyword";
         type union {
           type string {
             pattern "<.*>|$.*";
           }
           type uint32;
         }
       }
     }
     output {
       choice output-tags {
         case actual-tag {
           container ethernet-switch-error-information {
             uses ethernet-switch-error-information-block;
           }
         }
         case multichassis-tag {
           container multi-routing-engine-results {
             list multi-routing-engine-item {
               leaf re-name {
                 type string;
               }
               choice output-tags {
                 case actual-tag {
                   container ethernet-switch-error-information {
                     uses ethernet-switch-error-information-block;
                   }
                 }
               }
             }
           }
         }
       }
     }
   }
   rpc get-re-redundancy-information {
     description "Show RE failover redundancy information";
     junos:command "show chassis redundancy failover";
     output {
       choice output-tags {
         case output-tag {
           leaf output {
             type string;
           }
         }
         case actual-tag {
           anyxml re-redundancy-information;
         }
         case multichassis-tag {
           anyxml multi-routing-engine-results;
         }
       }
     }
   }
   rpc get-feb-redundancy-information {
     description "Show Forwarding Engine Board redundancy information";
     junos:command "show chassis redundancy feb";
     output {
       choice output-tags {
         case actual-tag {
           container feb-redundancy-information {
             uses feb-redundancy-information-block;
           }
         }
         case multichassis-tag {
           container multi-routing-engine-results {
             list multi-routing-engine-item {
               leaf re-name {
                 type string;
               }
               choice output-tags {
                 case actual-tag {
                   container feb-redundancy-information {
                     uses feb-redundancy-information-block;
                   }
                 }
               }
             }
           }
         }
       }
     }
   }
   rpc get-feb-redundancy-error-information {
     description "Show error information";
     junos:command "show chassis redundancy feb errors";
     output {
       choice output-tags {
         case actual-tag {
           container feb-redundancy-error-information {
             uses feb-redundancy-error-information-block;
           }
         }
         case multichassis-tag {
           container multi-routing-engine-results {
             list multi-routing-engine-item {
               leaf re-name {
                 type string;
               }
               choice output-tags {
                 case actual-tag {
                   container feb-redundancy-error-information {
                     uses feb-redundancy-error-information-block;
                   }
                 }
               }
             }
           }
         }
       }
     }
   }
   rpc get-feb-redundancy-group-information {
     description "Show FEB redundancy group information";
     junos:command "show chassis redundancy feb redundancy-group";
     input {
       leaf group {
         description "Name of FEB redundancy group";
         junos:cli-feature "nokeyword";
         type string;
         mandatory true;
       }
       leaf errors {
         description "Include error information";
         type empty;
       }
     }
     output {
       choice output-tags {
         case output-tag {
           leaf output {
             type string;
           }
         }
         case actual-tag {
           anyxml feb-redundancy-group-information;
         }
         case multichassis-tag {
           anyxml multi-routing-engine-results;
         }
       }
     }
   }
   rpc get-fpc-feb-connectivity-information {
     description "Show connectivity between Flexible PIC Concentrators and Forwarding Engine boards";
     junos:command "show chassis fpc-feb-connectivity";
     output {
       choice output-tags {
         case actual-tag {
           container fpc-feb-connectivity {
             uses fpc-feb-connectivity-block;
           }
         }
         case multichassis-tag {
           container multi-routing-engine-results {
             list multi-routing-engine-item {
               leaf re-name {
                 type string;
               }
               choice output-tags {
                 case actual-tag {
                   container fpc-feb-connectivity {
                     uses fpc-feb-connectivity-block;
                   }
                 }
               }
             }
           }
         }
       }
     }
   }
   rpc get-ioc-npc-connectivity-information {
     description "Show connectivity between IOC and NPC";
     junos:command "show chassis ioc-npc-connectivity";
     output {
       choice output-tags {
         case actual-tag {
           container ioc-npc-connectivity {
             uses ioc-npc-connectivity-block;
           }
         }
         case multichassis-tag {
           container multi-routing-engine-results {
             list multi-routing-engine-item {
               leaf re-name {
                 type string;
               }
               choice output-tags {
                 case actual-tag {
                   container ioc-npc-connectivity {
                     uses ioc-npc-connectivity-block;
                   }
                 }
               }
             }
           }
         }
       }
     }
   }
   rpc get-chassis-memory-usage-chassisd {
     description "Dump LMLD data to /var/log/chassisd_memory_usage";
     junos:command "show chassis memory-usage-chassisd";
     input {
       leaf root {
         junos:cli-feature "nokeyword";
         type string;
       }
     }
     output {
       choice output-tags {
         case output-tag {
           leaf output {
             type string;
           }
         }
         case multichassis-tag {
           anyxml multi-routing-engine-results;
         }
       }
     }
   }
   rpc get-chassis-zones-information {
     description "Show chassis cooling zones information";
     junos:command "show chassis zones";
     input {
       uses command-forwarding;
       leaf detail {
         description "Display detailed output";
         type empty;
       }
     }
     output {
       choice output-tags {
         case actual-tag {
           container chassis-zones-information {
             uses chassis-zones-information-block;
           }
         }
         case multichassis-tag {
           container multi-routing-engine-results {
             list multi-routing-engine-item {
               leaf re-name {
                 type string;
               }
               choice output-tags {
                 case actual-tag {
                   container chassis-zones-information {
                     uses chassis-zones-information-block;
                   }
                 }
               }
             }
           }
         }
       }
     }
   }
   rpc get-environment-information {
     description "Show component status and temperature, cooling system speeds";
     junos:command "show chassis environment";
     input {
       uses command-forwarding;
       leaf monitored {
         description "Show items whose temperatures are monitored";
         type empty;
       }
     }
     output {
       choice output-tags {
         case actual-tag {
           container environment-information {
             uses environment-information-block;
           }
         }
         case multichassis-tag {
           container multi-routing-engine-results {
             list multi-routing-engine-item {
               leaf re-name {
                 type string;
               }
               choice output-tags {
                 case actual-tag {
                   container environment-information {
                     uses environment-information-block;
                   }
                 }
               }
             }
           }
         }
       }
     }
   }
   rpc get-environment-sib-information {
     description "Show Switch Interface Board information";
     junos:command "show chassis environment sib";
     input {
       uses command-forwarding;
       leaf sib-slot {
         description "SIB slot number";
         junos:cli-feature "nokeyword";
         type union {
           type string {
             pattern "<.*>|$.*";
           }
           type uint32;
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-fan-information {
     description "Show fan status";
     junos:command "show chassis environment fan";
     input {
       uses command-forwarding;
       leaf slot {
         description "Fantray slot number";
         junos:cli-feature "nokeyword";
         type union {
           type string {
             pattern "<.*>|$.*";
           }
           type uint32 {
             range "0 .. 6";
           }
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-fpc-information {
     description "Show Flexible PIC Concentrator information";
     junos:command "show chassis environment fpc";
     input {
       uses command-forwarding;
       leaf fpc-slot {
         description "FPC slot number";
         junos:cli-feature "nokeyword";
         type union {
           type string {
             pattern "<.*>|$.*";
           }
           type uint32;
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-chassis-environment-fpc-satellite-info {
     description "Show environment FPC details";
     junos:command "show chassis environment fpc satellite";
     input {
       leaf fpc-slot {
         description "Satellite slot number";
         type union {
           type string {
             pattern "<.*>|$.*";
           }
           type uint16 {
             range "65 .. 254";
           }
         }
       }
       leaf device-alias {
         description "Device alias";
         type string;
       }
     }
     output {
       choice output-tags {
         case output-tag {
           leaf output {
             type string;
           }
         }
         case actual-tag {
           anyxml chassis-environment-fpc-satellite-information;
         }
         case multichassis-tag {
           anyxml multi-routing-engine-results;
         }
       }
     }
   }
   rpc get-environment-fpm-information {
     description "Show craft interface information";
     junos:command "show chassis environment fpm";
     input {
       uses command-forwarding;
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-mcs-information {
     description "Show Miscellaneous Control Subsystem information";
     junos:command "show chassis environment mcs";
     input {
       leaf slot {
         description "MCS slot number";
         junos:cli-feature "nokeyword";
         type union {
           type string {
             pattern "<.*>|$.*";
           }
           type uint32 {
             range "0 .. 1";
           }
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-pcg-information {
     description "Show Packet Forwarding Engine Clock Generator information";
     junos:command "show chassis environment pcg";
     input {
       leaf slot {
         description "PCG slot number";
         junos:cli-feature "nokeyword";
         type union {
           type string {
             pattern "<.*>|$.*";
           }
           type uint32 {
             range "0 .. 1";
           }
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-scg-information {
     description "Show SONET Clock Generator information";
     junos:command "show chassis environment scg";
     input {
       uses command-forwarding;
       leaf slot {
         description "SCG slot number";
         junos:cli-feature "nokeyword";
         type union {
           type string {
             pattern "<.*>|$.*";
           }
           type uint32 {
             range "0 .. 1";
           }
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-ccg-information {
     description "Show clock generator information";
     junos:command "show chassis environment ccg";
     input {
       leaf slot {
         description "CCG slot number";
         junos:cli-feature "nokeyword";
         type union {
           type string {
             pattern "<.*>|$.*";
           }
           type uint32 {
             range "0 .. 1";
           }
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-cb-information {
     description "Show Control Board information";
     junos:command "show chassis environment cb";
     input {
       uses command-forwarding;
       leaf slot {
         description "CB slot number";
         junos:cli-feature "nokeyword";
         type union {
           type string {
             pattern "<.*>|$.*";
           }
           type uint32;
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-psu-information {
     description "Show Power Supply Unit information";
     junos:command "show chassis environment psu";
     input {
       uses command-forwarding;
       leaf slot {
         description "PSU slot number";
         junos:cli-feature "nokeyword";
         type union {
           type string {
             pattern "<.*>|$.*";
           }
           type uint32;
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-power-supply-unit-information {
     description "Show power supply unit information";
     junos:command "show chassis environment power-supply-unit";
     input {
       uses command-forwarding;
       leaf slot {
         description "FPC slot number";
         type union {
           type string {
             pattern "<.*>|$.*";
           }
           type uint32;
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-pem-information {
     description "Show Power Entry Module information";
     junos:command "show chassis environment pem";
     input {
       uses command-forwarding;
       leaf slot {
         description "PEM slot number";
         junos:cli-feature "nokeyword";
         type union {
           type string {
             pattern "<.*>|$.*";
           }
           type uint32;
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-chassis-environment-pem-satellite-info {
     description "Show environment PEM details";
     junos:command "show chassis environment pem satellite";
     input {
       leaf fpc-slot {
         description "Satellite slot number";
         type union {
           type string {
             pattern "<.*>|$.*";
           }
           type uint16 {
             range "65 .. 254";
           }
         }
       }
       leaf device-alias {
         description "Device alias";
         type string;
       }
     }
     output {
       choice output-tags {
         case output-tag {
           leaf output {
             type string;
           }
         }
         case actual-tag {
           anyxml chassis-environment-pem-satellite-information;
         }
         case multichassis-tag {
           anyxml multi-routing-engine-results;
         }
       }
     }
   }
   rpc get-environment-psm-information {
     description "Show Power Supply Module information";
     junos:command "show chassis environment psm";
     input {
       uses command-forwarding;
       leaf slot {
         description "PSM slot number";
         junos:cli-feature "nokeyword";
         type union {
           type string {
             pattern "<.*>|$.*";
           }
           type uint32;
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-sfb-information {
     description "Show SFB status";
     junos:command "show chassis environment sfb";
     input {
       uses command-forwarding;
       leaf sfb-slot {
         description "SFB slot number";
         junos:cli-feature "nokeyword";
         type union {
           type string {
             pattern "<.*>|$.*";
           }
           type uint32;
         }
       }
     }
     output {
       choice output-tags {
         case actual-tag {
           container sfb-information {
             uses sfb-information-block;
           }
         }
         case multichassis-tag {
           container multi-routing-engine-results {
             list multi-routing-engine-item {
               leaf re-name {
                 type string;
               }
               choice output-tags {
                 case actual-tag {
                   container sfb-information {
                     uses sfb-information-block;
                   }
                 }
               }
             }
           }
         }
       }
     }
   }
   rpc get-environment-ftc-information {
     description "Show Fan Tray Controller information";
     junos:command "show chassis environment ftc";
     input {
       uses command-forwarding;
       leaf slot {
         description "FTC slot number";
         junos:cli-feature "nokeyword";
         type union {
           type string {
             pattern "<.*>|$.*";
           }
           type uint32;
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-adc-information {
     description "Show adc status";
     junos:command "show chassis environment adc";
     input {
       uses command-forwarding;
       leaf adc-slot {
         description "ADC slot number";
         junos:cli-feature "nokeyword";
         type union {
           type string {
             pattern "<.*>|$.*";
           }
           type uint32;
         }
       }
     }
     output {
       choice output-tags {
         case actual-tag {
           container sfb-information {
             uses sfb-information-block;
           }
         }
         case multichassis-tag {
           container multi-routing-engine-results {
             list multi-routing-engine-item {
               leaf re-name {
                 type string;
               }
               choice output-tags {
                 case actual-tag {
                   container sfb-information {
                     uses sfb-information-block;
                   }
                 }
               }
             }
           }
         }
       }
     }
   }
   rpc get-environment-pdu-information {
     description "Show Power Distribution Unit information";
     junos:command "show chassis environment pdu";
     input {
       leaf slot {
         description "PDU slot number";
         junos:cli-feature "nokeyword";
         type union {
           type string {
             pattern "<.*>|$.*";
           }
           type uint32 {
             range "0 .. 3";
           }
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-re-information {
     description "Show Routing Engine information";
     junos:command "show chassis environment routing-engine";
     input {
       uses command-forwarding;
       leaf slot {
         description "Routing Engine slot number";
         junos:cli-feature "nokeyword";
         type union {
           type string {
             pattern "<.*>|$.*";
           }
           type uint32;
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-chassis-environment-re-satellite-info {
     description "Show environment routing engine details";
     junos:command "show chassis environment routing-engine satellite";
     input {
       leaf fpc-slot {
         description "Satellite slot number";
         type union {
           type string {
             pattern "<.*>|$.*";
           }
           type uint16 {
             range "65 .. 254";
           }
         }
       }
       leaf device-alias {
         description "Device alias";
         type string;
       }
     }
     output {
       choice output-tags {
         case output-tag {
           leaf output {
             type string;
           }
         }
         case actual-tag {
           anyxml chassis-environment-routing-engine-satellite-information;
         }
         case multichassis-tag {
           anyxml multi-routing-engine-results;
         }
       }
     }
   }
   rpc get-environment-sfm-information {
     description "Show Switching and Forwarding Module information";
     junos:command "show chassis environment sfm";
     input {
       leaf sfm_plane {
         description "SFM slot number";
         junos:cli-feature "nokeyword";
         type union {
           type string {
             pattern "<.*>|$.*";
           }
           type uint32;
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-feb-information {
     description "Show Forwarding Engine Board information";
     junos:command "show chassis environment feb";
     input {
       leaf slot {
         description "FEB slot number";
         junos:cli-feature "nokeyword";
         type union {
           type string {
             pattern "<.*>|$.*";
           }
           type uint32;
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-cip-information {
     description "Show Connector Interface Panel Information";
     junos:command "show chassis environment cip";
     input {
       leaf slot {
         description "CIP slot number";
         junos:cli-feature "nokeyword";
         type union {
           type string {
             pattern "<.*>|$.*";
           }
           type uint32 {
             range "0 .. 1";
           }
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-service-node-information {
     description "Show Compute Node Environment information";
     junos:command "show chassis environment service-node";
     input {
       leaf slot {
         description "Service node slot number";
         type union {
           type string {
             pattern "<.*>|$.*";
           }
           type uint32 {
             range "0 .. 1";
           }
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-chassis-environment-satellite-information {
     description "Show environment details";
     junos:command "show chassis environment satellite";
     input {
       leaf fpc-slot {
         description "Satellite slot number";
         type union {
           type string {
             pattern "<.*>|$.*";
           }
           type uint16 {
             range "65 .. 254";
           }
         }
       }
       leaf device-alias {
         description "Device alias";
         type string;
       }
     }
     output {
       choice output-tags {
         case output-tag {
           leaf output {
             type string;
           }
         }
         case actual-tag {
           anyxml chassis-environment-satellite-information;
         }
         case multichassis-tag {
           anyxml multi-routing-engine-results;
         }
       }
     }
   }
   rpc get-firmware-information {
     description "Show firmware and operating system version for components";
     junos:command "show chassis firmware";
     input {
       uses command-forwarding;
       leaf fpc {
         description "Flexible PIC Controller slot number";
         type union {
           type string {
             pattern "<.*>|$.*";
           }
           type uint32;
         }
       }
     }
     output {
       choice output-tags {
         case actual-tag {
           container firmware-information {
             uses firmware-information-block;
           }
         }
         case multichassis-tag {
           container multi-routing-engine-results {
             list multi-routing-engine-item {
               leaf re-name {
                 type string;
               }
               choice output-tags {
                 case actual-tag {
                   container firmware-information {
                     uses firmware-information-block;
                   }
                 }
               }
             }
           }
         }
       }
     }
   }
   rpc get-firmware-information-detail {
     description "Show detailed output";
     junos:command "show chassis firmware detail";
     output {
       choice output-tags {
         case actual-tag {
           container hardware-version-information {
             uses hardware-version-information-block;
           }
         }
         case multichassis-tag {
           container multi-routing-engine-results {
             list multi-routing-engine-item {
               leaf re-name {
                 type string;
               }
               choice output-tags {
                 case actual-tag {
                   container hardware-version-information {
                     uses hardware-version-information-block;
                   }
                 }
               }
             }
           }
         }
       }
     }
   }
   rpc get-chassis-firmware-satellite-information {
     description "Show FPC firmware details";
     junos:command "show chassis firmware satellite";
     input {
       leaf fpc-slot {
         description "Satellite slot number";
         type union {
           type string {
             pattern "<.*>|$.*";
           }
           type uint16 {
             range "65 .. 254";
           }
         }
       }
       leaf device-alias {
         description "Device alias";
         type string;
       }
     }
     output {
       choice output-tags {
         case output-tag {
           leaf output {
             type string;
           }
         }
         case actual-tag {
           anyxml chassis-firmware-satellite-information;
         }
         case multichassis-tag {
           anyxml multi-routing-engine-results;
         }
       }
     }
   }
   rpc get-usb-storage-status {
     description "Show USB storage status";
     junos:command "show chassis usb storage";
     output {
       choice output-tags {
         case output-tag {
           leaf output {
             type string;
           }
         }
         case actual-tag {
           anyxml usb-storage-status;
         }
         case multichassis-tag {
           anyxml multi-routing-engine-results;
         }
       }
     }
   }
   rpc get-chassis-fabric-utilization-information {
     description "PFE fabric utilization";
     junos:command "show chassis utilization forwarding fabric";
     input {
       uses command-forwarding;
       leaf fpc {
         description "FPC number";
         type union {
           type string {
             pattern "<.*>|$.*";
           }
           type uint32 {
             range "0 .. 63";
           }
         }
       }
       leaf pfe {
         description "PFE number";
         type union {
           type string {
             pattern "<.*>|$.*";
           }
           type uint32 {
             range "0 .. 9";
           }
         }
       }
     }
     output {
       choice output-tags {
         case actual-tag {
           container chassis-fabric-utilization-information {
             uses chassis-fabric-utilization-information-block;
           }
         }
         case multichassis-tag {
           container multi-routing-engine-results {
             list multi-routing-engine-item {
               leaf re-name {
                 type string;
               }
               choice output-tags {
                 case actual-tag {
                   container chassis-fabric-utilization-information {
                     uses chassis-fabric-utilization-information-block;
                   }
                 }
               }
             }
           }
         }
       }
     }
   }
   rpc get-fpc-information {
     description "Show Flexible PIC Concentrator status";
     junos:command "show chassis fpc";
     input {
       uses command-forwarding;
       leaf detail {
         description "Display detailed output";
         type empty;
       }
       leaf fpc-slot {
         description "FPC slot number";
         junos:cli-feature "nokeyword";
         type union {
           type string {
             pattern "<.*>|$.*";
           }
           type uint32;
         }
       }
     }
     output {
       choice output-tags {
         case actual-tag {
           container fpc-information {
             uses fpc-information-block;
           }
         }
         case multichassis-tag {
           container multi-routing-engine-results {
             list multi-routing-engine-item {
               leaf re-name {
                 type string;
               }
               choice output-tags {
                 case actual-tag {
                   container fpc-information {
                     uses fpc-information-block;
                   }
                 }
               }
             }
           }
         }
       }
     }
   }
   rpc get-pic-information {
     description "Show Physical Interface Cards installed in FPC";
     junos:command "show chassis fpc pic-status";
     input {
       uses command-forwarding;
       leaf slot {
         description "FPC slot number";
         junos:cli-feature "nokeyword";
         type union {
           type string {
             pattern "<.*>|$.*";
           }
           type uint32;
         }
       }
     }
     output {
       choice output-tags {
         case actual-tag {
           container fpc-information {
             uses fpc-information-block;
           }
         }
         case multichassis-tag {
           container multi-routing-engine-results {
             list multi-routing-engine-item {
               leaf re-name {
                 type string;
               }
               choice output-tags {
                 case actual-tag {
                   container fpc-information {
                     uses fpc-information-block;
                   }
                 }
               }
             }
           }
         }
       }
     }
   }
   rpc get-mic-information {
     description "Show Modular Interface Cards installed in FPC";
     junos:command "show chassis fpc mic-status";
     input {
       leaf slot {
         description "FPC slot number";
         junos:cli-feature "nokeyword";
         type union {
           type string {
             pattern "<.*>|$.*";
           }
           type uint32;
         }
       }
     }
     output {
       choice output-tags {
         case actual-tag {
           container fpc-information {
             uses fpc-information-block;
           }
         }
         case multichassis-tag {
           container multi-routing-engine-results {
             list multi-routing-engine-item {
               leaf re-name {
                 type string;
               }
               choice output-tags {
                 case actual-tag {
                   container fpc-information {
                     uses fpc-information-block;
                   }
                 }
               }
             }
           }
         }
       }
     }
   }
   rpc get-fpc-ether-types-information {
     description "Show Ether Types";
     junos:command "show chassis fpc ether-types";
     input {
       leaf slot {
         description "FPC slot number";
         junos:cli-feature "nokeyword";
         type union {
           type string {
             pattern "<.*>|$.*";
           }
           type uint32;
         }
       }
     }
     output {
       choice output-tags {
         case actual-tag {
           container fpc-ether-types-information {
             uses fpc-ether-types-information-block;
           }
         }
         case multichassis-tag {
           container multi-routing-engine-results {
             list multi-routing-engine-item {
               leaf re-name {
                 type string;
               }
               choice output-tags {
                 case actual-tag {
                   container fpc-ether-types-information {
                     uses fpc-ether-types-information-block;
                   }
                 }
               }
             }
           }
         }
       }
     }
   }
   rpc get-fpc-port-information {
     description "Show Port status installed in FPC";
     junos:command "show chassis fpc port-status";
     input {
       leaf slot {
         description "FPC slot number";
         junos:cli-feature "nokeyword";
         type union {
           type string {
             pattern "<.*>|$.*";
           }
           type uint32;
         }
       }
     }
     output {
       choice output-tags {
         case actual-tag {
           container fpc-port-information {
             uses fpc-port-information-block;
           }
         }
         case multichassis-tag {
           container multi-routing-engine-results {
             list multi-routing-engine-item {
               leaf re-name {
                 type string;
               }
               choice output-tags {
                 case actual-tag {
                   container fpc-port-information {
                     uses fpc-port-information-block;
                   }
                 }
               }
             }
           }
         }
       }
     }
   }
   rpc get-fpc-error-information {
     description "Show ASIC errors on all the FPC's";
     junos:command "show chassis fpc errors";
     input {
       uses command-forwarding;
       leaf fpc-slot {
         description "FPC slot number";
         junos:cli-feature "nokeyword";
         type union {
           type string {
             pattern "<.*>|$.*";
           }
           type uint32;
         }
       }
       leaf detail {
         description "Display detailed output";
         type empty;
       }
       leaf scope {
         description "Error scope";
         type enumeration {
           enum "board" {
             description "Show board errors";
           }
           enum "pfe" {
             description "Show pfe errors";
           }
         }
       }
       leaf category {
         description "Error category";
         type enumeration {
           enum "functional" {
             description "Functional category errors";
           }
           enum "memory" {
             description "Memory category errors";
           }
           enum "io" {
             description "Io category errors";
           }
           enum "storage" {
             description "Storage category errors";
           }
           enum "switch" {
             description "Switch category errors";
           }
           enum "processing" {
             description "Processing category errors";
           }
         }
       }
     }
     output {
       choice output-tags {
         case actual-tag {
           container fpc-error-information {
             uses fpc-error-information-block;
           }
         }
         case multichassis-tag {
           container multi-routing-engine-results {
             list multi-routing-engine-item {
               leaf re-name {
                 type string;
               }
               choice output-tags {
                 case actual-tag {
                   container fpc-error-information {
                     uses fpc-error-information-block;
                   }
                 }
               }
             }
           }
         }
       }
     }
   }
   rpc get-fpc-error-i2c {
     description "Display I2C error statistics";
     junos:command "show chassis fpc errors i2c";
     input {
       uses command-forwarding;
       leaf fpc-slot {
         description "FPC slot number";
         type union {
           type string {
             pattern "<.*>|$.*";
           }
           type uint32;
         }
       }
     }
     output {
       choice output-tags {
         case output-tag {
           leaf output {
             type string;
           }
         }
         case actual-tag {
           anyxml fpc-tvp-error-information;
         }
         case multichassis-tag {
           anyxml multi-routing-engine-results;
         }
       }
     }
   }
   rpc get-fpc-optical-information {
     description "Show optical properties of the card";
     junos:command "show chassis fpc optical-properties";
     output {
       choice output-tags {
         case actual-tag {
           container fpc-optical-information {
             uses fpc-optical-information-block;
           }
         }
         case multichassis-tag {
           container multi-routing-engine-results {
             list multi-routing-engine-item {
               leaf re-name {
                 type string;
               }
               choice output-tags {
                 case actual-tag {
                   container fpc-optical-information {
                     uses fpc-optical-information-block;
                   }
                 }
               }
             }
           }
         }
       }
     }
   }
   rpc get-fpc-optical-mfg-info-information {
     description "Show mfg-info of optical module";
     junos:command "show chassis fpc optical-properties mfg-info";
     input {
       leaf fpc-slot {
         description "FPC slot number";
         type union {
           type string {
             pattern "<.*>|$.*";
           }
           type uint32;
         }
         mandatory true;
       }
     }
     output {
       choice output-tags {
         case output-tag {
           leaf output {
             type string;
           }
         }
         case actual-tag {
           anyxml fpc-optical-mfg-info-information;
         }
         case multichassis-tag {
           anyxml multi-routing-engine-results;
         }
       }
     }
   }
   rpc get-fpc-optical-status-information {
     description "Show status of optical module";
     junos:command "show chassis fpc optical-properties status";
     input {
       leaf fpc-slot {
         description "FPC slot number";
         type union {
           type string {
             pattern "<.*>|$.*";
           }
           type uint32;
         }
         mandatory true;
       }
     }
     output {
       choice output-tags {
         case output-tag {
           leaf output {
             type string;
           }
         }
         case actual-tag {
           anyxml fpc-optical-status-information;
         }
         case multichassis-tag {
           anyxml multi-routing-engine-results;
         }
       }
     }
   }
   rpc get-fpc-optical-alarms-information {
     description "Show alarms of optical module";
     junos:command "show chassis fpc optical-properties alarms";
     input {
       leaf fpc-slot {
         description "FPC slot number";
         type union {
           type string {
             pattern "<.*>|$.*";
           }
           type uint32;
         }
         mandatory true;
       }
     }
     output {
       choice output-tags {
         case output-tag {
           leaf output {
             type string;
           }
         }
         case actual-tag {
           anyxml fpc-optical-alarms-information;
         }
         case multichassis-tag {
           anyxml multi-routing-engine-results;
         }
       }
     }
   }
   rpc get-fpc-optical-edfa-information {
     description "Show edfa of optical module";
     junos:command "show chassis fpc optical-properties edfa";
     input {
       leaf fpc-slot {
         description "FPC slot number";
         type union {
           type string {
             pattern "<.*>|$.*";
           }
           type uint32;
         }
         mandatory true;
       }
     }
     output {
       choice output-tags {
         case output-tag {
           leaf output {
             type string;
           }
         }
         case actual-tag {
           anyxml fpc-optical-edfa-information;
         }
         case multichassis-tag {
           anyxml multi-routing-engine-results;
         }
       }
     }
   }
   rpc get-fpc-optical-ocm-information {
     description "Show ocm of optical module";
     junos:command "show chassis fpc optical-properties ocm";
     input {
       leaf fpc-slot {
         description "FPC slot number";
         type union {
           type string {
             pattern "<.*>|$.*";
           }
           type uint32;
         }
         mandatory true;
       }
     }
     output {
       choice output-tags {
         case output-tag {
           leaf output {
             type string;
           }
         }
         case actual-tag {
           anyxml fpc-optical-ocm-information;
         }
         case multichassis-tag {
           anyxml multi-routing-engine-results;
         }
       }
     }
   }
   rpc get-fpc-optical-wss-information {
     description "Show wss of optical module";
     junos:command "show chassis fpc optical-properties wss";
     input {
       leaf fpc-slot {
         description "FPC slot number";
         type union {
           type string {
             pattern "<.*>|$.*";
           }
           type uint32;
         }
         mandatory true;
       }
     }
     output {
       choice output-tags {
         case output-tag {
           leaf output {
             type string;
           }
         }
         case actual-tag {
           anyxml fpc-optical-wss-information;
         }
         case multichassis-tag {
           anyxml multi-routing-engine-results;
         }
       }
     }
   }
   rpc get-fpc-optical-pm-current-information {
     description "Show pm-current of optical module";
     junos:command "show chassis fpc optical-properties pm-current";
     input {
       leaf fpc-slot {
         description "FPC slot number";
         type union {
           type string {
             pattern "<.*>|$.*";
           }
           type uint32;
         }
         mandatory true;
       }
     }
     output {
       choice output-tags {
         case output-tag {
           leaf output {
             type string;
           }
         }
         case actual-tag {
           anyxml fpc-optical-pm-current-information;
         }
         case multichassis-tag {
           anyxml multi-routing-engine-results;
         }
       }
     }
   }
   rpc get-fpc-optical-pm-interval-information {
     description "Show pm-interval of optical module";
     junos:command "show chassis fpc optical-properties pm-interval";
     input {
       leaf fpc-slot {
         description "FPC slot number";
         type union {
           type string {
             pattern "<.*>|$.*";
           }
           type uint32;
         }
         mandatory true;
       }
     }
     output {
       choice output-tags {
         case output-tag {
           leaf output {
             type string;
           }
         }
         case actual-tag {
           anyxml fpc-optical-pm-interval-information;
         }
         case multichassis-tag {
           anyxml multi-routing-engine-results;
         }
       }
     }
   }
   rpc get-fpc-optical-pm-currentday-information {
     description "Show pm-currentday of optical module";
     junos:command "show chassis fpc optical-properties pm-currentday";
     input {
       leaf fpc-slot {
         description "FPC slot number";
         type union {
           type string {
             pattern "<.*>|$.*";
           }
           type uint32;
         }
         mandatory true;
       }
     }
     output {
       choice output-tags {
         case output-tag {
           leaf output {
             type string;
           }
         }
         case actual-tag {
           anyxml fpc-optical-pm-currentday-information;
         }
         case multichassis-tag {
           anyxml multi-routing-engine-results;
         }
       }
     }
   }
   rpc get-fpc-optical-pm-previousday-information {
     description "Show pm-previousday of optical module";
     junos:command "show chassis fpc optical-properties pm-previousday";
     input {
       leaf fpc-slot {
         description "FPC slot number";
         type union {
           type string {
             pattern "<.*>|$.*";
           }
           type uint32;
         }
         mandatory true;
       }
     }
     output {
       choice output-tags {
         case output-tag {
           leaf output {
             type string;
           }
         }
         case actual-tag {
           anyxml fpc-optical-pm-previousday-information;
         }
         case multichassis-tag {
           anyxml multi-routing-engine-results;
         }
       }
     }
   }
   rpc get-fpc-optical-amplifier-topology-information {
     description "Show amplifier-topology of optical module";
     junos:command "show chassis fpc optical-properties amplifier-topology";
     input {
       leaf fpc-slot {
         description "FPC slot number";
         type union {
           type string {
             pattern "<.*>|$.*";
           }
           type uint32;
         }
         mandatory true;
       }
     }
     output {
       choice output-tags {
         case output-tag {
           leaf output {
             type string;
           }
         }
         case actual-tag {
           anyxml fpc-optical-amplifier-topology-information;
         }
         case multichassis-tag {
           anyxml multi-routing-engine-results;
         }
       }
     }
   }
   rpc get-fpc-optical-topology-information {
     description "Show IPLC Topology Information";
     junos:command "show chassis fpc optical-properties topology";
     input {
       leaf fpc-slot {
         description "FPC slot number";
         type union {
           type string {
             pattern "<.*>|$.*";
           }
           type uint32;
         }
         mandatory true;
       }
       leaf detail {
         description "Show IPLC Topology Detailed Information";
         type empty;
       }
     }
     output {
       choice output-tags {
         case output-tag {
           leaf output {
             type string;
           }
         }
         case actual-tag {
           anyxml fpc-optical-topology-information;
         }
         case multichassis-tag {
           anyxml multi-routing-engine-results;
         }
       }
     }
   }
   rpc get-fpc-optical-amplifier-chain-information {
     description "Show in-line amplifier amplifier-chain information";
     junos:command "show chassis fpc optical-properties amplifier-chain ila";
     output {
       choice output-tags {
         case output-tag {
           leaf output {
             type string;
           }
         }
         case actual-tag {
           anyxml fpc-optical-amplifier-chain-information;
         }
         case multichassis-tag {
           anyxml multi-routing-engine-results;
         }
       }
     }
   }
   rpc get-fpc-optical-ila-summary-information {
     description "Show summary of ila module";
     junos:command "show chassis fpc optical-properties amplifier-chain ila summary";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output-tags {
         case output-tag {
           leaf output {
             type string;
           }
         }
         case actual-tag {
           anyxml fpc-optical-ila-summary-information;
         }
         case multichassis-tag {
           anyxml multi-routing-engine-results;
         }
       }
     }
   }
   rpc get-fpc-optical-ila-edfa-information {
     description "Show edfa of ila module";
     junos:command "show chassis fpc optical-properties amplifier-chain ila edfa";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output-tags {
         case output-tag {
           leaf output {
             type string;
           }
         }
         case actual-tag {
           anyxml fpc-optical-ila-edfa-information;
         }
         case multichassis-tag {
           anyxml multi-routing-engine-results;
         }
       }
     }
   }
   rpc get-fpc-optical-ila-osc-information {
     description "Show osc of ila module";
     junos:command "show chassis fpc optical-properties amplifier-chain ila osc";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output-tags {
         case output-tag {
           leaf output {
             type string;
           }
         }
         case actual-tag {
           anyxml fpc-optical-ila-osc-information;
         }
         case multichassis-tag {
           anyxml multi-routing-engine-results;
         }
       }
     }
   }
   rpc get-fpc-optical-ila-voa-information {
     description "Show voa of ila module";
     junos:command "show chassis fpc optical-properties amplifier-chain ila voa";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output-tags {
         case output-tag {
           leaf output {
             type string;
           }
         }
         case actual-tag {
           anyxml fpc-optical-ila-voa-information;
         }
         case multichassis-tag {
           anyxml multi-routing-engine-results;
         }
       }
     }
   }
   rpc get-fpc-optical-ila-alarms-information {
     description "Show alarms of ila module";
     junos:command "show chassis fpc optical-properties amplifier-chain ila alarms";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output-tags {
         case output-tag {
           leaf output {
             type string;
           }
         }
         case actual-tag {
           anyxml fpc-optical-ila-alarms-information;
         }
         case multichassis-tag {
           anyxml multi-routing-engine-results;
         }
       }
     }
   }
   rpc get-fpc-optical-ila-pm-current-information {
     description "Show pm-current of ila module";
     junos:command "show chassis fpc optical-properties amplifier-chain ila pm-current";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output-tags {
         case output-tag {
           leaf output {
             type string;
           }
         }
         case actual-tag {
           anyxml fpc-optical-ila-pm-current-information;
         }
         case multichassis-tag {
           anyxml multi-routing-engine-results;
         }
       }
     }
   }
   rpc get-fpc-optical-ila-pm-interval-information {
     description "Show pm-interval of ila module";
     junos:command "show chassis fpc optical-properties amplifier-chain ila pm-interval";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output-tags {
         case output-tag {
           leaf output {
             type string;
           }
         }
         case actual-tag {
           anyxml fpc-optical-ila-pm-interval-information;
         }
         case multichassis-tag {
           anyxml multi-routing-engine-results;
         }
       }
     }
   }
   rpc get-fpc-optical-ila-pm-currentday-information {
     description "Show pm-currentday of ila module";
     junos:command "show chassis fpc optical-properties amplifier-chain ila pm-currentday";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output-tags {
         case output-tag {
           leaf output {
             type string;
           }
         }
         case actual-tag {
           anyxml fpc-optical-ila-pm-currentday-information;
         }
         case multichassis-tag {
           anyxml multi-routing-engine-results;
         }
       }
     }
   }
   rpc get-fpc-optical-ila-pm-previousday-information {
     description "Show pm-previousday of ila module";
     junos:command "show chassis fpc optical-properties amplifier-chain ila pm-previousday";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output-tags {
         case output-tag {
           leaf output {
             type string;
           }
         }
         case actual-tag {
           anyxml fpc-optical-ila-pm-previousday-information;
         }
         case multichassis-tag {
           anyxml multi-routing-engine-results;
         }
       }
     }
   }
   rpc get-global-pfe-id {
     description "Show Global PFE IDs";
     junos:command "show chassis fpc global-pfe-id";
     input {
       uses command-forwarding;
     }
     output {
       choice output-tags {
         case actual-tag {
           container global-pfe-id-information {
             uses global-pfe-id-information-block;
           }
         }
         case multichassis-tag {
           container multi-routing-engine-results {
             list multi-routing-engine-item {
               leaf re-name {
                 type string;
               }
               choice output-tags {
                 case actual-tag {
                   container global-pfe-id-information {
                     uses global-pfe-id-information-block;
                   }
                 }
               }
             }
           }
         }
       }
     }
   }
   rpc get-adc-information {
     description "Show ADC status";
     junos:command "show chassis adc";
     input {
       uses command-forwarding;
     }
     output {
       choice output-tags {
         case actual-tag {
           container adc-information {
             uses adc-information-block;
           }
         }
         case multichassis-tag {
           container multi-routing-engine-results {
             list multi-routing-engine-item {
               leaf re-name {
                 type string;
               }
               choice output-tags {
                 case actual-tag {
                   container adc-information {
                     uses adc-information-block;
                   }
                 }
               }
             }
           }
         }
       }
     }
   }
   rpc get-vcpu-information {
     description "Show Visibility CPU status";
     junos:command "show chassis vcpu";
     input {
       uses command-forwarding;
       leaf detail {
         description "Display detailed output";
         type empty;
       }
       leaf slot {
         description "VCPU slot number";
         junos:cli-feature "nokeyword";
         type union {
           type string {
             pattern "<.*>|$.*";
           }
           type uint32;
         }
       }
     }
     output {
       choice output-tags {
         case output-tag {
           leaf output {
             type string;
           }
         }
         case actual-tag {
           anyxml vcpu-information;
         }
         case multichassis-tag {
           anyxml multi-routing-engine-results;
         }
       }
     }
   }
   rpc get-pic-detail {
     description "Show Physical Interface Card state, type, and uptime";
     junos:command "show chassis pic";
     input {
       uses command-forwarding;
       leaf fpc-slot {
         description "Slot number of FPC that houses PIC";
         type union {
           type string {
             pattern "<.*>|$.*";
           }
           type uint32;
         }
       }
       leaf pic-slot {
         description "PIC slot number";
         type union {
           type string {
             pattern "<.*>|$.*";
           }
           type int32;
         }
         mandatory true;
       }
     }
     output {
       choice output-tags {
         case actual-tag {
           container fpc-information {
             uses fpc-information-block;
           }
         }
         case multichassis-tag {
           container multi-routing-engine-results {
             list multi-routing-engine-item {
               leaf re-name {
                 type string;
               }
               choice output-tags {
                 case actual-tag {
                   container fpc-information {
                     uses fpc-information-block;
                   }
                 }
               }
             }
           }
         }
       }
     }
   }
   rpc get-pic-transport-information {
     description "Show Physical Interface Card transport information";
     junos:command "show chassis pic transport";
     input {
       leaf fpc-slot {
         description "Slot number of FPC that houses PIC";
         type union {
           type string {
             pattern "<.*>|$.*";
           }
           type uint32;
         }
         mandatory true;
       }
       leaf pic-slot {
         description "PIC slot number";
         type union {
           type string {
             pattern "<.*>|$.*";
           }
           type int32;
         }
         mandatory true;
       }
     }
     output {
       choice output-tags {
         case output-tag {
           leaf output {
             type string;
           }
         }
         case actual-tag {
           anyxml pic-transport-information;
         }
         case multichassis-tag {
           anyxml multi-routing-engine-results;
         }
       }
     }
   }
   rpc get-port-profile-speed-information {
     description "Show Physical Interface Card Port Profile information";
     junos:command "show chassis pic port-profile";
     input {
       leaf fpc-slot {
         description "Slot number of FPC that houses PIC";
         type union {
           type string {
             pattern "<.*>|$.*";
           }
           type uint32;
         }
         mandatory true;
       }
       leaf pic-slot {
         description "PIC slot number";
         type union {
           type string {
             pattern "<.*>|$.*";
           }
           type int32;
         }
         mandatory true;
       }
     }
     output {
       choice output-tags {
         case output-tag {
           leaf output {
             type string;
           }
         }
         case actual-tag {
           anyxml port-profile-speed-information;
         }
         case multichassis-tag {
           anyxml multi-routing-engine-results;
         }
       }
     }
   }
   rpc get-spmb-information {
     description "Show Switch Processor Mezzanine Board status";
     junos:command "show chassis spmb";
     input {
       uses command-forwarding;
     }
     output {
       choice output-tags {
         case actual-tag {
           container spmb-information {
             uses spmb-information-block;
           }
         }
         case multichassis-tag {
           container multi-routing-engine-results {
             list multi-routing-engine-item {
               leaf re-name {
                 type string;
               }
               choice output-tags {
                 case actual-tag {
                   container spmb-information {
                     uses spmb-information-block;
                   }
                 }
               }
             }
           }
         }
       }
     }
   }
   rpc get-spmb-sib-information {
     description "Show Switch Interface Board status";
     junos:command "show chassis spmb sibs";
     input {
       uses command-forwarding;
     }
     output {
       choice output-tags {
         case actual-tag {
           container sib-information {
             uses sib-information-block;
           }
         }
         case multichassis-tag {
           container multi-routing-engine-results {
             list multi-routing-engine-item {
               leaf re-name {
                 type string;
               }
               choice output-tags {
                 case actual-tag {
                   container sib-information {
                     uses sib-information-block;
                   }
                 }
               }
             }
           }
         }
       }
     }
   }
   rpc get-spmb-error-information {
     description "Show errors on SPMB";
     junos:command "show chassis spmb errors";
     output {
       choice output-tags {
         case actual-tag {
           container spmb-error-information {
             uses spmb-error-information-block;
           }
         }
         case multichassis-tag {
           container multi-routing-engine-results {
             list multi-routing-engine-item {
               leaf re-name {
                 type string;
               }
               choice output-tags {
                 case actual-tag {
                   container spmb-error-information {
                     uses spmb-error-information-block;
                   }
                 }
               }
             }
           }
         }
       }
     }
   }
   rpc get-sib-information {
     description "Show Switch Interface Board status";
     junos:command "show chassis sibs";
     input {
       uses command-forwarding;
       leaf detail {
         description "Display detailed output";
         type empty;
       }
       leaf slot {
         description "SIB slot number";
         type union {
           type string {
             pattern "<.*>|$.*";
           }
           type uint32;
         }
       }
     }
     output {
       choice output-tags {
         case actual-tag {
           container sib-information {
             uses sib-information-block;
           }
         }
         case multichassis-tag {
           container multi-routing-engine-results {
             list multi-routing-engine-item {
               leaf re-name {
                 type string;
               }
               choice output-tags {
                 case actual-tag {
                   container sib-information {
                     uses sib-information-block;
                   }
                 }
               }
             }
           }
         }
       }
     }
   }
   rpc get-sibs-errors {
     description "Show ASIC errors on sib";
     junos:command "show chassis sibs errors";
     input {
       leaf sib-slot {
         description "SIB slot number";
         type union {
           type string {
             pattern "<.*>|$.*";
           }
           type uint32;
         }
       }
     }
     output {
       choice output-tags {
         case actual-tag {
           container sib-information {
             uses sib-information-block;
           }
         }
         case multichassis-tag {
           container multi-routing-engine-results {
             list multi-routing-engine-item {
               leaf re-name {
                 type string;
               }
               choice output-tags {
                 case actual-tag {
                   container sib-information {
                     uses sib-information-block;
                   }
                 }
               }
             }
           }
         }
       }
     }
   }
   rpc get-replacement-status {
     description "Show fru replacement status";
     junos:command "show chassis fru";
     input {
       leaf replacement {
         description "Shows the replacemeent status";
         type enumeration {
           enum "status" {
             description "Shows the fru replacement status";
           }
         }
         mandatory true;
       }
     }
     output {
       choice output-tags {
         case output-tag {
           leaf output {
             type string;
           }
         }
         case multichassis-tag {
           anyxml multi-routing-engine-results;
         }
       }
     }
   }
   rpc get-sfb-information {
     description "Show Switch Fabric Board status";
     junos:command "show chassis sfb";
     input {
       uses command-forwarding;
       leaf slot {
         description "SFB slot number";
         type union {
           type string {
             pattern "<.*>|$.*";
           }
           type uint32;
         }
       }
     }
     output {
       choice output-tags {
         case actual-tag {
           container sfb-information {
             uses sfb-information-block;
           }
         }
         case multichassis-tag {
           container multi-routing-engine-results {
             list multi-routing-engine-item {
               leaf re-name {
                 type string;
               }
               choice output-tags {
                 case actual-tag {
                   container sfb-information {
                     uses sfb-information-block;
                   }
                 }
               }
             }
           }
         }
       }
     }
   }
   rpc get-sfb-errors {
     description "Show ASIC errors on sfb";
     junos:command "show chassis sfb errors";
     input {
       leaf slot {
         description "SFB slot number";
         type union {
           type string {
             pattern "<.*>|$.*";
           }
           type uint32;
         }
       }
     }
     output {
       choice output-tags {
         case actual-tag {
           container sfb-information {
             uses sfb-information-block;
           }
         }
         case multichassis-tag {
           container multi-routing-engine-results {
             list multi-routing-engine-item {
               leaf re-name {
                 type string;
               }
               choice output-tags {
                 case actual-tag {
                   container sfb-information {
                     uses sfb-information-block;
                   }
                 }
               }
             }
           }
         }
       }
     }
   }
   rpc get-fru-information {
     description "Show Line Card Chassis (LCC) status";
     junos:command "show chassis lccs";
     output {
       choice output-tags {
         case actual-tag {
           container fru-information {
             uses fru-information-block;
           }
         }
         case multichassis-tag {
           container multi-routing-engine-results {
             list multi-routing-engine-item {
               leaf re-name {
                 type string;
               }
               choice output-tags {
                 case actual-tag {
                   container fru-information {
                     uses fru-information-block;
                   }
                 }
               }
             }
           }
         }
       }
     }
   }
   rpc get-chassis-lcc-mode-information {
     description "Show chassis lcc mode information";
     junos:command "show chassis lcc-mode";
     input {
       leaf lcc {
         description "LCC number";
         type union {
           type string {
             pattern "<.*>|$.*";
           }
           type uint32;
         }
       }
     }
     output {
       choice output-tags {
         case actual-tag {
           container chassis-lcc-mode-information {
             uses chassis-lcc-mode-information-block;
           }
         }
         case multichassis-tag {
           container multi-routing-engine-results {
             list multi-routing-engine-item {
               leaf re-name {
                 type string;
               }
               choice output-tags {
                 case actual-tag {
                   container chassis-lcc-mode-information {
                     uses chassis-lcc-mode-information-block;
                   }
                 }
               }
             }
           }
         }
       }
     }
   }
   rpc get-psd-information {
     description "Show Protected System Domain (PSD) status";
     junos:command "show chassis psd";
     output {
       choice output-tags {
         case actual-tag {
           container psd-information {
             uses psd-information-block;
           }
         }
         case multichassis-tag {
           container multi-routing-engine-results {
             list multi-routing-engine-item {
               leaf re-name {
                 type string;
               }
               choice output-tags {
                 case actual-tag {
                   container psd-information {
                     uses psd-information-block;
                   }
                 }
               }
             }
           }
         }
       }
     }
   }
   rpc get-gnf-information {
     description "Show Network Slices status";
     junos:command "show chassis network-slices";
     output {
       choice output-tags {
         case actual-tag {
           container gnf-information {
             uses gnf-information-block;
           }
         }
         case multichassis-tag {
           container multi-routing-engine-results {
             list multi-routing-engine-item {
               leaf re-name {
                 type string;
               }
               choice output-tags {
                 case actual-tag {
                   container gnf-information {
                     uses gnf-information-block;
                   }
                 }
               }
             }
           }
         }
       }
     }
   }
   rpc get-gnf-fpcs-information {
     description "Show FPCs assigned to GNFs";
     junos:command "show chassis network-slices fpcs";
     output {
       choice output-tags {
         case actual-tag {
           container gnf-fpcs-information {
             uses gnf-fpcs-information-block;
           }
         }
         case multichassis-tag {
           container multi-routing-engine-results {
             list multi-routing-engine-item {
               leaf re-name {
                 type string;
               }
               choice output-tags {
                 case actual-tag {
                   container gnf-fpcs-information {
                     uses gnf-fpcs-information-block;
                   }
                 }
               }
             }
           }
         }
       }
     }
   }
   rpc get-network-slice-description {
     description "Show GNF description";
     junos:command "show chassis network-slices gnf";
     input {
       leaf gnf-slot {
         description "GNF slot number";
         junos:cli-feature "nokeyword";
         type union {
           type string {
             pattern "<.*>|$.*";
           }
           type uint32 {
             range "1 .. 10";
           }
         }
       }
     }
     output {
       choice output-tags {
         case actual-tag {
           container gnf-description {
             uses gnf-description-block;
           }
         }
         case multichassis-tag {
           container multi-routing-engine-results {
             list multi-routing-engine-item {
               leaf re-name {
                 type string;
               }
               choice output-tags {
                 case actual-tag {
                   container gnf-description {
                     uses gnf-description-block;
                   }
                 }
               }
             }
           }
         }
       }
     }
   }
   rpc get-afs-information {
     description "Show AFs information";
     junos:command "show chassis network-slices af-info";
     output {
       choice output-tags {
         case actual-tag {
           container afs-information {
             uses afs-information-block;
           }
         }
         case multichassis-tag {
           container multi-routing-engine-results {
             list multi-routing-engine-item {
               leaf re-name {
                 type string;
               }
               choice output-tags {
                 case actual-tag {
                   container afs-information {
                     uses afs-information-block;
                   }
                 }
               }
             }
           }
         }
       }
     }
   }
   rpc get-jnu-satellites-information {
     description "Show jnu satellites information";
     junos:command "show chassis jnu satellites";
     output {
       choice output-tags {
         case actual-tag {
           container jnu-satellites-information {
             uses jnu-satellites-information-block;
           }
         }
         case multichassis-tag {
           container multi-routing-engine-results {
             list multi-routing-engine-item {
               leaf re-name {
                 type string;
               }
               choice output-tags {
                 case actual-tag {
                   container jnu-satellites-information {
                     uses jnu-satellites-information-block;
                   }
                 }
               }
             }
           }
         }
       }
     }
   }
   rpc get-jnu-role-information {
     description "Show jnu role";
     junos:command "show chassis jnu role";
     output {
       choice output-tags {
         case actual-tag {
           container jnu-role-information {
             uses jnu-role-information-block;
           }
         }
         case multichassis-tag {
           container multi-routing-engine-results {
             list multi-routing-engine-item {
               leaf re-name {
                 type string;
               }
               choice output-tags {
                 case actual-tag {
                   container jnu-role-information {
                     uses jnu-role-information-block;
                   }
                 }
               }
             }
           }
         }
       }
     }
   }
   rpc get-chassis-fabric-mesh-topo-information {
     description "Show mesh topology";
     junos:command "show chassis fabric mesh topology";
     output {
       choice output-tags {
         case actual-tag {
           container chassis-fabric-mesh-topo-information {
             uses chassis-fabric-mesh-topo-information-block;
           }
         }
         case multichassis-tag {
           container multi-routing-engine-results {
             list multi-routing-engine-item {
               leaf re-name {
                 type string;
               }
               choice output-tags {
                 case actual-tag {
                   container chassis-fabric-mesh-topo-information {
                     uses chassis-fabric-mesh-topo-information-block;
                   }
                 }
               }
             }
           }
         }
       }
     }
   }
   rpc get-chassis-fabric-mesh-feb-information {
     description "Show summary fabric management FEB state";
     junos:command "show chassis fabric mesh feb";
     output {
       choice output-tags {
         case actual-tag {
           container chassis-fabric-mesh-feb-information {
             uses chassis-fabric-mesh-feb-information-block;
           }
         }
         case multichassis-tag {
           container multi-routing-engine-results {
             list multi-routing-engine-item {
               leaf re-name {
                 type string;
               }
               choice output-tags {
                 case actual-tag {
                   container chassis-fabric-mesh-feb-information {
                     uses chassis-fabric-mesh-feb-information-block;
                   }
                 }
               }
             }
           }
         }
       }
     }
   }
   rpc get-fm-fpc-state-information {
     description "Show summary fabric management FPC state from Routing Engine";
     junos:command "show chassis fabric fpcs";
     input {
       uses command-forwarding;
       leaf slot {
         description "FPC slot number";
         type union {
           type string {
             pattern "<.*>|$.*";
           }
           type uint32;
         }
       }
       leaf mode {
         junos:cli-feature "nokeyword";
         type enumeration {
           enum "extended" {
             description "Show all planes in output";
           }
         }
       }
     }
     output {
       choice output-tags {
         case actual-tag {
           container fm-fpc-state-information {
             uses fm-fpc-state-information-block;
           }
         }
         case multichassis-tag {
           container multi-routing-engine-results {
             list multi-routing-engine-item {
               leaf re-name {
                 type string;
               }
               choice output-tags {
                 case actual-tag {
                   container fm-fpc-state-information {
                     uses fm-fpc-state-information-block;
                   }
                 }
               }
             }
           }
         }
       }
     }
   }
   rpc get-fm-bandwidth-degradation {
     description "Show FPC fabric bandwidth degradation information";
     junos:command "show chassis fabric degradation";
     input {
       uses command-forwarding;
     }
     output {
       choice output-tags {
         case actual-tag {
           container fm-bandwidth-degradation {
             uses fm-bandwidth-degradation-block;
           }
         }
         case multichassis-tag {
           container multi-routing-engine-results {
             list multi-routing-engine-item {
               leaf re-name {
                 type string;
               }
               choice output-tags {
                 case actual-tag {
                   container fm-bandwidth-degradation {
                     uses fm-bandwidth-degradation-block;
                   }
                 }
               }
             }
           }
         }
       }
     }
   }
   rpc get-fm-degradation-information-details {
     description "Show fpc fabric degradation action history";
     junos:command "show chassis fabric degradation actions";
     input {
       uses command-forwarding;
     }
     output {
       choice output-tags {
         case output-tag {
           leaf output {
             type string;
           }
         }
         case actual-tag {
           anyxml fm-degradation-information-details;
         }
         case multichassis-tag {
           anyxml multi-routing-engine-results;
         }
       }
     }
   }
   rpc get-fm-fabric-destinations-state {
     description "Show fabric destinations state for all FPCs";
     junos:command "show chassis fabric destinations";
     input {
       uses command-forwarding;
       leaf fpc {
         description "FPC slot number";
         type union {
           type string {
             pattern "<.*>|$.*";
           }
           type uint32;
         }
       }
       leaf mode {
         junos:cli-feature "nokeyword";
         type enumeration {
           enum "extended" {
             description "Show all 24 planes in output";
           }
         }
       }
     }
     output {
       choice output-tags {
         case actual-tag {
           container fm-fabric-destinations-state {
             uses fm-fabric-destinations-state-block;
           }
         }
         case multichassis-tag {
           container multi-routing-engine-results {
             list multi-routing-engine-item {
               leaf re-name {
                 type string;
               }
               choice output-tags {
                 case actual-tag {
                   container fm-fabric-destinations-state {
                     uses fm-fabric-destinations-state-block;
                   }
                 }
               }
             }
           }
         }
       }
     }
   }
   rpc get-fm-plane-location-information {
     description "Show fabric plane location";
     junos:command "show chassis fabric plane-location";
     input {
       uses command-forwarding;
     }
     output {
       choice output-tags {
         case actual-tag {
           container fm-plane-location-information {
             uses fm-plane-location-information-block;
           }
         }
         case multichassis-tag {
           container multi-routing-engine-results {
             list multi-routing-engine-item {
               leaf re-name {
                 type string;
               }
               choice output-tags {
                 case actual-tag {
                   container fm-plane-location-information {
                     uses fm-plane-location-information-block;
                   }
                 }
               }
             }
           }
         }
       }
     }
   }
   rpc get-fm-topology {
     description "Show fabric topology for plane";
     junos:command "show chassis fabric map";
     input {
       uses command-forwarding;
       leaf plane {
         description "Fabric plane number";
         type union {
           type string {
             pattern "<.*>|$.*";
           }
           type uint32;
         }
       }
     }
     output {
       choice output-tags {
         case actual-tag {
           container fm-topology {
             uses fm-topology-block;
           }
         }
         case multichassis-tag {
           container multi-routing-engine-results {
             list multi-routing-engine-item {
               leaf re-name {
                 type string;
               }
               choice output-tags {
                 case actual-tag {
                   container fm-topology {
                     uses fm-topology-block;
                   }
                 }
               }
             }
           }
         }
       }
     }
   }
   rpc get-fm-optical-links-state-information {
     description "Show state of fabric management optical links";
     junos:command "show chassis fabric optical-links";
     input {
       leaf lcc {
         description "Lcc number";
         type union {
           type string {
             pattern "<.*>|$.*";
           }
           type uint32;
         }
       }
       leaf detail {
         description "Display detailed output";
         type empty;
       }
     }
     output {
       choice output-tags {
         case actual-tag {
           container fm-optical-links-state-information {
             uses fm-optical-links-state-information-block;
           }
         }
         case multichassis-tag {
           container multi-routing-engine-results {
             list multi-routing-engine-item {
               leaf re-name {
                 type string;
               }
               choice output-tags {
                 case actual-tag {
                   container fm-optical-links-state-information {
                     uses fm-optical-links-state-information-block;
                   }
                 }
               }
             }
           }
         }
       }
     }
   }
   rpc get-fm-optics-port-information {
     description "Show info of fabric optical ports";
     junos:command "show chassis fabric optics";
     input {
       uses command-forwarding;
       leaf display {
         junos:cli-feature "nokeyword";
         type enumeration {
           enum "brief" {
             description "Show brief output";
           }
           enum "detail" {
             description "Show detailed output";
           }
         }
       }
       leaf sib-slot {
         description "SIB slot number";
         junos:cli-feature "nokeyword";
         type union {
           type string {
             pattern "<.*>|$.*";
           }
           type uint32;
         }
       }
     }
     output {
       choice output-tags {
         case actual-tag {
           container fm-optics-port-information {
             uses fm-optics-port-information-block;
           }
         }
         case multichassis-tag {
           container multi-routing-engine-results {
             list multi-routing-engine-item {
               leaf re-name {
                 type string;
               }
               choice output-tags {
                 case actual-tag {
                   container fm-optics-port-information {
                     uses fm-optics-port-information-block;
                   }
                 }
               }
             }
           }
         }
       }
     }
   }
   rpc get-fm-plane-state-information {
     description "Show state of fabric management plane";
     junos:command "show chassis fabric plane";
     input {
       uses command-forwarding;
       leaf display {
         junos:cli-feature "nokeyword";
         type enumeration {
           enum "terse" {
             description "Show terse output";
           }
           enum "detail" {
             description "Show detail output";
           }
           enum "extensive" {
             description "Show extensive output";
           }
         }
       }
       leaf number {
         description "Fabric plane number";
         junos:cli-feature "nokeyword";
         type union {
           type string {
             pattern "<.*>|$.*";
           }
           type uint32 {
             range "0 .. 4";
           }
         }
       }
       leaf mode {
         junos:cli-feature "nokeyword";
         type enumeration {
           enum "extended" {
             description "Show all 24 planes in output";
           }
         }
       }
     }
     output {
       choice output-tags {
         case actual-tag {
           container fm-plane-state-information {
             uses fm-plane-state-information-block;
           }
         }
         case multichassis-tag {
           container multi-routing-engine-results {
             list multi-routing-engine-item {
               leaf re-name {
                 type string;
               }
               choice output-tags {
                 case actual-tag {
                   container fm-plane-state-information {
                     uses fm-plane-state-information-block;
                   }
                 }
               }
             }
           }
         }
       }
     }
   }
   rpc get-fm-mid-plane-state-information {
     description "Show state of fabric mid plane";
     junos:command "show chassis fabric midplane";
     input {
       uses command-forwarding;
     }
     output {
       choice output-tags {
         case actual-tag {
           container fm-plane-state-information {
             uses fm-plane-state-information-block;
           }
         }
         case multichassis-tag {
           container multi-routing-engine-results {
             list multi-routing-engine-item {
               leaf re-name {
                 type string;
               }
               choice output-tags {
                 case actual-tag {
                   container fm-plane-state-information {
                     uses fm-plane-state-information-block;
                   }
                 }
               }
             }
           }
         }
       }
     }
   }
   rpc get-fm-state-information {
     description "Show summary fabric management state";
     junos:command "show chassis fabric summary";
     input {
       uses command-forwarding;
     }
     output {
       choice output-tags {
         case actual-tag {
           container fm-state-information {
             uses fm-state-information-block;
           }
         }
         case multichassis-tag {
           container multi-routing-engine-results {
             list multi-routing-engine-item {
               leaf re-name {
                 type string;
               }
               choice output-tags {
                 case actual-tag {
                   container fm-state-information {
                     uses fm-state-information-block;
                   }
                 }
               }
             }
           }
         }
       }
     }
   }
   rpc get-fm-ext-state-information {
     description "Show extended summary fabric management state";
     junos:command "show chassis fabric summary extended";
     input {
       uses command-forwarding;
     }
     output {
       choice output-tags {
         case actual-tag {
           container fm-ext-state-information {
             uses fm-ext-state-information-block;
           }
         }
         case multichassis-tag {
           container multi-routing-engine-results {
             list multi-routing-engine-item {
               leaf re-name {
                 type string;
               }
               choice output-tags {
                 case actual-tag {
                   container fm-ext-state-information {
                     uses fm-ext-state-information-block;
                   }
                 }
               }
             }
           }
         }
       }
     }
   }
   rpc get-fm-state-legend {
     description "Show legend of fabric management states";
     junos:command "show chassis fabric legend";
     input {
       uses command-forwarding;
     }
     output {
       choice output-tags {
         case actual-tag {
           container fm-state-legend {
             uses fm-state-legend-block;
           }
         }
         case multichassis-tag {
           container multi-routing-engine-results {
             list multi-routing-engine-item {
               leaf re-name {
                 type string;
               }
               choice output-tags {
                 case actual-tag {
                   container fm-state-legend {
                     uses fm-state-legend-block;
                   }
                 }
               }
             }
           }
         }
       }
     }
   }
   rpc get-fm-sib-state-information {
     description "Show summary fabric management SIB state from Routing Engine";
     junos:command "show chassis fabric sibs";
     input {
       uses command-forwarding;
       leaf slot {
         description "SIB slot number";
         type union {
           type string {
             pattern "<.*>|$.*";
           }
           type uint32;
         }
       }
       leaf mode {
         junos:cli-feature "nokeyword";
         type enumeration {
           enum "extended" {
             description "Show all planes in output";
           }
         }
       }
     }
     output {
       choice output-tags {
         case actual-tag {
           container fm-sib-state-information {
             uses fm-sib-state-information-block;
           }
         }
         case multichassis-tag {
           container multi-routing-engine-results {
             list multi-routing-engine-item {
               leaf re-name {
                 type string;
               }
               choice output-tags {
                 case actual-tag {
                   container fm-sib-state-information {
                     uses fm-sib-state-information-block;
                   }
                 }
               }
             }
           }
         }
       }
     }
   }
   rpc get-chassis-fabric-topology-information {
     description "Show fabric topology information";
     junos:command "show chassis fabric topology";
     input {
       uses command-forwarding;
       leaf sib-slot {
         description "SIB slot number";
         junos:cli-feature "nokeyword";
         type union {
           type string {
             pattern "<.*>|$.*";
           }
           type uint32;
         }
       }
       leaf device {
         description "Device alias name or serial number";
         type string;
       }
       leaf slot {
         description "Slot number";
         type union {
           type string {
             pattern "<.*>|$.*";
           }
           type uint32 {
             range "0 .. 15";
           }
         }
       }
     }
     output {
       choice output-tags {
         case actual-tag {
           container fm-topology {
             uses fm-topology-block;
           }
         }
         case multichassis-tag {
           container multi-routing-engine-results {
             list multi-routing-engine-item {
               leaf re-name {
                 type string;
               }
               choice output-tags {
                 case actual-tag {
                   container fm-topology {
                     uses fm-topology-block;
                   }
                 }
               }
             }
           }
         }
       }
     }
   }
   rpc get-fm-topo-tracepath-link {
     description "Show info of fabric path";
     junos:command "show chassis fabric topology tracepath link";
     input {
       leaf hsl2link {
         description "HSL2 Link Name as in topology command";
         junos:cli-feature "nokeyword";
         type string;
         mandatory true;
       }
       leaf lcc {
         description "Lcc number. Default is 0";
         default "0";
         type union {
           type string {
             pattern "<.*>|$.*";
           }
           type uint32;
         }
       }
     }
     output {
       choice output-tags {
         case actual-tag {
           container fm-topo-tracepath-link {
             uses fm-topo-tracepath-link-block;
           }
         }
         case multichassis-tag {
           container multi-routing-engine-results {
             list multi-routing-engine-item {
               leaf re-name {
                 type string;
               }
               choice output-tags {
                 case actual-tag {
                   container fm-topo-tracepath-link {
                     uses fm-topo-tracepath-link-block;
                   }
                 }
               }
             }
           }
         }
       }
     }
   }
   rpc get-fm-topo-tracepath-fpc {
     description "Show info of fabric path";
     junos:command "show chassis fabric topology tracepath fpc";
     input {
       leaf fpcstr {
         description "FPC/PFE String as in topology cmd - e.g. FPC7PFE1";
         junos:cli-feature "nokeyword";
         type string;
         mandatory true;
       }
       leaf lcc {
         description "Lcc number.";
         type union {
           type string {
             pattern "<.*>|$.*";
           }
           type uint32;
         }
         mandatory true;
       }
       leaf plane {
         description "Fabric Plane - 0/1/2/3/4 and 5=all-active-planes(Default)";
         default "5";
         type union {
           type string {
             pattern "<.*>|$.*";
           }
           type uint32 {
             range "0 .. 5";
           }
         }
       }
     }
     output {
       choice output-tags {
         case actual-tag {
           container fm-topo-tracepath-fpc {
             uses fm-topo-tracepath-fpc-block;
           }
         }
         case multichassis-tag {
           container multi-routing-engine-results {
             list multi-routing-engine-item {
               leaf re-name {
                 type string;
               }
               choice output-tags {
                 case actual-tag {
                   container fm-topo-tracepath-fpc {
                     uses fm-topo-tracepath-fpc-block;
                   }
                 }
               }
             }
           }
         }
       }
     }
   }
   rpc get-chassis-fabric-spray-weight-information {
     description "Show fabric spray-weights";
     junos:command "show chassis fabric spray-weights";
     output {
       choice output-tags {
         case actual-tag {
           container chassis-fabric-spray-weight-information {
             uses chassis-fabric-spray-weight-information-block;
           }
         }
         case multichassis-tag {
           container multi-routing-engine-results {
             list multi-routing-engine-item {
               leaf re-name {
                 type string;
               }
               choice output-tags {
                 case actual-tag {
                   container chassis-fabric-spray-weight-information {
                     uses chassis-fabric-spray-weight-information-block;
                   }
                 }
               }
             }
           }
         }
       }
     }
   }
   rpc get-chassis-fabric-link-information {
     description "Show data-center fabric links";
     junos:command "show chassis fabric links";
     input {
       leaf link-type {
         description "Link type";
         junos:cli-feature "nokeyword";
         default "all";
         type enumeration {
           enum "up" {
             description "Up links";
           }
           enum "down" {
             description "Down links";
           }
           enum "error" {
             description "Error links";
           }
           enum "all" {
             description "All links";
           }
         }
       }
       leaf device {
         description "Device alias name or serial number";
         type string;
       }
       leaf slot {
         description "Slot number";
         type union {
           type string {
             pattern "<.*>|$.*";
           }
           type uint32 {
             range "0 .. 15";
           }
         }
       }
     }
     output {
       choice output-tags {
         case actual-tag {
           container chassis-fabric-information {
             uses chassis-fabric-information-block;
           }
         }
         case multichassis-tag {
           container multi-routing-engine-results {
             list multi-routing-engine-item {
               leaf re-name {
                 type string;
               }
               choice output-tags {
                 case actual-tag {
                   container chassis-fabric-information {
                     uses chassis-fabric-information-block;
                   }
                 }
               }
             }
           }
         }
       }
     }
   }
   rpc get-chassis-fabric-information-device {
     description "Show chassis fabric devices running FM component";
     junos:command "show chassis fabric device";
     input {
       leaf device-id {
         description "Device alias name or serial number";
         junos:cli-feature "nokeyword";
         type string;
       }
     }
     output {
       choice output-tags {
         case actual-tag {
           container chassis-fabric-information-device {
             uses chassis-fabric-information-device-block;
           }
         }
         case multichassis-tag {
           container multi-routing-engine-results {
             list multi-routing-engine-item {
               leaf re-name {
                 type string;
               }
               choice output-tags {
                 case actual-tag {
                   container chassis-fabric-information-device {
                     uses chassis-fabric-information-device-block;
                   }
                 }
               }
             }
           }
         }
       }
     }
   }
   rpc get-chassis-fabric-connectivity-information {
     description "Show data-center fabric connectivity";
     junos:command "show chassis fabric connectivity";
     input {
       leaf device {
         description "Device alias name or serial number";
         type string;
       }
       leaf slot {
         description "Slot number";
         type union {
           type string {
             pattern "<.*>|$.*";
           }
           type uint32 {
             range "0 .. 15";
           }
         }
       }
       leaf inter-chassis {
         description "Inter chassis fabric link connectivity details";
         type empty;
       }
       leaf intra-chassis {
         description "Intra chassis fabric link connectivity details";
         type empty;
       }
     }
     output {
       choice output-tags {
         case actual-tag {
           container chassis-fabric-connectivity-information {
             uses chassis-fabric-connectivity-information-block;
           }
         }
         case multichassis-tag {
           container multi-routing-engine-results {
             list multi-routing-engine-item {
               leaf re-name {
                 type string;
               }
               choice output-tags {
                 case actual-tag {
                   container chassis-fabric-connectivity-information {
                     uses chassis-fabric-connectivity-information-block;
                   }
                 }
               }
             }
           }
         }
       }
     }
   }
   rpc get-fm-unreachable-dest-information {
     description "Show unreachable destinations on all active planes";
     junos:command "show chassis fabric unreachable-destinations";
     output {
       choice output-tags {
         case actual-tag {
           container fm-unreachable-dest-information {
             uses fm-unreachable-dest-information-block;
           }
         }
         case multichassis-tag {
           container multi-routing-engine-results {
             list multi-routing-engine-item {
               leaf re-name {
                 type string;
               }
               choice output-tags {
                 case actual-tag {
                   container fm-unreachable-dest-information {
                     uses fm-unreachable-dest-information-block;
                   }
                 }
               }
             }
           }
         }
       }
     }
   }
   rpc get-fm-fabric-reachability-information {
     description "Show current status of fabric reachability";
     junos:command "show chassis fabric reachability";
     input {
       uses command-forwarding;
       leaf detail {
         description "Show reachability output in detail";
         type empty;
       }
       leaf extended {
         description "Show all 24 planes in output";
         type empty;
       }
     }
     output {
       choice output-tags {
         case actual-tag {
           container fm-fabric-reachability-information {
             uses fm-fabric-reachability-information-block;
           }
         }
         case multichassis-tag {
           container multi-routing-engine-results {
             list multi-routing-engine-item {
               leaf re-name {
                 type string;
               }
               choice output-tags {
                 case actual-tag {
                   container fm-fabric-reachability-information {
                     uses fm-fabric-reachability-information-block;
                   }
                 }
               }
             }
           }
         }
       }
     }
   }
   rpc get-fm-fabric-events-information {
     description "Show current fabric events that are in progress";
     junos:command "show chassis fabric events queue";
     input {
       uses command-forwarding;
     }
     output {
       choice output-tags {
         case actual-tag {
           container fm-fabric-events-information {
             uses fm-fabric-events-information-block;
           }
         }
         case multichassis-tag {
           container multi-routing-engine-results {
             list multi-routing-engine-item {
               leaf re-name {
                 type string;
               }
               choice output-tags {
                 case actual-tag {
                   container fm-fabric-events-information {
                     uses fm-fabric-events-information-block;
                   }
                 }
               }
             }
           }
         }
       }
     }
   }
   rpc get-fm-fabric-events-history {
     description "Show fabric events history.";
     junos:command "show chassis fabric events history";
     output {
       choice output-tags {
         case actual-tag {
           container fm-fabric-events-history {
             uses fm-fabric-events-history-block;
           }
         }
         case multichassis-tag {
           container multi-routing-engine-results {
             list multi-routing-engine-item {
               leaf re-name {
                 type string;
               }
               choice output-tags {
                 case actual-tag {
                   container fm-fabric-events-history {
                     uses fm-fabric-events-history-block;
                   }
                 }
               }
             }
           }
         }
       }
     }
   }
   rpc get-fm-degraded-fabric-state-information {
     description "Show degraded fabric state on all active planes";
     junos:command "show chassis fabric degraded-fabric-reachability";
     output {
       choice output-tags {
         case actual-tag {
           container fm-degraded-fabric-state-information {
             uses fm-degraded-fabric-state-information-block;
           }
         }
         case multichassis-tag {
           container multi-routing-engine-results {
             list multi-routing-engine-item {
               leaf re-name {
                 type string;
               }
               choice output-tags {
                 case actual-tag {
                   container fm-degraded-fabric-state-information {
                     uses fm-degraded-fabric-state-information-block;
                   }
                 }
               }
             }
           }
         }
       }
     }
   }
   rpc get-fm-sib-errors {
     description "Show Switch Interface Board errors";
     junos:command "show chassis fabric errors sib";
     input {
       uses command-forwarding;
       leaf sib-slot {
         description "SIB slot number";
         junos:cli-feature "nokeyword";
         type union {
           type string {
             pattern "<.*>|$.*";
           }
           type uint32;
         }
         mandatory true;
       }
     }
     output {
       choice output-tags {
         case actual-tag {
           container fm-fru-errors {
             uses fm-fru-errors-block;
           }
         }
         case multichassis-tag {
           container multi-routing-engine-results {
             list multi-routing-engine-item {
               leaf re-name {
                 type string;
               }
               choice output-tags {
                 case actual-tag {
                   container fm-fru-errors {
                     uses fm-fru-errors-block;
                   }
                 }
               }
             }
           }
         }
       }
     }
   }
   rpc get-fm-fpc-errors {
     description "Show Flexible PIC Controller errors";
     junos:command "show chassis fabric errors fpc";
     input {
       uses command-forwarding;
       leaf slot {
         description "FPC slot number";
         junos:cli-feature "nokeyword";
         type union {
           type string {
             pattern "<.*>|$.*";
           }
           type uint32;
         }
         mandatory true;
       }
     }
     output {
       choice output-tags {
         case actual-tag {
           container fm-fru-errors {
             uses fm-fru-errors-block;
           }
         }
         case multichassis-tag {
           container multi-routing-engine-results {
             list multi-routing-engine-item {
               leaf re-name {
                 type string;
               }
               choice output-tags {
                 case actual-tag {
                   container fm-fru-errors {
                     uses fm-fru-errors-block;
                   }
                 }
               }
             }
           }
         }
       }
     }
   }
   rpc get-fm-plane-autoheal-errors {
     description "Show Planes autoheal state";
     junos:command "show chassis fabric errors autoheal";
     output {
       choice output-tags {
         case actual-tag {
           container fm-fru-errors {
             uses fm-fru-errors-block;
           }
         }
         case multichassis-tag {
           container multi-routing-engine-results {
             list multi-routing-engine-item {
               leaf re-name {
                 type string;
               }
               choice output-tags {
                 case actual-tag {
                   container fm-fru-errors {
                     uses fm-fru-errors-block;
                   }
                 }
               }
             }
           }
         }
       }
     }
   }
   rpc get-fm-plane-recent-autoheal-errors {
     description "Show the recent history for planes autoheal state";
     junos:command "show chassis fabric errors autoheal recent";
     input {
       leaf count {
         description "Number of log entries to be displayed";
         type union {
           type uint32;
           type string {
             pattern "<.*>|$.*";
           }
         }
       }
     }
     output {
       choice output-tags {
         case actual-tag {
           container fm-fru-errors-recent {
             uses fm-fru-errors-recent-block;
           }
         }
         case multichassis-tag {
           container multi-routing-engine-results {
             list multi-routing-engine-item {
               leaf re-name {
                 type string;
               }
               choice output-tags {
                 case actual-tag {
                   container fm-fru-errors-recent {
                     uses fm-fru-errors-recent-block;
                   }
                 }
               }
             }
           }
         }
       }
     }
   }
   rpc get-fm-plane-oldest-autoheal-errors {
     description "Show the oldest history for planes autoheal state";
     junos:command "show chassis fabric errors autoheal oldest";
     input {
       leaf count {
         description "Number of log entries to be displayed";
         type union {
           type uint32;
           type string {
             pattern "<.*>|$.*";
           }
         }
       }
     }
     output {
       choice output-tags {
         case actual-tag {
           container fm-fru-errors-oldest {
             uses fm-fru-errors-oldest-block;
           }
         }
         case multichassis-tag {
           container multi-routing-engine-results {
             list multi-routing-engine-item {
               leaf re-name {
                 type string;
               }
               choice output-tags {
                 case actual-tag {
                   container fm-fru-errors-oldest {
                     uses fm-fru-errors-oldest-block;
                   }
                 }
               }
             }
           }
         }
       }
     }
   }
   rpc get-fm-plane-all-autoheal-errors {
     description "Show the history for all the planes autoheal state";
     junos:command "show chassis fabric errors autoheal all";
     output {
       choice output-tags {
         case actual-tag {
           container fm-fru-errors-all {
             uses fm-fru-errors-all-block;
           }
         }
         case multichassis-tag {
           container multi-routing-engine-results {
             list multi-routing-engine-item {
               leaf re-name {
                 type string;
               }
               choice output-tags {
                 case actual-tag {
                   container fm-fru-errors-all {
                     uses fm-fru-errors-all-block;
                   }
                 }
               }
             }
           }
         }
       }
     }
   }
   rpc get-fm-fpc-plane-link-history-autoheal-errors {
     description "Show the autoheal history for a given plane";
     junos:command "show chassis fabric errors autoheal fpc";
     input {
       leaf fpc-slot {
         description "FPC slot number";
         junos:cli-feature "nokeyword";
         type union {
           type string {
             pattern "<.*>|$.*";
           }
           type uint32;
         }
         mandatory true;
       }
       leaf pfe {
         description "PFE number for the link";
         type union {
           type uint32;
           type string {
             pattern "<.*>|$.*";
           }
         }
         mandatory true;
       }
       leaf plane {
         description "Plane number for the link";
         type union {
           type uint32;
           type string {
             pattern "<.*>|$.*";
           }
         }
         mandatory true;
       }
     }
     output {
       choice output-tags {
         case actual-tag {
           container fm-fru-errors-plane-history {
             uses fm-fru-errors-plane-history-block;
           }
         }
         case multichassis-tag {
           container multi-routing-engine-results {
             list multi-routing-engine-item {
               leaf re-name {
                 type string;
               }
               choice output-tags {
                 case actual-tag {
                   container fm-fru-errors-plane-history {
                     uses fm-fru-errors-plane-history-block;
                   }
                 }
               }
             }
           }
         }
       }
     }
   }
   rpc get-fm-fpc-stream-information {
     description "Show FPC stream number information";
     junos:command "show chassis fabric stream-info";
     input {
       uses command-forwarding;
     }
     output {
       choice output-tags {
         case actual-tag {
           container fm-fpc-stream-information {
             uses fm-fpc-stream-information-block;
           }
         }
         case multichassis-tag {
           container multi-routing-engine-results {
             list multi-routing-engine-item {
               leaf re-name {
                 type string;
               }
               choice output-tags {
                 case actual-tag {
                   container fm-fpc-stream-information {
                     uses fm-fpc-stream-information-block;
                   }
                 }
               }
             }
           }
         }
       }
     }
   }
   rpc get-chassis-inventory {
     description "Show installed hardware components";
     junos:command "show chassis hardware";
     input {
       uses command-forwarding;
       leaf verbosity {
         junos:cli-feature "nokeyword";
         type enumeration {
           enum "detail" {
             description "Include RAM and disk information in output";
           }
           enum "extensive" {
             description "Display ID EEPROM information";
           }
           enum "models" {
             description "Display serial number and model number for orderable FRUs";
           }
           enum "clei-models" {
             description "Display CLEI barcode and model number for orderable FRUs";
           }
         }
       }
       leaf fpc {
         description "Flexible PIC Controller slot number";
         type union {
           type string {
             pattern "<.*>|$.*";
           }
           type uint32;
         }
       }
     }
     output {
       choice output-tags {
         case actual-tag {
           container chassis-inventory {
             uses chassis-inventory-block;
           }
         }
         case multichassis-tag {
           container multi-routing-engine-results {
             list multi-routing-engine-item {
               leaf re-name {
                 type string;
               }
               choice output-tags {
                 case actual-tag {
                   container chassis-inventory {
                     uses chassis-inventory-block;
                   }
                 }
               }
             }
           }
         }
       }
     }
   }
   rpc get-chassis-hardware-satellite-information {
     description "Show hardware details";
     junos:command "show chassis hardware satellite";
     input {
       leaf fpc-slot {
         description "Satellite slot number";
         type union {
           type string {
             pattern "<.*>|$.*";
           }
           type uint16 {
             range "65 .. 254";
           }
         }
       }
       leaf device-alias {
         description "Device alias";
         type string;
       }
       leaf verbosity {
         junos:cli-feature "nokeyword";
         type enumeration {
           enum "detail" {
             description "Include RAM and disk information in output";
           }
           enum "extensive" {
             description "Display ID EEPROM information";
           }
           enum "models" {
             description "Display serial number and model number for orderable FRUs";
           }
           enum "clei-models" {
             description "Display CLEI barcode and model number for orderable FRUs";
           }
         }
       }
     }
     output {
       choice output-tags {
         case output-tag {
           leaf output {
             type string;
           }
         }
         case actual-tag {
           anyxml chassis-hardware-satellite-information;
         }
         case multichassis-tag {
           anyxml multi-routing-engine-results;
         }
       }
     }
   }
   rpc get-reswatch-config-information {
     description "Show rewatch configuration";
     junos:command "show chassis reswatch-config";
     input {
       uses command-forwarding;
     }
     output {
       choice output-tags {
         case actual-tag {
           container reswatch-config-information {
             uses reswatch-config-information-block;
           }
         }
         case multichassis-tag {
           container multi-routing-engine-results {
             list multi-routing-engine-item {
               leaf re-name {
                 type string;
               }
               choice output-tags {
                 case actual-tag {
                   container reswatch-config-information {
                     uses reswatch-config-information-block;
                   }
                 }
               }
             }
           }
         }
       }
     }
   }
   rpc get-power-budget-information {
     description "Show power budget chassis information";
     junos:command "show chassis power-budget-statistics";
     input {
       uses command-forwarding;
     }
     output {
       choice output-tags {
         case actual-tag {
           container power-budget-information {
             uses power-budget-information-block;
           }
         }
         case multichassis-tag {
           container multi-routing-engine-results {
             list multi-routing-engine-item {
               leaf re-name {
                 type string;
               }
               choice output-tags {
                 case actual-tag {
                   container power-budget-information {
                     uses power-budget-information-block;
                   }
                 }
               }
             }
           }
         }
       }
     }
   }
   rpc get-chassis-ae-lb-information {
     description "Show multicast load balancing settings";
     junos:command "show chassis multicast-loadbalance";
     output {
       choice output-tags {
         case actual-tag {
           container chassis-ae-lb-information {
             uses chassis-ae-lb-information-block;
           }
         }
         case multichassis-tag {
           container multi-routing-engine-results {
             list multi-routing-engine-item {
               leaf re-name {
                 type string;
               }
               choice output-tags {
                 case actual-tag {
                   container chassis-ae-lb-information {
                     uses chassis-ae-lb-information-block;
                   }
                 }
               }
             }
           }
         }
       }
     }
   }
   rpc get-rps-chassis-information {
     description "Show redundant power system chassis information";
     junos:command "show chassis redundant-power-system";
     output {
       choice output-tags {
         case actual-tag {
           container rps-chassis-information {
             uses rps-chassis-information-block;
           }
         }
         case multichassis-tag {
           container multi-routing-engine-results {
             list multi-routing-engine-item {
               leaf re-name {
                 type string;
               }
               choice output-tags {
                 case actual-tag {
                   container rps-chassis-information {
                     uses rps-chassis-information-block;
                   }
                 }
               }
             }
           }
         }
       }
     }
   }
   rpc get-chassis-mac-addresses {
     description "Show media access control addresses";
     junos:command "show chassis mac-addresses";
     input {
       uses command-forwarding;
     }
     output {
       choice output-tags {
         case actual-tag {
           container chassis-mac-addresses {
             uses chassis-mac-addresses-block;
           }
         }
         case multichassis-tag {
           container multi-routing-engine-results {
             list multi-routing-engine-item {
               leaf re-name {
                 type string;
               }
               choice output-tags {
                 case actual-tag {
                   container chassis-mac-addresses {
                     uses chassis-mac-addresses-block;
                   }
                 }
               }
             }
           }
         }
       }
     }
   }
   rpc get-raid-status {
     description "Show RAID status";
     junos:command "show chassis raid status";
     input {
       uses command-forwarding;
     }
     output {
       choice output-tags {
         case actual-tag {
           container raid-information {
             uses raid-information-block;
           }
         }
         case multichassis-tag {
           container multi-routing-engine-results {
             list multi-routing-engine-item {
               leaf re-name {
                 type string;
               }
               choice output-tags {
                 case actual-tag {
                   container raid-information {
                     uses raid-information-block;
                   }
                 }
               }
             }
           }
         }
       }
     }
   }
   rpc get-raid-members {
     description "Show RAID members";
     junos:command "show chassis raid members";
     input {
       uses command-forwarding;
     }
     output {
       choice output-tags {
         case actual-tag {
           container raid-information {
             uses raid-information-block;
           }
         }
         case multichassis-tag {
           container multi-routing-engine-results {
             list multi-routing-engine-item {
               leaf re-name {
                 type string;
               }
               choice output-tags {
                 case actual-tag {
                   container raid-information {
                     uses raid-information-block;
                   }
                 }
               }
             }
           }
         }
       }
     }
   }
   rpc get-route-engine-information {
     description "Show Routing Engine status";
     junos:command "show chassis routing-engine";
     input {
       uses command-forwarding;
       leaf slot {
         description "Routing Engine slot number";
         junos:cli-feature "nokeyword";
         type union {
           type string {
             pattern "<.*>|$.*";
           }
           type uint32;
         }
       }
     }
     output {
       choice output-tags {
         case actual-tag {
           container route-engine-information {
             uses route-engine-information-block;
           }
         }
         case multichassis-tag {
           container multi-routing-engine-results {
             list multi-routing-engine-item {
               leaf re-name {
                 type string;
               }
               choice output-tags {
                 case actual-tag {
                   container route-engine-information {
                     uses route-engine-information-block;
                   }
                 }
               }
             }
           }
         }
       }
     }
   }
   rpc get-bios-version-information {
     description "Show BIOS firmware version";
     junos:command "show chassis routing-engine bios";
     input {
       uses command-forwarding;
       leaf slot {
         description "Routing Engine slot number";
         junos:cli-feature "nokeyword";
         type union {
           type string {
             pattern "<.*>|$.*";
           }
           type uint32;
         }
         mandatory true;
       }
     }
     output {
       choice output-tags {
         case actual-tag {
           container route-engine-information {
             uses route-engine-information-block;
           }
         }
         case multichassis-tag {
           container multi-routing-engine-results {
             list multi-routing-engine-item {
               leaf re-name {
                 type string;
               }
               choice output-tags {
                 case actual-tag {
                   container route-engine-information {
                     uses route-engine-information-block;
                   }
                 }
               }
             }
           }
         }
       }
     }
   }
   rpc get-chassis-routing-engine-bios-satellite-info {
     description "Show routing engine bios details";
     junos:command "show chassis routing-engine bios satellite";
     input {
       leaf fpc-slot {
         description "Satellite slot number";
         type union {
           type string {
             pattern "<.*>|$.*";
           }
           type uint16 {
             range "65 .. 254";
           }
         }
       }
       leaf device-alias {
         description "Device alias";
         type string;
       }
     }
     output {
       choice output-tags {
         case output-tag {
           leaf output {
             type string;
           }
         }
         case actual-tag {
           anyxml chassis-routing-engine-bios-satellite-information;
         }
         case multichassis-tag {
           anyxml multi-routing-engine-results;
         }
       }
     }
   }
   rpc get-chassis-hard-disk-test {
     description "Show smartd self tests status on hard disks";
     junos:command "show chassis routing-engine hard-disk-test";
     input {
       leaf status {
         description "Display status of test";
         type empty;
         mandatory true;
       }
       leaf disk {
         description "Name of hard disk";
         type string;
         mandatory true;
       }
     }
     output {
       choice output-tags {
         case actual-tag {
           container raid-information {
             uses raid-information-block;
           }
         }
         case multichassis-tag {
           container multi-routing-engine-results {
             list multi-routing-engine-item {
               leaf re-name {
                 type string;
               }
               choice output-tags {
                 case actual-tag {
                   container raid-information {
                     uses raid-information-block;
                   }
                 }
               }
             }
           }
         }
       }
     }
   }
   rpc get-chassis-routing-engine-errors {
     description "Show RE errors";
     junos:command "show chassis routing-engine errors";
     input {
       uses command-forwarding;
     }
     output {
       choice output-tags {
         case actual-tag {
           container route-engine-resiliency-information {
             uses route-engine-resiliency-information-block;
           }
         }
         case multichassis-tag {
           container multi-routing-engine-results {
             list multi-routing-engine-item {
               leaf re-name {
                 type string;
               }
               choice output-tags {
                 case actual-tag {
                   container route-engine-resiliency-information {
                     uses route-engine-resiliency-information-block;
                   }
                 }
               }
             }
           }
         }
       }
     }
   }
   rpc get-chassis-routing-engine-satellite-information {
     description "Show routing engine details";
     junos:command "show chassis routing-engine satellite";
     input {
       leaf fpc-slot {
         description "Satellite slot number";
         type union {
           type string {
             pattern "<.*>|$.*";
           }
           type uint16 {
             range "65 .. 254";
           }
         }
       }
       leaf device-alias {
         description "Device alias";
         type string;
       }
     }
     output {
       choice output-tags {
         case output-tag {
           leaf output {
             type string;
           }
         }
         case actual-tag {
           anyxml chassis-routing-engine-satellite-information;
         }
         case multichassis-tag {
           anyxml multi-routing-engine-results;
         }
       }
     }
   }
   rpc get-emmc-health-routing-engine-information {
     description "Show eMMC Health Information routing engine";
     junos:command "show chassis emmc-health-information routing-engine";
     input {
       leaf re-slot {
         description "RE slot number";
         junos:cli-feature "nokeyword";
         type union {
           type string {
             pattern "<.*>|$.*";
           }
           type uint32 {
             range "0 .. 31";
           }
         }
       }
     }
     output {
       choice output-tags {
         case actual-tag {
           container emmc-health-information {
             uses emmc-health-information-block;
           }
         }
         case multichassis-tag {
           container multi-routing-engine-results {
             list multi-routing-engine-item {
               leaf re-name {
                 type string;
               }
               choice output-tags {
                 case actual-tag {
                   container emmc-health-information {
                     uses emmc-health-information-block;
                   }
                 }
               }
             }
           }
         }
       }
     }
   }
   rpc get-service-node-information {
     description "Show service node information";
     junos:command "show chassis service-node";
     input {
       leaf version {
         description "Show service-node version information";
         type empty;
       }
       leaf slot {
         description "Service node slot number";
         type union {
           type string {
             pattern "<.*>|$.*";
           }
           type uint32 {
             range "0 .. 1";
           }
         }
       }
     }
     output {
       choice output-tags {
         case actual-tag {
           container service-node-information {
             uses service-node-information-block;
           }
         }
         case multichassis-tag {
           container multi-routing-engine-results {
             list multi-routing-engine-item {
               leaf re-name {
                 type string;
               }
               choice output-tags {
                 case actual-tag {
                   container service-node-information {
                     uses service-node-information-block;
                   }
                 }
               }
             }
           }
         }
       }
     }
   }
   rpc get-ssb-information {
     description "Show System and Switch Board status";
     junos:command "show chassis ssb";
     input {
       leaf slot {
         description "SSB slot number";
         junos:cli-feature "nokeyword";
         type union {
           type string {
             pattern "<.*>|$.*";
           }
           type uint32 {
             range "0 .. 1";
           }
         }
       }
     }
     output {
       choice output-tags {
         case actual-tag {
           container scb-information {
             uses scb-information-block;
           }
         }
         case multichassis-tag {
           container multi-routing-engine-results {
             list multi-routing-engine-item {
               leaf re-name {
                 type string;
               }
               choice output-tags {
                 case actual-tag {
                   container scb-information {
                     uses scb-information-block;
                   }
                 }
               }
             }
           }
         }
       }
     }
   }
   rpc get-scb-information {
     description "Show System Control Board status";
     junos:command "show chassis scb";
     output {
       choice output-tags {
         case actual-tag {
           container scb-information {
             uses scb-information-block;
           }
         }
         case multichassis-tag {
           container multi-routing-engine-results {
             list multi-routing-engine-item {
               leaf re-name {
                 type string;
               }
               choice output-tags {
                 case actual-tag {
                   container scb-information {
                     uses scb-information-block;
                   }
                 }
               }
             }
           }
         }
       }
     }
   }
   rpc get-fwdd-information {
     description "Show forwarding process (fwdd) status";
     junos:command "show chassis forwarding";
     input {
       uses command-forwarding;
     }
     output {
       choice output-tags {
         case actual-tag {
           container scb-information {
             uses scb-information-block;
           }
         }
         case multichassis-tag {
           container multi-routing-engine-results {
             list multi-routing-engine-item {
               leaf re-name {
                 type string;
               }
               choice output-tags {
                 case actual-tag {
                   container scb-information {
                     uses scb-information-block;
                   }
                 }
               }
             }
           }
         }
       }
     }
   }
   rpc get-sfm-information {
     description "Show Switching and Forwarding Module status";
     junos:command "show chassis sfm";
     output {
       choice output-tags {
         case actual-tag {
           container scb-information {
             uses scb-information-block;
           }
         }
         case multichassis-tag {
           container multi-routing-engine-results {
             list multi-routing-engine-item {
               leaf re-name {
                 type string;
               }
               choice output-tags {
                 case actual-tag {
                   container scb-information {
                     uses scb-information-block;
                   }
                 }
               }
             }
           }
         }
       }
     }
   }
   rpc get-cb-brief-information {
     description "Show Control Board status";
     junos:command "show chassis cb";
     output {
       choice output-tags {
         case actual-tag {
           container scb-information {
             uses scb-information-block;
           }
         }
         case multichassis-tag {
           container multi-routing-engine-results {
             list multi-routing-engine-item {
               leaf re-name {
                 type string;
               }
               choice output-tags {
                 case actual-tag {
                   container scb-information {
                     uses scb-information-block;
                   }
                 }
               }
             }
           }
         }
       }
     }
   }
   rpc get-feb-brief-information {
     description "Show Forwarding Engine Board status";
     junos:command "show chassis feb";
     input {
       leaf feb_slot {
         description "FEB slot number";
         junos:cli-feature "nokeyword";
         type union {
           type string {
             pattern "<.*>|$.*";
           }
           type uint32;
         }
       }
     }
     output {
       choice output-tags {
         case actual-tag {
           container scb-information {
             uses scb-information-block;
           }
         }
         case multichassis-tag {
           container multi-routing-engine-results {
             list multi-routing-engine-item {
               leaf re-name {
                 type string;
               }
               choice output-tags {
                 case actual-tag {
                   container scb-information {
                     uses scb-information-block;
                   }
                 }
               }
             }
           }
         }
       }
     }
   }
   rpc get-feb-information {
     description "Show detailed output";
     junos:command "show chassis feb detail";
     input {
       leaf feb_slot {
         description "FEB slot number";
         junos:cli-feature "nokeyword";
         type union {
           type string {
             pattern "<.*>|$.*";
           }
           type uint32;
         }
       }
     }
     output {
       choice output-tags {
         case actual-tag {
           container scb-information {
             uses scb-information-block;
           }
         }
         case multichassis-tag {
           container multi-routing-engine-results {
             list multi-routing-engine-item {
               leaf re-name {
                 type string;
               }
               choice output-tags {
                 case actual-tag {
                   container scb-information {
                     uses scb-information-block;
                   }
                 }
               }
             }
           }
         }
       }
     }
   }
   rpc get-cfeb-information {
     description "Show Compact Forwarding Engine Board status";
     junos:command "show chassis cfeb";
     output {
       choice output-tags {
         case actual-tag {
           container scb-information {
             uses scb-information-block;
           }
         }
         case multichassis-tag {
           container multi-routing-engine-results {
             list multi-routing-engine-item {
               leaf re-name {
                 type string;
               }
               choice output-tags {
                 case actual-tag {
                   container scb-information {
                     uses scb-information-block;
                   }
                 }
               }
             }
           }
         }
       }
     }
   }
   rpc get-afeb-information {
     description "Show Compact Forwarding Engine Board status";
     junos:command "show chassis afeb";
     output {
       choice output-tags {
         case actual-tag {
           container scb-information {
             uses scb-information-block;
           }
         }
         case multichassis-tag {
           container multi-routing-engine-results {
             list multi-routing-engine-item {
               leaf re-name {
                 type string;
               }
               choice output-tags {
                 case actual-tag {
                   container scb-information {
                     uses scb-information-block;
                   }
                 }
               }
             }
           }
         }
       }
     }
   }
   rpc get-tfeb-information {
     description "Show Compact Forwarding Engine Board status";
     junos:command "show chassis tfeb";
     output {
       choice output-tags {
         case actual-tag {
           container scb-information {
             uses scb-information-block;
           }
         }
         case multichassis-tag {
           container multi-routing-engine-results {
             list multi-routing-engine-item {
               leaf re-name {
                 type string;
               }
               choice output-tags {
                 case actual-tag {
                   container scb-information {
                     uses scb-information-block;
                   }
                 }
               }
             }
           }
         }
       }
     }
   }
   rpc get-fan-information {
     description "Show fan and fan tray information";
     junos:command "show chassis fan";
     input {
       uses command-forwarding;
     }
     output {
       choice output-tags {
         case actual-tag {
           container fan-information {
             uses fan-information-block;
           }
         }
         case multichassis-tag {
           container multi-routing-engine-results {
             list multi-routing-engine-item {
               leaf re-name {
                 type string;
               }
               choice output-tags {
                 case actual-tag {
                   container fan-information {
                     uses fan-information-block;
                   }
                 }
               }
             }
           }
         }
       }
     }
   }
   rpc get-fan-speed-change-history {
     description "Show fan speed change history";
     junos:command "show chassis fan speed-change-history";
     output {
       choice output-tags {
         case actual-tag {
           container fan-information {
             uses fan-information-block;
           }
         }
         case multichassis-tag {
           container multi-routing-engine-results {
             list multi-routing-engine-item {
               leaf re-name {
                 type string;
               }
               choice output-tags {
                 case actual-tag {
                   container fan-information {
                     uses fan-information-block;
                   }
                 }
               }
             }
           }
         }
       }
     }
   }
   rpc get-chassis-fan-satellite-information {
     description "Show fan details";
     junos:command "show chassis fan satellite";
     input {
       leaf fpc-slot {
         description "Satellite slot number";
         type union {
           type string {
             pattern "<.*>|$.*";
           }
           type uint16 {
             range "65 .. 254";
           }
         }
       }
       leaf device-alias {
         description "Device alias";
         type string;
       }
     }
     output {
       choice output-tags {
         case output-tag {
           leaf output {
             type string;
           }
         }
         case actual-tag {
           anyxml chassis-fan-satellite-information;
         }
         case multichassis-tag {
           anyxml multi-routing-engine-results;
         }
       }
     }
   }
   rpc get-chassis-location {
     description "Show physical location of chassis";
     junos:command "show chassis location";
     input {
       uses command-forwarding;
     }
     output {
       choice output-tags {
         case actual-tag {
           container chassis-location {
             uses chassis-location-block;
           }
         }
         case multichassis-tag {
           container multi-routing-engine-results {
             list multi-routing-engine-item {
               leaf re-name {
                 type string;
               }
               choice output-tags {
                 case actual-tag {
                   container chassis-location {
                     uses chassis-location-block;
                   }
                 }
               }
             }
           }
         }
       }
     }
   }
   rpc get-interface-location-name-information {
     description "Show physical location given interface name";
     junos:command "show chassis location interface by-name";
     input {
       leaf interface-name {
         description "Interface name";
         junos:cli-feature "nokeyword";
         type string;
         mandatory true;
       }
     }
     output {
       choice output-tags {
         case actual-tag {
           container interface-location-name-information {
             uses interface-location-name-information-block;
           }
         }
         case multichassis-tag {
           container multi-routing-engine-results {
             list multi-routing-engine-item {
               leaf re-name {
                 type string;
               }
               choice output-tags {
                 case actual-tag {
                   container interface-location-name-information {
                     uses interface-location-name-information-block;
                   }
                 }
               }
             }
           }
         }
       }
     }
   }
   rpc get-interface-location-information {
     description "Show interface name given location";
     junos:command "show chassis location interface by-slot";
     input {
       leaf lcc {
         description "LCC number";
         type union {
           type string {
             pattern "<.*>|$.*";
           }
           type uint32;
         }
         mandatory true;
       }
       leaf fpc {
         description "FPC number";
         type union {
           type string {
             pattern "<.*>|$.*";
           }
           type uint32;
         }
         mandatory true;
       }
     }
     output {
       choice output-tags {
         case actual-tag {
           container interface-location-slot-information {
             uses interface-location-slot-information-block;
           }
         }
         case multichassis-tag {
           container multi-routing-engine-results {
             list multi-routing-engine-item {
               leaf re-name {
                 type string;
               }
               choice output-tags {
                 case actual-tag {
                   container interface-location-slot-information {
                     uses interface-location-slot-information-block;
                   }
                 }
               }
             }
           }
         }
       }
     }
   }
   rpc get-temperature-threshold-information {
     description "Show chassis temperature threshold settings";
     junos:command "show chassis temperature-thresholds";
     input {
       uses command-forwarding;
       leaf fpc {
         description "Show Flexible PIC Concentrator temperature threshold settings";
         type union {
           type string {
             pattern "<.*>|$.*";
           }
           type uint32;
         }
       }
       leaf sfb {
         description "Show Switch Fabric Board temperature threshold settings";
         type union {
           type string {
             pattern "<.*>|$.*";
           }
           type uint32;
         }
       }
       leaf cb {
         description "Show Control Board temperature threshold settings";
         type union {
           type string {
             pattern "<.*>|$.*";
           }
           type uint32;
         }
       }
     }
     output {
       choice output-tags {
         case actual-tag {
           container temperature-threshold-information {
             uses temperature-threshold-information-block;
           }
         }
         case multichassis-tag {
           container multi-routing-engine-results {
             list multi-routing-engine-item {
               leaf re-name {
                 type string;
               }
               choice output-tags {
                 case actual-tag {
                   container temperature-threshold-information {
                     uses temperature-threshold-information-block;
                   }
                 }
               }
             }
           }
         }
       }
     }
   }
   rpc get-chassis-temp-thresholds-satellite-info {
     description "Show temperature thresholds details";
     junos:command "show chassis temperature-thresholds satellite";
     input {
       leaf fpc-slot {
         description "Satellite slot number";
         type union {
           type string {
             pattern "<.*>|$.*";
           }
           type uint16 {
             range "65 .. 254";
           }
         }
       }
       leaf device-alias {
         description "Device alias";
         type string;
       }
     }
     output {
       choice output-tags {
         case output-tag {
           leaf output {
             type string;
           }
         }
         case actual-tag {
           anyxml chassis-temperature-thresholds-satellite-information;
         }
         case multichassis-tag {
           anyxml multi-routing-engine-results;
         }
       }
     }
   }
   rpc get-enh-temperature-threshold-information {
     description "Show chassis temperature threshold settings";
     junos:command "show chassis enhanced-temperature-thresholds";
     input {
       leaf fpc {
         description "Show Flexible PIC Concentrator temperature threshold settings";
         type union {
           type string {
             pattern "<.*>|$.*";
           }
           type uint32;
         }
       }
     }
     output {
       choice output-tags {
         case actual-tag {
           container enh-temperature-threshold-information {
             uses enh-temperature-threshold-information-block;
           }
         }
         case multichassis-tag {
           container multi-routing-engine-results {
             list multi-routing-engine-item {
               leaf re-name {
                 type string;
               }
               choice output-tags {
                 case actual-tag {
                   container enh-temperature-threshold-information {
                     uses enh-temperature-threshold-information-block;
                   }
                 }
               }
             }
           }
         }
       }
     }
   }
   rpc get-power-management {
     description "Show power ratings for the router";
     junos:command "show chassis power-ratings";
     input {
       uses command-forwarding;
     }
     output {
       choice output-tags {
         case actual-tag {
           container power-management-information {
             uses power-management-information-block;
           }
         }
         case multichassis-tag {
           container multi-routing-engine-results {
             list multi-routing-engine-item {
               leaf re-name {
                 type string;
               }
               choice output-tags {
                 case actual-tag {
                   container power-management-information {
                     uses power-management-information-block;
                   }
                 }
               }
             }
           }
         }
       }
     }
   }
   rpc get-in-service-upgrade-status {
     description "Show In Service upgrade status";
     junos:command "show chassis in-service-upgrade";
     input {
       uses command-forwarding;
     }
     output {
       choice output-tags {
         case actual-tag {
           container in-service-upgrade-status {
             uses in-service-upgrade-status-block;
           }
         }
         case multichassis-tag {
           container multi-routing-engine-results {
             list multi-routing-engine-item {
               leaf re-name {
                 type string;
               }
               choice output-tags {
                 case actual-tag {
                   container in-service-upgrade-status {
                     uses in-service-upgrade-status-block;
                   }
                 }
               }
             }
           }
         }
       }
     }
   }
   rpc get-chassis-mode-status {
     description "Show chassis mode status";
     junos:command "show chassis mode";
     input {
       uses command-forwarding;
     }
     output {
       choice output-tags {
         case actual-tag {
           container chassis-mode-status {
             uses chassis-mode-status-block;
           }
         }
         case multichassis-tag {
           container multi-routing-engine-results {
             list multi-routing-engine-item {
               leaf re-name {
                 type string;
               }
               choice output-tags {
                 case actual-tag {
                   container chassis-mode-status {
                     uses chassis-mode-status-block;
                   }
                 }
               }
             }
           }
         }
       }
     }
   }
   rpc get-nonstop-upgrade-status {
     description "Show nonstop upgrade status";
     junos:command "show chassis nonstop-upgrade";
     input {
       uses command-forwarding;
     }
     output {
       choice output-tags {
         case actual-tag {
           container in-service-upgrade-status {
             uses in-service-upgrade-status-block;
           }
         }
         case multichassis-tag {
           container multi-routing-engine-results {
             list multi-routing-engine-item {
               leaf re-name {
                 type string;
               }
               choice output-tags {
                 case actual-tag {
                   container in-service-upgrade-status {
                     uses in-service-upgrade-status-block;
                   }
                 }
               }
             }
           }
         }
       }
     }
   }
   rpc get-dedicated-ukern-status {
     description "Show ukernel dedicated CPU core assignment status ";
     junos:command "show chassis dedicated-ukern-cpu";
     output {
       choice output-tags {
         case actual-tag {
           container dedicated-ukern-cpu {
             uses dedicated-ukern-cpu-block;
           }
         }
         case multichassis-tag {
           container multi-routing-engine-results {
             list multi-routing-engine-item {
               leaf re-name {
                 type string;
               }
               choice output-tags {
                 case actual-tag {
                   container dedicated-ukern-cpu {
                     uses dedicated-ukern-cpu-block;
                   }
                 }
               }
             }
           }
         }
       }
     }
   }
   rpc get-realtime-ukern-status {
     description "Show ukernel realtime thread assignment status ";
     junos:command "show chassis realtime-ukern-thread";
     output {
       choice output-tags {
         case output-tag {
           leaf output {
             type string;
           }
         }
         case actual-tag {
           anyxml realtime-ukern-thread;
         }
         case multichassis-tag {
           anyxml multi-routing-engine-results;
         }
       }
     }
   }
   rpc get-chassis-oss-map {
     description "Show Operation Supported System's translated model";
     junos:command "show chassis oss-map";
     output {
       choice output-tags {
         case actual-tag {
           container chassis-oss-map {
             uses chassis-oss-map-block;
           }
         }
         case multichassis-tag {
           container multi-routing-engine-results {
             list multi-routing-engine-item {
               leaf re-name {
                 type string;
               }
               choice output-tags {
                 case actual-tag {
                   container chassis-oss-map {
                     uses chassis-oss-map-block;
                   }
                 }
               }
             }
           }
         }
       }
     }
   }
   rpc security-uefi-variables {
     description "Show platform UEFI variables";
     junos:command "show chassis security uefi variables";
     output {
       choice output-tags {
         case output-tag {
           leaf output {
             type string;
           }
         }
         case actual-tag {
           anyxml uefi-vars;
         }
         case multichassis-tag {
           anyxml multi-routing-engine-results;
         }
       }
     }
   }
   rpc get-gnf-description {
     description "Show GNF information";
     junos:command "show chassis gnf";
     output {
       choice output-tags {
         case actual-tag {
           container gnf-description {
             uses gnf-description-block;
           }
         }
         case multichassis-tag {
           container multi-routing-engine-results {
             list multi-routing-engine-item {
               leaf re-name {
                 type string;
               }
               choice output-tags {
                 case actual-tag {
                   container gnf-description {
                     uses gnf-description-block;
                   }
                 }
               }
             }
           }
         }
       }
     }
   }
   rpc get-lcd-information {
     description "Show LCD display";
     junos:command "show chassis lcd";
     input {
       uses command-forwarding;
     }
     output {
       choice output-tags {
         case actual-tag {
           container craft-lcd-led-information {
             uses craft-lcd-led-information-block;
           }
         }
         case multichassis-tag {
           container multi-routing-engine-results {
             list multi-routing-engine-item {
               leaf re-name {
                 type string;
               }
               choice output-tags {
                 case actual-tag {
                   container craft-lcd-led-information {
                     uses craft-lcd-led-information-block;
                   }
                 }
               }
             }
           }
         }
       }
     }
   }
   rpc get-lcd-fpc-information {
     description "Show LCD display for FPC slot number";
     junos:command "show chassis lcd fpc-slot";
     input {
       uses command-forwarding;
       leaf fpc-slot {
         description "FPC slot number";
         junos:cli-feature "nokeyword";
         type union {
           type string {
             pattern "<.*>|$.*";
           }
           type uint32;
         }
       }
     }
     output {
       choice output-tags {
         case actual-tag {
           container craft-lcd-led-information {
             uses craft-lcd-led-information-block;
           }
         }
         case multichassis-tag {
           container multi-routing-engine-results {
             list multi-routing-engine-item {
               leaf re-name {
                 type string;
               }
               choice output-tags {
                 case actual-tag {
                   container craft-lcd-led-information {
                     uses craft-lcd-led-information-block;
                   }
                 }
               }
             }
           }
         }
       }
     }
   }
   rpc get-lcd-menu-information {
     description "Show active LCD menu items";
     junos:command "show chassis lcd menu";
     input {
       uses command-forwarding;
     }
     output {
       choice output-tags {
         case output-tag {
           leaf output {
             type string;
           }
         }
         case actual-tag {
           anyxml lcd-information;
         }
         case multichassis-tag {
           anyxml multi-routing-engine-results;
         }
       }
     }
   }
   rpc get-led-information {
     description "Show LED status";
     junos:command "show chassis led";
     input {
       uses command-forwarding;
     }
     output {
       choice output-tags {
         case actual-tag {
           container craft-lcd-led-information {
             uses craft-lcd-led-information-block;
           }
         }
         case multichassis-tag {
           container multi-routing-engine-results {
             list multi-routing-engine-item {
               leaf re-name {
                 type string;
               }
               choice output-tags {
                 case actual-tag {
                   container craft-lcd-led-information {
                     uses craft-lcd-led-information-block;
                   }
                 }
               }
             }
           }
         }
       }
     }
   }
   rpc get-led-fpc-information {
     description "Show LED status for FPC slot number";
     junos:command "show chassis led fpc-slot";
     input {
       uses command-forwarding;
       leaf fpc-slot {
         description "FPC slot number";
         junos:cli-feature "nokeyword";
         type union {
           type string {
             pattern "<.*>|$.*";
           }
           type uint32;
         }
       }
     }
     output {
       choice output-tags {
         case actual-tag {
           container craft-lcd-led-information {
             uses craft-lcd-led-information-block;
           }
         }
         case multichassis-tag {
           container multi-routing-engine-results {
             list multi-routing-engine-item {
               leaf re-name {
                 type string;
               }
               choice output-tags {
                 case actual-tag {
                   container craft-lcd-led-information {
                     uses craft-lcd-led-information-block;
                   }
                 }
               }
             }
           }
         }
       }
     }
   }
   rpc get-chassis-led-satellite-information {
     description "Show led details";
     junos:command "show chassis led satellite";
     input {
       leaf fpc-slot {
         description "Satellite slot number";
         type union {
           type string {
             pattern "<.*>|$.*";
           }
           type uint16 {
             range "65 .. 254";
           }
         }
       }
       leaf device-alias {
         description "Device alias";
         type string;
       }
     }
     output {
       choice output-tags {
         case output-tag {
           leaf output {
             type string;
           }
         }
         case actual-tag {
           anyxml chassis-led-satellite-information;
         }
         case multichassis-tag {
           anyxml multi-routing-engine-results;
         }
       }
     }
   }
   rpc get-chassis-cluster-interfaces {
     description "Display chassis cluster interfaces";
     junos:command "show chassis cluster interfaces";
     output {
       choice output-tags {
         case actual-tag {
           container chassis-cluster-interface-statistics {
             uses chassis-cluster-interface-statistics-block;
           }
         }
         case multichassis-tag {
           container multi-routing-engine-results {
             list multi-routing-engine-item {
               leaf re-name {
                 type string;
               }
               choice output-tags {
                 case actual-tag {
                   container chassis-cluster-interface-statistics {
                     uses chassis-cluster-interface-statistics-block;
                   }
                 }
               }
             }
           }
         }
       }
     }
   }
   rpc get-chassis-cluster-control-port-status {
     description "Display HA control port status";
     junos:command "show chassis cluster control-interface status";
     output {
       choice output-tags {
         case actual-tag {
           container chassis-cluster-control-port-status {
             uses chassis-cluster-control-port-status-block;
           }
         }
         case multichassis-tag {
           container multi-routing-engine-results {
             list multi-routing-engine-item {
               leaf re-name {
                 type string;
               }
               choice output-tags {
                 case actual-tag {
                   container chassis-cluster-control-port-status {
                     uses chassis-cluster-control-port-status-block;
                   }
                 }
               }
             }
           }
         }
       }
     }
   }
   rpc get-chassis-cluster-control-plane-statistics {
     description "Display control-plane statistics";
     junos:command "show chassis cluster control-plane statistics";
     output {
       choice output-tags {
         case actual-tag {
           container chassis-cluster-statistics {
             uses chassis-cluster-statistics-block;
           }
         }
         case multichassis-tag {
           container multi-routing-engine-results {
             list multi-routing-engine-item {
               leaf re-name {
                 type string;
               }
               choice output-tags {
                 case actual-tag {
                   container chassis-cluster-statistics {
                     uses chassis-cluster-statistics-block;
                   }
                 }
               }
             }
           }
         }
       }
     }
   }
   rpc get-chassis-cluster-data-plane-statistics {
     description "Display data-plane statistics";
     junos:command "show chassis cluster data-plane statistics";
     output {
       choice output-tags {
         case actual-tag {
           container services-synchronized {
             uses services-synchronized-block;
           }
         }
         case multichassis-tag {
           container multi-routing-engine-results {
             list multi-routing-engine-item {
               leaf re-name {
                 type string;
               }
               choice output-tags {
                 case actual-tag {
                   container services-synchronized {
                     uses services-synchronized-block;
                   }
                 }
               }
             }
           }
         }
       }
     }
   }
   rpc get-chassis-cluster-data-plane-interfaces {
     description "Display data-plane interfaces";
     junos:command "show chassis cluster data-plane interfaces";
     output {
       choice output-tags {
         case actual-tag {
           container chassis-cluster-dataplane-interfaces {
             uses chassis-cluster-dataplane-interfaces-block;
           }
         }
         case multichassis-tag {
           container multi-routing-engine-results {
             list multi-routing-engine-item {
               leaf re-name {
                 type string;
               }
               choice output-tags {
                 case actual-tag {
                   container chassis-cluster-dataplane-interfaces {
                     uses chassis-cluster-dataplane-interfaces-block;
                   }
                 }
               }
             }
           }
         }
       }
     }
   }
   rpc get-chassis-cluster-statistics {
     description "Display chassis cluster statistics";
     junos:command "show chassis cluster statistics";
     output {
       choice output-tags {
         case actual-tag {
           container chassis-cluster-statistics {
             uses chassis-cluster-statistics-block;
           }
         }
         case multichassis-tag {
           container multi-routing-engine-results {
             list multi-routing-engine-item {
               leaf re-name {
                 type string;
               }
               choice output-tags {
                 case actual-tag {
                   container chassis-cluster-statistics {
                     uses chassis-cluster-statistics-block;
                   }
                 }
               }
             }
           }
         }
       }
     }
   }
   rpc get-chassis-cluster-status {
     description "Display chassis cluster status";
     junos:command "show chassis cluster status";
     input {
       leaf redundancy-group {
         description "Display chassis cluster status per redundancy-group";
         type union {
           type string {
             pattern "<.*>|$.*";
           }
           type uint8;
         }
       }
     }
     output {
       choice output-tags {
         case actual-tag {
           container chassis-cluster-status {
             uses chassis-cluster-status-block;
           }
         }
         case multichassis-tag {
           container multi-routing-engine-results {
             list multi-routing-engine-item {
               leaf re-name {
                 type string;
               }
               choice output-tags {
                 case actual-tag {
                   container chassis-cluster-status {
                     uses chassis-cluster-status-block;
                   }
                 }
               }
             }
           }
         }
       }
     }
   }
   rpc get-chassis-cluster-information {
     description "Show chassis cluster information";
     junos:command "show chassis cluster information";
     input {
       uses command-forwarding;
     }
     output {
       choice output-tags {
         case actual-tag {
           container chassis-cluster-information {
             uses chassis-cluster-information-block;
           }
         }
         case multichassis-tag {
           container multi-routing-engine-results {
             list multi-routing-engine-item {
               leaf re-name {
                 type string;
               }
               choice output-tags {
                 case actual-tag {
                   container chassis-cluster-information {
                     uses chassis-cluster-information-block;
                   }
                 }
               }
             }
           }
         }
       }
     }
   }
   rpc get-chassis-cluster-configuration-synchronization-information {
     description "Display configuration synchronization information";
     junos:command "show chassis cluster information configuration-synchronization";
     input {
       uses command-forwarding;
     }
     output {
       choice output-tags {
         case actual-tag {
           container configuration-synchronization-information {
             uses configuration-synchronization-information-block;
           }
         }
         case multichassis-tag {
           container multi-routing-engine-results {
             list multi-routing-engine-item {
               leaf re-name {
                 type string;
               }
               choice output-tags {
                 case actual-tag {
                   container configuration-synchronization-information {
                     uses configuration-synchronization-information-block;
                   }
                 }
               }
             }
           }
         }
       }
     }
   }
   rpc get-chassis-cluster-issu-information {
     description "Display ISSU information";
     junos:command "show chassis cluster information issu";
     input {
       uses command-forwarding;
     }
     output {
       choice output-tags {
         case actual-tag {
           container issu-information {
             uses issu-information-block;
           }
         }
         case multichassis-tag {
           container multi-routing-engine-results {
             list multi-routing-engine-item {
               leaf re-name {
                 type string;
               }
               choice output-tags {
                 case actual-tag {
                   container issu-information {
                     uses issu-information-block;
                   }
                 }
               }
             }
           }
         }
       }
     }
   }
   rpc get-chassis-cluster-detail-information {
     description "Display all chassis cluster information";
     junos:command "show chassis cluster information detail";
     input {
       uses command-forwarding;
       leaf redundancy-group {
         description "Display chassis cluster status per redundancy-group";
         type union {
           type string {
             pattern "<.*>|$.*";
           }
           type uint8;
         }
       }
     }
     output {
       choice output-tags {
         case actual-tag {
           container chassis-cluster-detail-information {
             uses chassis-cluster-detail-information-block;
           }
         }
         case multichassis-tag {
           container multi-routing-engine-results {
             list multi-routing-engine-item {
               leaf re-name {
                 type string;
               }
               choice output-tags {
                 case actual-tag {
                   container chassis-cluster-detail-information {
                     uses chassis-cluster-detail-information-block;
                   }
                 }
               }
             }
           }
         }
       }
     }
   }
   rpc get-chassis-cluster-cold-synchronization-information {
     description "Display coldsync information";
     junos:command "show chassis cluster information detail coldsync";
     input {
       uses command-forwarding;
     }
     output {
       choice output-tags {
         case actual-tag {
           container cold-synchronization-monitoring-information {
             uses cold-synchronization-monitoring-information-block;
           }
         }
         case multichassis-tag {
           container multi-routing-engine-results {
             list multi-routing-engine-item {
               leaf re-name {
                 type string;
               }
               choice output-tags {
                 case actual-tag {
                   container cold-synchronization-monitoring-information {
                     uses cold-synchronization-monitoring-information-block;
                   }
                 }
               }
             }
           }
         }
       }
     }
   }
   rpc get-chassis-cluster-spu-information {
     description "Display SPU information";
     junos:command "show chassis cluster information detail spu";
     input {
       uses command-forwarding;
     }
     output {
       choice output-tags {
         case actual-tag {
           container spu-monitoring-information {
             uses spu-monitoring-information-block;
           }
         }
         case multichassis-tag {
           container multi-routing-engine-results {
             list multi-routing-engine-item {
               leaf re-name {
                 type string;
               }
               choice output-tags {
                 case actual-tag {
                   container spu-monitoring-information {
                     uses spu-monitoring-information-block;
                   }
                 }
               }
             }
           }
         }
       }
     }
   }
   rpc get-chassis-cluster-loopback-information {
     description "Display loopback monitoring information";
     junos:command "show chassis cluster information detail loopback";
     input {
       uses command-forwarding;
     }
     output {
       choice output-tags {
         case actual-tag {
           container loopback-information {
             uses loopback-information-block;
           }
         }
         case multichassis-tag {
           container multi-routing-engine-results {
             list multi-routing-engine-item {
               leaf re-name {
                 type string;
               }
               choice output-tags {
                 case actual-tag {
                   container loopback-information {
                     uses loopback-information-block;
                   }
                 }
               }
             }
           }
         }
       }
     }
   }
   rpc get-chassis-cluster-hardware-monitoring-information {
     description "Display hardware monitoring information";
     junos:command "show chassis cluster information detail hardware-monitor";
     input {
       uses command-forwarding;
     }
     output {
       choice output-tags {
         case actual-tag {
           container hardware-monitoring-information {
             uses hardware-monitoring-information-block;
           }
         }
         case multichassis-tag {
           container multi-routing-engine-results {
             list multi-routing-engine-item {
               leaf re-name {
                 type string;
               }
               choice output-tags {
                 case actual-tag {
                   container hardware-monitoring-information {
                     uses hardware-monitoring-information-block;
                   }
                 }
               }
             }
           }
         }
       }
     }
   }
   rpc get-chassis-cluster-schedule-monitoring-information {
     description "Display schedule monitoring information";
     junos:command "show chassis cluster information detail schedule-monitor";
     input {
       uses command-forwarding;
     }
     output {
       choice output-tags {
         case actual-tag {
           container schedule-monitoring-information {
             uses schedule-monitoring-information-block;
           }
         }
         case multichassis-tag {
           container multi-routing-engine-results {
             list multi-routing-engine-item {
               leaf re-name {
                 type string;
               }
               choice output-tags {
                 case actual-tag {
                   container schedule-monitoring-information {
                     uses schedule-monitoring-information-block;
                   }
                 }
               }
             }
           }
         }
       }
     }
   }
   rpc get-chassis-cluster-interface-monitoring-information {
     description "Display interface monitoring information";
     junos:command "show chassis cluster information detail interface-monitor";
     input {
       uses command-forwarding;
     }
     output {
       choice output-tags {
         case actual-tag {
           container interface-monitoring-information {
             uses interface-monitoring-information-block;
           }
         }
         case multichassis-tag {
           container multi-routing-engine-results {
             list multi-routing-engine-item {
               leaf re-name {
                 type string;
               }
               choice output-tags {
                 case actual-tag {
                   container interface-monitoring-information {
                     uses interface-monitoring-information-block;
                   }
                 }
               }
             }
           }
         }
       }
     }
   }
   rpc get-chassis-cluster-control-link-information {
     description "Display control link information";
     junos:command "show chassis cluster information detail control-link";
     input {
       uses command-forwarding;
     }
     output {
       choice output-tags {
         case actual-tag {
           container control-link-information {
             uses control-link-information-block;
           }
         }
         case multichassis-tag {
           container multi-routing-engine-results {
             list multi-routing-engine-item {
               leaf re-name {
                 type string;
               }
               choice output-tags {
                 case actual-tag {
                   container control-link-information {
                     uses control-link-information-block;
                   }
                 }
               }
             }
           }
         }
       }
     }
   }
   rpc get-chassis-cluster-fabric-link-information {
     description "Display fabric link information";
     junos:command "show chassis cluster information detail fabric-link";
     input {
       uses command-forwarding;
     }
     output {
       choice output-tags {
         case actual-tag {
           container fabric-link-information {
             uses fabric-link-information-block;
           }
         }
         case multichassis-tag {
           container multi-routing-engine-results {
             list multi-routing-engine-item {
               leaf re-name {
                 type string;
               }
               choice output-tags {
                 case actual-tag {
                   container fabric-link-information {
                     uses fabric-link-information-block;
                   }
                 }
               }
             }
           }
         }
       }
     }
   }
   rpc get-chassis-cluster-command-history-information {
     description "Display command history";
     junos:command "show chassis cluster information detail command-history";
     input {
       uses command-forwarding;
     }
     output {
       choice output-tags {
         case actual-tag {
           container command-history-information {
             uses command-history-information-block;
           }
         }
         case multichassis-tag {
           container multi-routing-engine-results {
             list multi-routing-engine-item {
               leaf re-name {
                 type string;
               }
               choice output-tags {
                 case actual-tag {
                   container command-history-information {
                     uses command-history-information-block;
                   }
                 }
               }
             }
           }
         }
       }
     }
   }
   rpc get-chassis-cluster-ip-monitoring-status {
     description "Display IP monitoring status";
     junos:command "show chassis cluster ip-monitoring status";
     input {
       uses command-forwarding;
     }
     output {
       choice output-tags {
         case actual-tag {
           container chassis-cluster-ip-monitoring {
             uses chassis-cluster-ip-monitoring-block;
           }
         }
         case multichassis-tag {
           container multi-routing-engine-results {
             list multi-routing-engine-item {
               leaf re-name {
                 type string;
               }
               choice output-tags {
                 case actual-tag {
                   container chassis-cluster-ip-monitoring {
                     uses chassis-cluster-ip-monitoring-block;
                   }
                 }
               }
             }
           }
         }
       }
     }
   }
   rpc get-chassis-cluster-ip-monitoring-status-redundancy-group {
     description "Show IP monitoring status of a specific redundancy-group";
     junos:command "show chassis cluster ip-monitoring status redundancy-group";
     input {
       uses command-forwarding;
       leaf redundancy-group-identifier {
         description "Redundancy-group identifier";
         junos:cli-feature "nokeyword";
         type union {
           type string {
             pattern "<.*>|$.*";
           }
           type uint8;
         }
         mandatory true;
       }
     }
     output {
       choice output-tags {
         case actual-tag {
           container chassis-cluster-ip-monitoring {
             uses chassis-cluster-ip-monitoring-block;
           }
         }
         case multichassis-tag {
           container multi-routing-engine-results {
             list multi-routing-engine-item {
               leaf re-name {
                 type string;
               }
               choice output-tags {
                 case actual-tag {
                   container chassis-cluster-ip-monitoring {
                     uses chassis-cluster-ip-monitoring-block;
                   }
                 }
               }
             }
           }
         }
       }
     }
   }
   rpc get-chassis-cluster-ethernet-switching-status {
     description "Display chassis cluster ethernet switching status";
     junos:command "show chassis cluster ethernet-switching status";
     output {
       choice output-tags {
         case actual-tag {
           container chassis-cluster-ethernet-switching-status {
             uses chassis-cluster-ethernet-switching-status-block;
           }
         }
         case multichassis-tag {
           container multi-routing-engine-results {
             list multi-routing-engine-item {
               leaf re-name {
                 type string;
               }
               choice output-tags {
                 case actual-tag {
                   container chassis-cluster-ethernet-switching-status {
                     uses chassis-cluster-ethernet-switching-status-block;
                   }
                 }
               }
             }
           }
         }
       }
     }
   }
   rpc get-chassis-cluster-switch-fabric-probe-statistics {
     description "Display chassis cluster switch fabric probe statistics";
     junos:command "show chassis cluster ethernet-switching statistics";
     output {
       choice output-tags {
         case actual-tag {
           container chassis-cluster-ethernet-switching-statistics {
             uses chassis-cluster-ethernet-switching-statistics-block;
           }
         }
         case multichassis-tag {
           container multi-routing-engine-results {
             list multi-routing-engine-item {
               leaf re-name {
                 type string;
               }
               choice output-tags {
                 case actual-tag {
                   container chassis-cluster-ethernet-switching-statistics {
                     uses chassis-cluster-ethernet-switching-statistics-block;
                   }
                 }
               }
             }
           }
         }
       }
     }
   }
   rpc get-chassis-cluster-switch-fabric-link-interfaces {
     description "Display chassis cluster switch fabric link interfaces";
     junos:command "show chassis cluster ethernet-switching interfaces";
     output {
       choice output-tags {
         case actual-tag {
           container chassis-cluster-ethernet-switching-interfaces {
             uses chassis-cluster-ethernet-switching-interfaces-block;
           }
         }
         case multichassis-tag {
           container multi-routing-engine-results {
             list multi-routing-engine-item {
               leaf re-name {
                 type string;
               }
               choice output-tags {
                 case actual-tag {
                   container chassis-cluster-ethernet-switching-interfaces {
                     uses chassis-cluster-ethernet-switching-interfaces-block;
                   }
                 }
               }
             }
           }
         }
       }
     }
   }
   rpc get-chassis-cluster-port-peering-status {
     description "Display chassis cluster port peering";
     junos:command "show chassis cluster port-peering";
     input {
       uses command-forwarding;
     }
     output {
       choice output-tags {
         case actual-tag {
           container chassis-cluster-port-peering-status {
             uses chassis-cluster-port-peering-status-block;
           }
         }
         case multichassis-tag {
           container multi-routing-engine-results {
             list multi-routing-engine-item {
               leaf re-name {
                 type string;
               }
               choice output-tags {
                 case actual-tag {
                   container chassis-cluster-port-peering-status {
                     uses chassis-cluster-port-peering-status-block;
                   }
                 }
               }
             }
           }
         }
       }
     }
   }
   rpc get-chassis-high-availability-information {
     description "Display high-availability information";
     junos:command "show chassis high-availability information";
     output {
       choice output-tags {
         case actual-tag {
           container chassis-high-availability-info {
             uses chassis-high-availability-info-block;
           }
         }
         case multichassis-tag {
           container multi-routing-engine-results {
             list multi-routing-engine-item {
               leaf re-name {
                 type string;
               }
               choice output-tags {
                 case actual-tag {
                   container chassis-high-availability-info {
                     uses chassis-high-availability-info-block;
                   }
                 }
               }
             }
           }
         }
       }
     }
   }
   rpc get-chassis-high-availability-detail-information {
     description "Display detailed high-availability info";
     junos:command "show chassis high-availability information detail";
     input {
       leaf services-redundancy-group {
         description "Service redundancy-group identifier";
         type union {
           type string {
             pattern "<.*>|$.*";
           }
           type uint8 {
             range "0 .. 20";
           }
         }
       }
     }
     output {
       choice output-tags {
         case actual-tag {
           container chassis-high-availability-detail-information {
             uses chassis-high-availability-detail-information-block;
           }
         }
         case multichassis-tag {
           container multi-routing-engine-results {
             list multi-routing-engine-item {
               leaf re-name {
                 type string;
               }
               choice output-tags {
                 case actual-tag {
                   container chassis-high-availability-detail-information {
                     uses chassis-high-availability-detail-information-block;
                   }
                 }
               }
             }
           }
         }
       }
     }
   }
   rpc get-chassis-high-availability-peer-information {
     description "Display high-availability peer information";
     junos:command "show chassis high-availability peer-info";
     output {
       choice output-tags {
         case actual-tag {
           container chassis-high-availability-peer-info-detail {
             uses chassis-high-availability-peer-info-detail-block;
           }
         }
         case multichassis-tag {
           container multi-routing-engine-results {
             list multi-routing-engine-item {
               leaf re-name {
                 type string;
               }
               choice output-tags {
                 case actual-tag {
                   container chassis-high-availability-peer-info-detail {
                     uses chassis-high-availability-peer-info-detail-block;
                   }
                 }
               }
             }
           }
         }
       }
     }
   }
   rpc get-chassis-ha-data-plane-statistics {
     description "Display data-plane statistics";
     junos:command "show chassis high-availability data-plane statistics";
     output {
       choice output-tags {
         case actual-tag {
           container chassis-cluster-data-plane-statistics {
             uses chassis-cluster-data-plane-statistics-block;
           }
         }
         case multichassis-tag {
           container multi-routing-engine-results {
             list multi-routing-engine-item {
               leaf re-name {
                 type string;
               }
               choice output-tags {
                 case actual-tag {
                   container chassis-cluster-data-plane-statistics {
                     uses chassis-cluster-data-plane-statistics-block;
                   }
                 }
               }
             }
           }
         }
       }
     }
   }
   rpc get-chassis-high-availability-srg-information {
     description "Show specific service-redundancy-group terse information";
     junos:command "show chassis high-availability services-redundancy-group";
     input {
       leaf services-redundancy-group-id {
         description "Service redundancy-group identifier";
         junos:cli-feature "nokeyword";
         type union {
           type string {
             pattern "<.*>|$.*";
           }
           type uint8 {
             range "0 .. 20";
           }
         }
         mandatory true;
       }
       leaf monitor-object {
         description "SRG monitored object name";
         type string;
       }
     }
     output {
       choice output-tags {
         case actual-tag {
           container chassis-high-availability-srg-terse-info {
             uses chassis-high-availability-srg-terse-info-block;
           }
         }
         case multichassis-tag {
           container multi-routing-engine-results {
             list multi-routing-engine-item {
               leaf re-name {
                 type string;
               }
               choice output-tags {
                 case actual-tag {
                   container chassis-high-availability-srg-terse-info {
                     uses chassis-high-availability-srg-terse-info-block;
                   }
                 }
               }
             }
           }
         }
       }
     }
   }
   rpc get-chassis-high-availability-prefix-information {
     description "Show ip prefix to srg mapping information";
     junos:command "show chassis high-availability prefix-srgid-table";
     output {
       choice output-tags {
         case actual-tag {
           container chassis-high-availability-prefix-information {
             uses chassis-high-availability-prefix-information-block;
           }
         }
         case multichassis-tag {
           container multi-routing-engine-results {
             list multi-routing-engine-item {
               leaf re-name {
                 type string;
               }
               choice output-tags {
                 case actual-tag {
                   container chassis-high-availability-prefix-information {
                     uses chassis-high-availability-prefix-information-block;
                   }
                 }
               }
             }
           }
         }
       }
     }
   }
   rpc get-chassis-high-availability-prefix-ip-information {
     description "IP to be queried for prefix-srgid mapping";
     junos:command "show chassis high-availability prefix-srgid-table query-ip";
     input {
       leaf ip-address {
         description "IP address";
         junos:cli-feature "nokeyword";
         type jt:ipaddr;
         mandatory true;
       }
       leaf routing-table {
         description "Routing table (e.g. - default)";
         type string;
         mandatory true;
       }
     }
     output {
       choice output-tags {
         case actual-tag {
           container chassis-high-availability-prefix-ip-information {
             uses chassis-high-availability-prefix-ip-information-block;
           }
         }
         case multichassis-tag {
           container multi-routing-engine-results {
             list multi-routing-engine-item {
               leaf re-name {
                 type string;
               }
               choice output-tags {
                 case actual-tag {
                   container chassis-high-availability-prefix-ip-information {
                     uses chassis-high-availability-prefix-ip-information-block;
                   }
                 }
               }
             }
           }
         }
       }
     }
   }
   rpc get-chassis-high-availability-prefix-srgid-information {
     description "SRG id to be queried for prefix-srgid mapping";
     junos:command "show chassis high-availability prefix-srgid-table query-srgid";
     input {
       leaf srg-id {
         description "Service redundancy-group identifier";
         junos:cli-feature "nokeyword";
         type union {
           type string {
             pattern "<.*>|$.*";
           }
           type uint8 {
             range "0 .. 20";
           }
         }
         mandatory true;
       }
     }
     output {
       choice output-tags {
         case actual-tag {
           container chassis-high-availability-prefix-srgid-information {
             uses chassis-high-availability-prefix-srgid-information-block;
           }
         }
         case multichassis-tag {
           container multi-routing-engine-results {
             list multi-routing-engine-item {
               leaf re-name {
                 type string;
               }
               choice output-tags {
                 case actual-tag {
                   container chassis-high-availability-prefix-srgid-information {
                     uses chassis-high-availability-prefix-srgid-information-block;
                   }
                 }
               }
             }
           }
         }
       }
     }
   }
   rpc get-chassis-high-availability-prefix-policy-information {
     description "Show policy table information";
     junos:command "show chassis high-availability prefix-srgid-table prefix-policy-table";
     output {
       choice output-tags {
         case actual-tag {
           container chassis-high-availability-prefix-policy-information {
             uses chassis-high-availability-prefix-policy-information-block;
           }
         }
         case multichassis-tag {
           container multi-routing-engine-results {
             list multi-routing-engine-item {
               leaf re-name {
                 type string;
               }
               choice output-tags {
                 case actual-tag {
                   container chassis-high-availability-prefix-policy-information {
                     uses chassis-high-availability-prefix-policy-information-block;
                   }
                 }
               }
             }
           }
         }
       }
     }
   }
   rpc get-chassis-satellite-information {
     description "Show Satellite Devices information";
     junos:command "show chassis satellite";
     input {
       choice arg {
         case fpc-slot {
           leaf fpc-slot {
             description "Satellite slot number";
             type union {
               type string {
                 pattern "<.*>|$.*";
               }
               type uint32 {
                 range "65 .. 254";
               }
             }
           }
         }
         case device-alias {
           leaf device-alias {
             description "Device alias";
             type string;
           }
         }
       }
       leaf cluster {
         description "Cluster name";
         type string;
       }
       leaf since {
         description "Show history since YYYY-MM-DD.HH:MM:SS";
         type jt:time;
       }
       leaf level {
         junos:cli-feature "nokeyword";
         default "brief";
         type enumeration {
           enum "terse" {
             description "Display terse output";
           }
           enum "brief" {
             description "Display brief output (default)";
           }
           enum "detail" {
             description "Display detailed output";
           }
           enum "extensive" {
             description "Display extensive output";
           }
         }
       }
     }
     output {
       choice output-tags {
         case actual-tag {
           container satellite-information {
             uses satellite-information-block;
           }
         }
         case multichassis-tag {
           container multi-routing-engine-results {
             list multi-routing-engine-item {
               leaf re-name {
                 type string;
               }
               choice output-tags {
                 case actual-tag {
                   container satellite-information {
                     uses satellite-information-block;
                   }
                 }
               }
             }
           }
         }
       }
     }
   }
   rpc get-chassis-satellite-unprovision-information {
     description "Display unprovisioned satellites";
     junos:command "show chassis satellite unprovision";
     input {
       leaf system-id {
         description "Satellite system id";
         junos:cli-feature "nokeyword";
         type jt:mac-addr;
       }
       leaf since {
         description "Show history since YYYY-MM-DD.HH:MM:SS";
         type jt:time;
       }
       leaf level {
         junos:cli-feature "nokeyword";
         default "brief";
         type enumeration {
           enum "brief" {
             description "Display brief output (default)";
           }
           enum "detail" {
             description "Display detailed output";
           }
           enum "extensive" {
             description "Display extensive output";
           }
         }
       }
     }
     output {
       choice output-tags {
         case actual-tag {
           container satellite-information {
             uses satellite-information-block;
           }
         }
         case multichassis-tag {
           container multi-routing-engine-results {
             list multi-routing-engine-item {
               leaf re-name {
                 type string;
               }
               choice output-tags {
                 case actual-tag {
                   container satellite-information {
                     uses satellite-information-block;
                   }
                 }
               }
             }
           }
         }
       }
     }
   }
   rpc get-chassis-satellite-statistics {
     description "Display device statistics information";
     junos:command "show chassis satellite statistics";
     input {
       choice arg {
         case fpc-slot {
           leaf fpc-slot {
             description "Satellite slot number";
             type union {
               type string {
                 pattern "<.*>|$.*";
               }
               type uint32 {
                 range "65 .. 254";
               }
             }
           }
         }
         case device-alias {
           leaf device-alias {
             description "Device alias";
             type string;
           }
         }
       }
       leaf cluster {
         description "Cluster name";
         type string;
       }
     }
     output {
       choice output-tags {
         case output-tag {
           leaf output {
             type string;
           }
         }
         case actual-tag {
           anyxml device-statistics;
         }
         case multichassis-tag {
           anyxml multi-routing-engine-results;
         }
       }
     }
   }
   rpc get-chassis-satellite-redundancy-group-info {
     description "Display multi-chassis cluster information";
     junos:command "show chassis satellite redundancy-group";
     input {
       leaf since {
         description "Show history since YYYY-MM-DD.HH:MM:SS";
         type jt:time;
       }
       leaf level {
         junos:cli-feature "nokeyword";
         default "terse";
         type enumeration {
           enum "terse" {
             description "Display terse output (default)";
           }
           enum "brief" {
             description "Display brief output";
           }
           enum "detail" {
             description "Display detailed output";
           }
           enum "extensive" {
             description "Display extensive output";
           }
         }
       }
     }
     output {
       choice output-tags {
         case actual-tag {
           container multi-chassis-cluster-information {
             uses multi-chassis-cluster-information-block;
           }
         }
         case multichassis-tag {
           container multi-routing-engine-results {
             list multi-routing-engine-item {
               leaf re-name {
                 type string;
               }
               choice output-tags {
                 case actual-tag {
                   container multi-chassis-cluster-information {
                     uses multi-chassis-cluster-information-block;
                   }
                 }
               }
             }
           }
         }
       }
     }
   }
   rpc get-chassis-satellite-redundacy-grp-devices-info {
     description "Display satellite device information";
     junos:command "show chassis satellite redundancy-group devices";
     input {
       leaf fpc-slot {
         description "Satellite slot number";
         type union {
           type string {
             pattern "<.*>|$.*";
           }
           type uint32 {
             range "65 .. 254";
           }
         }
       }
       leaf level {
         junos:cli-feature "nokeyword";
         default "terse";
         type enumeration {
           enum "terse" {
             description "Display terse output (default)";
           }
           enum "brief" {
             description "Display brief output";
           }
           enum "detail" {
             description "Display detailed output";
           }
           enum "extensive" {
             description "Display extensive output";
           }
         }
       }
     }
     output {
       choice output-tags {
         case actual-tag {
           container multi-chassis-cluster-device-information {
             uses multi-chassis-cluster-device-information-block;
           }
         }
         case multichassis-tag {
           container multi-routing-engine-results {
             list multi-routing-engine-item {
               leaf re-name {
                 type string;
               }
               choice output-tags {
                 case actual-tag {
                   container multi-chassis-cluster-device-information {
                     uses multi-chassis-cluster-device-information-block;
                   }
                 }
               }
             }
           }
         }
       }
     }
   }
   rpc get-chassis-satellite-redundancy-grp-dev-history {
     description "Display device history information";
     junos:command "show chassis satellite redundancy-group devices history";
     input {
       leaf verbosity_level {
         junos:cli-feature "nokeyword";
         default "brief";
         type enumeration {
           enum "brief" {
             description "Display brief output (default)";
           }
           enum "detail" {
             description "Display detailed output";
           }
           enum "extensive" {
             description "Display extensive output";
           }
         }
       }
       leaf serial-number {
         description "Device Serial Number";
         type string;
       }
       leaf global {
         description "Global history";
         type empty;
       }
     }
     output {
       choice output-tags {
         case output-tag {
           leaf output {
             type string;
           }
         }
         case actual-tag {
           anyxml multi-chassis-cluster-device-history-information;
         }
         case multichassis-tag {
           anyxml multi-routing-engine-results;
         }
       }
     }
   }
   rpc get-chassis-satellite-redundacy-grp-if-info {
     description "Display satellite interface information";
     junos:command "show chassis satellite redundancy-group interfaces";
     input {
       leaf interface-name {
         description "Name of interface";
         junos:cli-feature "nokeyword";
         type union {
           type jt:interface-name;
           type string {
             pattern "<.*>|$.*";
           }
         }
       }
       leaf level {
         junos:cli-feature "nokeyword";
         default "terse";
         type enumeration {
           enum "terse" {
             description "Display terse output (default)";
           }
           enum "brief" {
             description "Display brief output";
           }
           enum "detail" {
             description "Display detailed output";
           }
           enum "extensive" {
             description "Display extensive output";
           }
         }
       }
     }
     output {
       choice output-tags {
         case actual-tag {
           container multi-chassis-cluster-interface-information {
             uses multi-chassis-cluster-interface-information-block;
           }
         }
         case multichassis-tag {
           container multi-routing-engine-results {
             list multi-routing-engine-item {
               leaf re-name {
                 type string;
               }
               choice output-tags {
                 case actual-tag {
                   container multi-chassis-cluster-interface-information {
                     uses multi-chassis-cluster-interface-information-block;
                   }
                 }
               }
             }
           }
         }
       }
     }
   }
   rpc get-chassis-satellite-extended-port-information {
     description "Display extended-port information";
     junos:command "show chassis satellite extended-port";
     input {
       leaf interface-name {
         description "Interface name";
         junos:cli-feature "nokeyword";
         type string;
       }
       leaf since {
         description "Show history since YYYY-MM-DD.HH:MM:SS";
         type jt:time;
       }
       leaf fpc-slot {
         description "Satellite slot number";
         type union {
           type string {
             pattern "<.*>|$.*";
           }
           type uint32 {
             range "65 .. 254";
           }
         }
       }
       leaf level {
         junos:cli-feature "nokeyword";
         default "terse";
         type enumeration {
           enum "terse" {
             description "Display terse output (default)";
           }
           enum "brief" {
             description "Display brief output";
           }
           enum "detail" {
             description "Display detailed output";
           }
           enum "extensive" {
             description "Display extensive output";
           }
         }
       }
     }
     output {
       choice output-tags {
         case actual-tag {
           container extended-port-information {
             uses extended-port-information-block;
           }
         }
         case multichassis-tag {
           container multi-routing-engine-results {
             list multi-routing-engine-item {
               leaf re-name {
                 type string;
               }
               choice output-tags {
                 case actual-tag {
                   container extended-port-information {
                     uses extended-port-information-block;
                   }
                 }
               }
             }
           }
         }
       }
     }
   }
   rpc get-chassis-satellite-upgrade-group-information {
     description "Display upgrade group information";
     junos:command "show chassis satellite upgrade-group";
     input {
       leaf level {
         junos:cli-feature "nokeyword";
         default "terse";
         type enumeration {
           enum "terse" {
             description "Display terse output (default)";
           }
           enum "brief" {
             description "Display brief output";
           }
           enum "detail" {
             description "Display detailed output";
           }
           enum "extensive" {
             description "Display extensive output";
           }
         }
       }
       leaf group-name {
         description "Upgrade group name";
         junos:cli-feature "nokeyword";
         type string;
       }
     }
     output {
       choice output-tags {
         case actual-tag {
           container upgrade-group-information {
             uses upgrade-group-information-block;
           }
         }
         case multichassis-tag {
           container multi-routing-engine-results {
             list multi-routing-engine-item {
               leaf re-name {
                 type string;
               }
               choice output-tags {
                 case actual-tag {
                   container upgrade-group-information {
                     uses upgrade-group-information-block;
                   }
                 }
               }
             }
           }
         }
       }
     }
   }
   rpc get-chassis-satellite-neighbor-information {
     description "Display satellite adjacency information";
     junos:command "show chassis satellite neighbor";
     input {
       leaf interface-name {
         description "Name of interface";
         junos:cli-feature "nokeyword";
         type string;
       }
       leaf since {
         description "Show history since YYYY-MM-DD.HH:MM:SS";
         type jt:time;
       }
       leaf level {
         junos:cli-feature "nokeyword";
         default "terse";
         type enumeration {
           enum "terse" {
             description "Display terse output (default)";
           }
           enum "brief" {
             description "Display brief output";
           }
           enum "detail" {
             description "Display detailed output";
           }
           enum "extensive" {
             description "Display extensive output";
           }
         }
       }
     }
     output {
       choice output-tags {
         case actual-tag {
           container adjacency-information {
             uses adjacency-information-block;
           }
         }
         case multichassis-tag {
           container multi-routing-engine-results {
             list multi-routing-engine-item {
               leaf re-name {
                 type string;
               }
               choice output-tags {
                 case actual-tag {
                   container adjacency-information {
                     uses adjacency-information-block;
                   }
                 }
               }
             }
           }
         }
       }
     }
   }
   rpc get-chassis-satellite-neighbor-statistics {
     description "Display adjacency statistics information";
     junos:command "show chassis satellite neighbor statistics";
     input {
       leaf interface-name {
         description "Name of interface";
         junos:cli-feature "nokeyword";
         type string;
       }
     }
     output {
       choice output-tags {
         case actual-tag {
           container adjacency-statistics {
             uses adjacency-statistics-block;
           }
         }
         case multichassis-tag {
           container multi-routing-engine-results {
             list multi-routing-engine-item {
               leaf re-name {
                 type string;
               }
               choice output-tags {
                 case actual-tag {
                   container adjacency-statistics {
                     uses adjacency-statistics-block;
                   }
                 }
               }
             }
           }
         }
       }
     }
   }
   rpc get-chassis-satellite-interface-information {
     description "Display satellite protocol interface information";
     junos:command "show chassis satellite interface";
     input {
       leaf verbosity_level {
         junos:cli-feature "nokeyword";
         default "brief";
         type enumeration {
           enum "brief" {
             description "Display brief output (default)";
           }
           enum "detail" {
             description "Display detailed output";
           }
           enum "extensive" {
             description "Display extensive output";
           }
         }
       }
       leaf interface-name {
         description "Name of interface";
         junos:cli-feature "nokeyword";
         type string;
       }
       leaf since {
         description "Show history since YYYY-MM-DD.HH:MM:SS";
         type jt:time;
       }
     }
     output {
       choice output-tags {
         case actual-tag {
           container satellite-interface-information {
             uses satellite-interface-information-block;
           }
         }
         case multichassis-tag {
           container multi-routing-engine-results {
             list multi-routing-engine-item {
               leaf re-name {
                 type string;
               }
               choice output-tags {
                 case actual-tag {
                   container satellite-interface-information {
                     uses satellite-interface-information-block;
                   }
                 }
               }
             }
           }
         }
       }
     }
   }
   rpc get-satellite-management-software-information {
     description "Show satellite software installed";
     junos:command "show chassis satellite software";
     input {
       leaf level {
         junos:cli-feature "nokeyword";
         default "brief";
         type enumeration {
           enum "brief" {
             description "Display brief output (default)";
           }
           enum "detail" {
             description "Display detailed output";
           }
         }
       }
     }
     output {
       choice output-tags {
         case actual-tag {
           container satellite-software-information {
             uses satellite-software-information-block;
           }
         }
         case multichassis-tag {
           container multi-routing-engine-results {
             list multi-routing-engine-item {
               leaf re-name {
                 type string;
               }
               choice output-tags {
                 case actual-tag {
                   container satellite-software-information {
                     uses satellite-software-information-block;
                   }
                 }
               }
             }
           }
         }
       }
     }
   }
   rpc get-satellite-power-budget-information {
     description "Show power budget chassis satellite information";
     junos:command "show chassis satellite power-budget-statistics";
     input {
       leaf fpc-slot {
         description "Satellite slot number";
         type union {
           type string {
             pattern "<.*>|$.*";
           }
           type uint16 {
             range "65 .. 254";
           }
         }
       }
     }
     output {
       choice output-tags {
         case actual-tag {
           container power-budget-information {
             uses power-budget-information-block;
           }
         }
         case multichassis-tag {
           container multi-routing-engine-results {
             list multi-routing-engine-item {
               leaf re-name {
                 type string;
               }
               choice output-tags {
                 case actual-tag {
                   container power-budget-information {
                     uses power-budget-information-block;
                   }
                 }
               }
             }
           }
         }
       }
     }
   }
   rpc get-chassis-satellite-cluster-information {
     description "Show Satellite Cluster information";
     junos:command "show chassis satellite-cluster";
     input {
       leaf cluster {
         description "Cluster name";
         type string;
       }
       leaf level {
         junos:cli-feature "nokeyword";
         default "brief";
         type enumeration {
           enum "terse" {
             description "Display terse output";
           }
           enum "brief" {
             description "Display brief output (default)";
           }
           enum "detail" {
             description "Display detailed output";
           }
           enum "extensive" {
             description "Display extensive output";
           }
         }
       }
     }
     output {
       choice output-tags {
         case actual-tag {
           container satellite-cluster-information {
             uses satellite-cluster-information-block;
           }
         }
         case multichassis-tag {
           container multi-routing-engine-results {
             list multi-routing-engine-item {
               leaf re-name {
                 type string;
               }
               choice output-tags {
                 case actual-tag {
                   container satellite-cluster-information {
                     uses satellite-cluster-information-block;
                   }
                 }
               }
             }
           }
         }
       }
     }
   }
   rpc get-chassis-satellite-cluster-route {
     description "Display cluster route information";
     junos:command "show chassis satellite-cluster route";
     input {
       leaf cluster {
         description "Cluster name";
         type string;
       }
       leaf fpc-slot {
         description "Satellite slot number";
         type union {
           type string {
             pattern "<.*>|$.*";
           }
           type uint32 {
             range "65 .. 254";
           }
         }
       }
     }
     output {
       choice output-tags {
         case output-tag {
           leaf output {
             type string;
           }
         }
         case actual-tag {
           anyxml cluster-statistics-route;
         }
         case multichassis-tag {
           anyxml multi-routing-engine-results;
         }
       }
     }
   }
   rpc get-chassis-satellite-cluster-statistics {
     description "Display cluster statistics information";
     junos:command "show chassis satellite-cluster statistics";
     input {
       leaf cluster {
         description "Cluster name";
         type string;
       }
       leaf fpc-slot {
         description "Satellite slot number";
         type union {
           type string {
             pattern "<.*>|$.*";
           }
           type uint32 {
             range "65 .. 254";
           }
         }
       }
     }
     output {
       choice output-tags {
         case output-tag {
           leaf output {
             type string;
           }
         }
         case actual-tag {
           anyxml cluster-statistics;
         }
         case multichassis-tag {
           anyxml multi-routing-engine-results;
         }
       }
     }
   }
   rpc get-chassis-pic-mode-information {
     description "Show a member's chassis pic-mode";
     junos:command "show chassis pic-mode";
     input {
       uses command-forwarding;
     }
     output {
       choice output-tags {
         case actual-tag {
           container chassis-pic-mode-information {
             uses chassis-pic-mode-information-block;
           }
         }
         case multichassis-tag {
           container multi-routing-engine-results {
             list multi-routing-engine-item {
               leaf re-name {
                 type string;
               }
               choice output-tags {
                 case actual-tag {
                   container chassis-pic-mode-information {
                     uses chassis-pic-mode-information-block;
                   }
                 }
               }
             }
           }
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping chassis-scb-ha-port-block {
     container chassis-scb-ha-port-eeprom {
       description
         "Information about Switch Control Board HA control port ideeprom 
         data";
       leaf scb-port-number {
         type int32;
         description
           "Port number on the PIC";
       }
       leaf scb-cable-type {
         type string;
         description
           "Port cable type";
       }
       leaf scb-fiber-mode {
         type string;
         description
           "Single or multi-mode";
       }
       leaf scb-sfp-vendor-name {
         type string;
         description
           "SFP vendor name";
       }
       leaf scb-sfp-vendor-pno {
         type string;
         description
           "SFP vendor part number";
       }
       leaf scb-wavelength {
         type string;
         description
           "Wavelength of the optical transceiver";
       }
       leaf scb-sfp-vendor-fw-ver {
         type string;
         description
           "Vendor firmware version";
       }
       leaf scb-sfp-jnpr-ver {
         type string;
         description
           "Juniper revision";
       }
       leaf scb-sfp-msa-version {
         type string;
         description
           "Multi-Source Agreement version";
       }
     }
     container chassis-scb-ha-port-diag {
       description
         "Information about Switch Control Board HA control port diagnostics
         data";
       leaf port-index {
         type int32;
       }
       leaf current {
         type string;
       }
       leaf output-powers {
         type string;
       }
       leaf temp {
         type string;
       }
       leaf-list voltage {
         type string;
       }
       leaf receiver-power {
         type string;
       }
       leaf alarm-warning-flags {
         type string;
       }
       leaf current-high-alarm {
         type string;
       }
       leaf current-low-alarm {
         type string;
       }
       leaf current-high-warning {
         type string;
       }
       leaf current-low-warning {
         type string;
       }
       leaf output-power-high-alarm {
         type string;
       }
       leaf output-power-low-alarm {
         type string;
       }
       leaf output-power-high-warning {
         type string;
       }
       leaf output-power-low-warning {
         type string;
       }
       leaf temperature-high-alarm {
         type string;
       }
       leaf temperature-low-alarm {
         type string;
       }
       leaf temperature-high-warning {
         type string;
       }
       leaf temperature-low-warning {
         type string;
       }
       leaf voltage-high-alarm {
         type string;
       }
       leaf voltage-low-alarm {
         type string;
       }
       leaf voltage-high-warning {
         type string;
       }
       leaf voltage-low-warning {
         type string;
       }
       leaf rx-power-high-alarm {
         type string;
       }
       leaf rx-power-low-alarm {
         type string;
       }
       leaf rx-power-high-warning {
         type string;
       }
       leaf rx-power-low-warning {
         type string;
       }
       leaf current-high-alarm-threshold {
         type string;
       }
       leaf current-low-alarm-threshold {
         type string;
       }
       leaf current-high-warning-threshold {
         type string;
       }
       leaf current-low-warning-threshold {
         type string;
       }
       leaf output-power-high-alarm-threshold {
         type string;
       }
       leaf output-power-low-alarm-threshold {
         type string;
       }
       leaf output-power-high-warning-threshold {
         type string;
       }
       leaf output-power-low-warning-threshold {
         type string;
       }
       leaf temperature-high-alarm-threshold {
         type string;
       }
       leaf temperature-low-alarm-threshold {
         type string;
       }
       leaf temperature-high-warning-threshold {
         type string;
       }
       leaf temperature-low-warning-threshold {
         type string;
       }
       leaf voltage-high-alarm-threshold {
         type string;
       }
       leaf voltage-low-alarm-threshold {
         type string;
       }
       leaf voltage-high-warning-threshold {
         type string;
       }
       leaf voltage-low-warning-threshold {
         type string;
       }
       leaf rx-power-high-alarm-threshold {
         type string;
       }
       leaf rx-power-low-alarm-threshold {
         type string;
       }
       leaf rx-power-high-warning-threshold {
         type string;
       }
       leaf rx-power-low-warning-threshold {
         type string;
       }
     }
   }
   grouping uft-information-block {
     leaf uft {
       type string;
     }
   }
   grouping system-mode-information-block {
     leaf system-mode {
       type string;
     }
     leaf system-mode-warning {
       type string;
     }
   }
   grouping power-usage-information-block {
     leaf capacity-actual {
       type uint32;
       description
         "Actual capacity in volt";
     }
     leaf capacity-max {
       type uint32;
       description
         "Maximum capacity in volt";
     }
     leaf capacity-allocated {
       type uint32;
       description
         "Allocated capacity in volt";
     }
     leaf capacity-remaining {
       type uint32;
       description
         "Remaining capacity in volt";
     }
     leaf capacity-actual-usage {
       type uint32;
       description
         "Actual usage in volt";
     }
     leaf capacity-load {
       type uint32;
       description
         "Percentage usage";
     }
     leaf zone {
       type uint32;
       description
         "Power zone";
     }
     leaf str-zone {
       type string;
       description
         "Power zone";
     }
     container power-usage-item {
       leaf name {
         type string;
         description
           "Name of this component";
       }
       leaf status {
         type string;
         description
           "Status of clock synchronization source";
       }
       leaf state {
         type string;
         description
           "Status of the component";
       }
       container ac-input-detail {
         leaf ac-input {
           type string;
           description
             "AC input state";
         }
         leaf ac-expect-feed {
           type uint32;
           description
             "Expect power input feed";
         }
         leaf ac-actual-feed {
           type uint32;
           description
             "Actual power input feed";
         }
       }
       container ac-input-detail2 {
         leaf ac-input_status {
           type string;
           description
             "AC input status";
         }
         leaf str-ac-expect-feed {
           type string;
           description
             "Expect power input feed";
         }
         leaf str-ac-actual-feed {
           type string;
           description
             "Actual power input feed";
         }
         leaf ac-feed0-voltage {
           type string;
           description
             "AC feed0 voltage";
         }
         leaf ac-feed0-current {
           type string;
           description
             "AC feed0 current";
         }
         leaf ac-feed0-power {
           type string;
           description
             "AC feed0 power";
         }
         leaf ac-feed1-voltage {
           type string;
           description
             "AC feed1 voltage";
         }
         leaf ac-feed1-current {
           type string;
           description
             "AC feed1 current";
         }
         leaf ac-feed1-power {
           type string;
           description
             "AC feed1 power";
         }
       }
       container dc-input-detail {
         leaf dc-input {
           type string;
           description
             "DC input state";
         }
         leaf dc-expect-feed {
           type uint32;
           description
             "Expect power input feed";
         }
         leaf dc-actual-feed {
           type uint32;
           description
             "Actual power input feed";
         }
         leaf reference-voltage {
           type string;
           description
             "Voltage of the item in Volts";
         }
         leaf actual-voltage {
           type int32;
           description
             "Voltage of the item in mVlots";
         }
       }
       container dc-input-detail2 {
         leaf dc-input-status {
           type string;
           description
             "DC input status";
         }
         leaf str-dc-expect-feed {
           type string;
           description
             "Expect power input feed";
         }
         leaf str-dc-actual-feed {
           type string;
           description
             "Actual power input feed";
         }
         leaf dc-feed0-voltage {
           type string;
           description
             "DC feed0 voltage";
         }
         leaf dc-feed0-current {
           type string;
           description
             "DC feed0 current";
         }
         leaf dc-feed0-power {
           type string;
           description
             "DC feed0 power";
         }
         leaf dc-feed1-voltage {
           type string;
           description
             "DC feed1 voltage";
         }
         leaf dc-feed1-current {
           type string;
           description
             "DC feed1 current";
         }
         leaf dc-feed1-power {
           type string;
           description
             "DC feed1 power";
         }
       }
       container dc-output-detail {
         leaf dc-power {
           type uint32;
         }
         leaf zone {
           type uint32;
           description
             "Power zone";
         }
         leaf dc-current {
           type uint32;
         }
         leaf dc-voltage {
           type uint32;
         }
         leaf dc-load {
           type uint32;
         }
         leaf str3-dc-current {
           type string;
         }
         leaf str3-dc-voltage {
           type string;
         }
       }
       container dc-output-detail2 {
         leaf str-dc-power {
           type string;
         }
         leaf str-zone {
           type string;
           description
             "Power zone";
         }
         leaf str-dc-current {
           type string;
         }
         leaf str-dc-voltage {
           type string;
         }
         leaf str-dc-load {
           type string;
         }
       }
       container dc-output-detail3 {
         leaf str2-dc-power {
           type string;
         }
         leaf str2-dc-current {
           type string;
         }
         leaf str2-dc-voltage {
           type string;
         }
         leaf str2-dc-load {
           type string;
         }
       }
       container pem-capacity-detail {
         leaf capacity-actual {
           type uint32;
           description
             "Actual capacity in volt";
         }
         leaf capacity-max {
           type uint32;
           description
             "Maximum capacity in volt";
         }
       }
       container dc-output-detail4 {
         leaf dc-power1 {
           type uint32;
         }
         leaf zone1 {
           type uint32;
         }
         leaf str4-dc-current {
           type string;
         }
         leaf str4-dc-voltage {
           type string;
         }
         leaf dc-load-integer {
           type uint32;
         }
         leaf str-dip-switch-input {
           type string;
         }
       }
       container input-mode-detail {
         leaf feed-number {
           type uint32;
           description
             "Index of the Feed";
         }
         leaf feed-type {
           type string;
           description
             "Type of input given to the feed";
         }
       }
     }
     container power-usage-system {
       leaf capacity-res-power {
         type uint32;
       }
       leaf capacity-sys-actual {
         type uint32;
       }
       leaf capacity-sys-max {
         type uint32;
       }
       leaf capacity-sys-remaining {
         type uint32;
       }
       container power-usage-zone-information {
         leaf zone {
           type uint32;
           description
             "Power zone";
         }
         leaf str-zone {
           type string;
           description
             "Power zone";
         }
         leaf capacity-actual {
           type uint32;
           description
             "Actual capacity in volt";
         }
         leaf capacity-max {
           type uint32;
           description
             "Maximum capacity in volt";
         }
         leaf capacity-allocated {
           type uint32;
           description
             "Allocated capacity in volt";
         }
         leaf capacity-remaining {
           type uint32;
           description
             "Remaining capacity in volt";
         }
         leaf capacity-actual-usage {
           type uint32;
           description
             "Actual usage in volt";
         }
       }
       container power-mode-system-information {
         leaf power-mode {
           type string;
           description
             "Power mode";
         }
       }
     }
     container power-usage-system2 {
       container power-usage-zone-information2 {
         leaf capacity-actual {
           type uint32;
           description
             "Actual capacity in volt";
         }
         leaf capacity-max {
           type uint32;
           description
             "Maximum capacity in volt";
         }
         leaf capacity-allocated {
           type uint32;
           description
             "Allocated capacity in volt";
         }
         leaf capacity-remaining {
           type uint32;
           description
             "Remaining capacity in volt";
         }
         leaf capacity-actual-usage {
           type uint32;
           description
             "Actual usage in volt";
         }
       }
     }
     container power-usage-total {
       leaf dc-power {
         type uint32;
       }
     }
     container power-usage-voltage-total {
       leaf dc-power {
         type uint32;
       }
     }
     container power-usage-pdu-item {
       leaf slot {
         type int32;
       }
       leaf dc-power {
         type uint32;
       }
       container power-usage-psm-item {
         leaf slot {
           type int32;
         }
         container power-usage-psm-input {
           leaf name {
             type string;
             description
               "Name of this component";
           }
           leaf dc-voltage {
             type uint32;
           }
           leaf dc-power {
             type uint32;
           }
         }
         leaf state {
           type string;
           description
             "Status of the component";
         }
         container power-usage-psm-detail {
           leaf capacity-actual {
             type uint32;
             description
               "Actual capacity in volt";
           }
           leaf capacity-max {
             type uint32;
             description
               "Maximum capacity in volt";
           }
         }
       }
     }
     container power-usage-psm-item1 {
       leaf slot {
         type int32;
       }
       container power-usage-psm-input1 {
         leaf name {
           type string;
           description
             "Name of this component";
         }
         leaf dc-voltage {
           type uint32;
         }
         leaf dc-power {
           type uint32;
         }
         container power-usage-psm-a-feed {
           leaf feed-a-num {
             type uint32;
           }
           leaf dc-vin-a {
             type uint32;
           }
         }
         container power-usage-psm-b-feed {
           leaf feed-b-num {
             type uint32;
           }
           leaf dc-vin-b {
             type uint32;
           }
         }
         container power-usage-psm-ac-feed {
           leaf name {
             type string;
             description
               "Name of this component";
           }
           leaf ac-voltage {
             type uint32;
           }
           leaf ac-power {
             type uint32;
           }
         }
         container power-usage-psm-dc-feed {
           leaf name {
             type string;
             description
               "Name of this component";
           }
           leaf dc-voltage {
             type uint32;
           }
           leaf dc-power {
             type uint32;
           }
         }
       }
       leaf name {
         type string;
         description
           "Name of this component";
       }
       leaf state {
         type string;
         description
           "Status of the component";
       }
       container power-usage-psm-info {
         leaf psm-type {
           type string;
           description
             "Psm type";
         }
         leaf psm-feed {
           type string;
           description
             "Psm feed";
         }
       }
       container power-usage-psm-output {
         leaf name {
           type string;
           description
             "Name of this component";
         }
         leaf dc-voltage {
           type uint32;
         }
         leaf dc-power {
           type uint32;
         }
         leaf input-source {
           type string;
           description
             "Input source";
         }
       }
       container power-usage-psm-detail1 {
         leaf capacity-actual {
           type uint32;
           description
             "Actual capacity in volt";
         }
         leaf capacity-max {
           type uint32;
           description
             "Maximum capacity in volt";
         }
       }
       container power-usage-psm-detail2 {
         leaf capacity-used {
           type uint32;
           description
             "Capacity used percentage";
         }
         leaf conversion-efficiency {
           type uint32;
           description
             "Conversion efficiency";
         }
       }
     }
     container power-usage-fru-item {
       leaf name {
         type string;
         description
           "Name of this component";
       }
       leaf dc-power {
         type uint32;
       }
       container sub-components {
         list sub-component {
           leaf comp-name {
             type string;
           }
           leaf comp-power {
             type uint32;
           }
         }
       }
     }
     leaf percent-capacity-allocated {
       type uint32;
       description
         "Percentage of maximum capacity allocated";
     }
     leaf power-mode {
       type string;
       description
         "Power mode";
     }
     container power-usage-system3 {
       leaf capacity-max {
         type uint32;
         description
           "Maximum capacity in volt";
       }
       leaf capacity-allocated {
         type uint32;
         description
           "Allocated capacity in volt";
       }
       leaf percent-capacity-allocated {
         type uint32;
         description
           "Percentage of maximum capacity allocated";
       }
       leaf capacity-remaining {
         type uint32;
         description
           "Remaining capacity in volt";
       }
       leaf capacity-actual-usage {
         type uint32;
         description
           "Actual usage in volt";
       }
     }
     container power-usage-voltage-total1 {
       leaf dc-power {
         type uint32;
       }
     }
     container sub-components {
     }
     container power-usage-component {
       leaf name {
         type string;
         description
           "Name of this component";
       }
       leaf dc-power {
         type uint32;
       }
     }
     container power-usage-max-fru-item {
       leaf name {
         type string;
         description
           "Name of this component";
       }
       leaf dc-power {
         type uint32;
       }
       leaf max-power {
         type uint32;
       }
     }
   }
   grouping fru-power-on-sequence-block {
     leaf sequence {
       type string;
     }
   }
   grouping alarm-information-block {
     container alarm-summary {
       description
         "Number of alarms currently active";
       leaf active-alarm-count {
         type int32;
         description
           "Number of active alarms";
       }
       leaf no-active-alarms {
         type empty;
         description
           "No active alarms";
       }
       leaf active-fpc-slot {
         type int32;
         description
           "FPC slot with active alarms";
       }
       leaf no-active-fpc-slot {
         type int32;
         description
           "FPC slot with non active alarms";
       }
     }
     list alarm-detail {
       description
         "Detailed information about an active alarm";
       leaf alarm-time {
         type string;
         description
           "Time of the alarm";
       }
       leaf alarm-class {
         type string;
         description
           "Class of the alarm";
       }
       leaf alarm-description {
         type string;
         description
           "Description of the alarm";
       }
       leaf alarm-short-description {
         type string;
         description
           "Short description of the alarm";
       }
       leaf alarm-type {
         type string;
         description
           "Type (class) of the alarm";
       }
     }
   }
   grouping chassis-beacon-information-block {
     container chassis-beacon-item {
       leaf beacon-name {
         type string;
       }
       leaf beacon-state {
         type string;
       }
     }
   }
   grouping get-chassis-interoperability-block {
     container chassis-interoperability-information {
       leaf name {
         type string;
         description
           "Name of this component";
       }
     }
   }
   grouping network-services-block {
     container network-services-information {
       leaf name {
         type string;
         description
           "Name of this component";
       }
     }
   }
   grouping ambient-temperature-block {
     container ambient-temperature-information {
       leaf name {
         type string;
         description
           "Name of this component";
       }
     }
   }
   grouping satellite-device-list-block {
     list satellite-device {
       key "slot";
       leaf slot {
         type int32;
       }
       leaf description {
         type string;
         description
           "Description of this component";
       }
       leaf ip-address {
         type jt:ipaddr;
       }
       leaf target-mode {
         type string;
       }
       leaf mac-address-base {
         type jt:mac-addr;
       }
       leaf mac-address-count {
         type int32;
       }
       leaf-list cascade-port {
         type string;
       }
     }
   }
   grouping clock-synchronization-block {
     leaf clock-status {
       type string;
       description
         "Current clock status";
     }
     leaf clock-lock-information {
       type string;
       description
         "Clock locked information";
     }
     leaf clock-ineligible-reason {
       type string;
       description
         "Clock ineligiblity reason";
     }
     leaf snmp-trap-status {
       type string;
       description
         "SNMP trap status";
     }
     leaf clock-synchronization-one-pps-status-string {
       type string;
       description
         "One PPS status";
     }
     leaf interface-synce-capab-mismatch-warning-msg {
       type string;
       description
         "SyncE Capability Mismatch Warning";
     }
     list clock-synchronization-port {
       description
         "Clock synchronization port status";
       leaf clock-synchronization-port-name {
         type string;
         description
           "Port name";
       }
       leaf clock-synchronization-port-rx-status {
         type string;
         description
           "Port input status";
       }
       leaf clock-synchronization-port-rx-message {
         type string;
         description
           "Port message received";
       }
       leaf clock-synchronization-port-current-tod {
         type string;
         description
           "Current time-of-day date and time";
       }
       leaf clock-synchronization-port-last-tod-update {
         type string;
         description
           "Time of the last time-of-day update";
       }
       leaf clock-synchronization-port-gps-status {
         type string;
         description
           "Port GPS receiver status";
       }
       leaf clock-synchronization-port-utc-offset {
         type uint32;
         description
           "Port TOD received UTC offset";
       }
       leaf clock-synchronization-port-utc-pending {
         type string;
         description
           "Port TOD UTC pending status";
       }
     }
     list clock-synchronization-interface {
       description
         "Clock synchronization interface status";
       leaf clock-synchronization-interface-name {
         type string;
         description
           "Interface name";
       }
       leaf clock-synchronization-interface-signal-type {
         type string;
         description
           "Interface signal type";
       }
       leaf clock-synchronization-interface-rx-status {
         type string;
         description
           "Interface rx status";
       }
       leaf clock-synchronization-interface-tx-status {
         type string;
         description
           "Interface tx status";
       }
       leaf clock-synchronization-interface-led-status {
         type string;
         description
           "Interface LED status";
       }
     }
     list clock-synchronization-output {
       description
         "Clock synchronization output status";
       leaf clock-synchronization-output-name {
         type string;
         description
           "Output interface name";
       }
       leaf clock-synchronization-output-tx-status {
         type string;
         description
           "Output interface transmit status";
       }
       leaf clock-synchronization-output-minimum-ql {
         type string;
         description
           "Output interface minimum quality level";
       }
       leaf clock-synchronization-output-tx-ql {
         type string;
         description
           "Output interface transmit quality level";
       }
       leaf clock-synchronization-output-holdover-mode {
         type string;
         description
           "Output interface holdover mode";
       }
       leaf clock-synchronization-output-wander-filter {
         type string;
         description
           "Output interface wander filter";
       }
       leaf clock-synchronization-output-source-mode {
         type string;
         description
           "Output interface source mode (line | chassis)";
       }
       leaf clock-synchronization-output-source-tx-dnu {
         type string;
         description
           "Output interface source Tx DNU (enabled/disabled)";
       }
       leaf clock-synchronization-output-holdover-data {
         type string;
         description
           "Output interface holdover data status";
       }
       leaf clock-synchronization-output-current-state {
         type string;
         description
           "Output interface current state";
       }
       leaf clock-synchronization-output-state-for-time {
         type string;
         description
           "Output interface state for time";
       }
       leaf clock-synchronization-output-state-since-date {
         type string;
         description
           "Output interface state since date";
       }
     }
     list clock-synchronization-source {
       description
         "Synchronous Ethernet source interface details:";
       leaf source-interface-name {
         type string;
         description
           "Possible source interface for syncE";
       }
       leaf source-priority {
         type string;
         description
           "Priority of clock source";
       }
       leaf source-interface-status {
         type string;
         description
           "Current status of interface (pri/sec)";
       }
       leaf source-quality-level {
         type string;
         description
           "Configured quality level of clock source";
       }
       leaf synce-bundle-name {
         type string;
         description
           "Synchronous ethernet bundle name";
       }
       leaf source-interface-index {
         type int32;
         description
           "Source interface index";
       }
       leaf clock-state {
         type string;
         description
           "Current state of clock";
       }
       leaf esmc-quality-level {
         type string;
         description
           "ESMC quality level of clock source";
       }
       leaf source-clock-type {
         type string;
         description
           "Clock is type ifd/ifl/extern";
       }
       leaf source-clock-event {
         type string;
         description
           "Clock's last event";
       }
       leaf interface-configuration-flags {
         type string;
         description
           "Current configuration state of the interface";
       }
       leaf interface-wait-to-restore {
         type uint32;
         description
           "Interface configured wait to restore time";
       }
       leaf interface-hold-off {
         type uint32;
         description
           "Interface configured hold-off time";
       }
       leaf interface-flags {
         type string;
         description
           "Current kernel state of the interface";
       }
       leaf clock-failure-reason {
         type string;
         description
           "Clock failure reason";
       }
       leaf interface-ineligible-reason {
         type string;
         description
           "Reason for source ineligiblity";
       }
       leaf interface-hold-interval-expiry {
         type uint32;
         description
           "Hold interval expiry time";
       }
     }
   }
   grouping clksyncd-in-memory-debug-information-summary-block {
     leaf clksyncd-mem-log-max-size {
       type uint32;
       description
         "Max mem logs can store in memory";
     }
     leaf clksyncd-criti-log-size {
       type uint32;
       description
         "Critical messages size";
     }
     leaf clksyncd-pri-log-size {
       type uint32;
       description
         "Priority trace messages";
     }
     leaf clksyncd-criti-info-log-size {
       type uint32;
       description
         "Critical info log size";
     }
     leaf clksyncd-criti-trace-log-size {
       type uint32;
       description
         "Critical trace log size";
     }
     leaf clksyncd-dump-on-wrap {
       type string;
       description
         "Memory logs dump on wrap";
     }
     leaf clksyncd-no-of-buffer-wraps {
       type uint32;
       description
         "Memory logs buffer wraps";
     }
     leaf clksyncd-memory-logs-enabled {
       type string;
       description
         "Memory logs enabled";
     }
     leaf clksyncd-memory-logs-dump-file-name {
       type string;
       description
         "Memory logs dump file-name";
     }
   }
   grouping clksyncd-in-memory-debug-information-trace-block {
     leaf clksyncd-trace {
       type string;
       description
         "Print in-memory-buffer traces";
     }
     leaf clksyncd-critical-log {
       type string;
       description
         "Critical log header";
     }
     leaf clksyncd-priority-log {
       type string;
       description
         "Priority log header";
     }
   }
   grouping craft-information-block {
     leaf-list output {
       type string;
       description
         "Formatted ASCII output displayed by the CLI";
     }
     container front-panel {
       description
         "Information from the craft interface";
       container display-panel {
         description
           "Text currently appearing on the craft interface display";
         leaf-list display-line {
           type string;
           description
             "Single line of text currently appearing on the craft interface
             display";
         }
       }
       container re-panel {
         description
           "State of status LEDs on the craft interface for one or more 
           Routing Engines. The front panel of each Routing Engine has the 
           same LEDs.";
         list re {
           key "slot";
           description
             "State of status LEDs on the craft interface for a Routing 
             Engine. The front panel of the Routing Engine has the same 
             LEDs.";
           leaf slot {
             type int32;
           }
           leaf ok-led {
             type empty;
             description
               "OK LED is lit";
           }
           leaf fail-led {
             type empty;
             description
               "Fail LED is lit";
           }
           leaf master-led {
             type empty;
             description
               "Master LED is lit";
           }
         }
       }
       container alarm-indicators {
         description
           "Information about alarms from the craft interface";
         leaf red-led {
           type empty;
           description
             "Red LED is lit";
         }
         leaf yellow-led {
           type empty;
           description
             "Yellow LED is lit";
         }
         leaf major-alarm-relay {
           type empty;
           description
             "Major (red) alarm relay is active";
         }
         leaf minor-alarm-relay {
           type empty;
           description
             "Minor (yellow) alarm relay is active";
         }
       }
       container fpc-panel {
         description
           "State of status LEDs on the craft interface for Flexible PIC 
           Concentrators";
         list fpccraft {
           key "slot";
           description
             "State of status LEDs on the craft interface for Flexible 
             PICConcentrators.";
           leaf slot {
             type int32;
           }
           leaf red-led {
             type empty;
             description
               "Red LED is lit";
           }
           leaf green-led {
             type empty;
             description
               "Green LED is lit";
           }
         }
       }
       container sib-panel {
         description
           "State of the status LEDs on the faceplate of one or more Switch 
           Interface Boards. Some of the LEDs also appear on the craft 
           interface.";
         container sib {
           leaf ok-led {
             type empty;
             description
               "OK LED is lit";
           }
           leaf fail-led {
             type empty;
             description
               "Fail LED is lit";
           }
           leaf active-led {
             type empty;
             description
               "Active LED is lit";
           }
         }
       }
       container ccg-panel {
         description
           "State of the status LEDs on the faceplate of one or more SONET 
           ClockGenerators";
         container ccg {
           description
             "State of the CCG status LEDs on the craft interface";
           leaf slot {
             type int32;
           }
           leaf ok-led {
             type empty;
             description
               "OK LED is lit";
           }
           leaf fail-led {
             type empty;
             description
               "Fail LED is lit";
           }
           leaf master-led {
             type empty;
             description
               "Master LED is lit";
           }
         }
       }
       container cb-panel {
         description
           "State of status LEDs on one or more Control Boards";
         list cb {
           key "slot";
           description
             "State of status LEDs on a Control Board";
           leaf slot {
             type int32;
           }
           leaf amber-led {
             type empty;
             description
               "Amber LED is lit";
           }
           leaf green-led {
             type empty;
             description
               "Green LED is lit";
           }
           leaf blue-led {
             type empty;
             description
               "Blue LED is lit";
           }
         }
       }
       container fan-tray-panel {
         description
           "State of status LEDs on the craft interface for Fan Trays";
         container fan-tray {
           description
             "State of the status LEDs on the craft interface for a fan tray";
           leaf slot {
             type int32;
           }
           leaf red-led {
             type empty;
             description
               "Red LED is lit";
           }
           leaf green-led {
             type empty;
             description
               "Green LED is lit";
           }
         }
       }
       container power-supply-panel {
         description
           "State of the status LEDs on the faceplate of one or more power 
           supplies";
         list power-supply {
           description
             "State of the status LEDs on the faceplate of a power supply";
           leaf slot {
             type int32;
           }
           leaf amber-led {
             type empty;
             description
               "Amber LED is lit";
           }
           leaf green-led {
             type empty;
             description
               "Green LED is lit";
           }
           leaf blue-led {
             type empty;
             description
               "Blue LED is lit";
           }
         }
         container pdu {
           description
             "State of the PDU status LEDs on the craft interface";
           leaf slot {
             type int32;
           }
           leaf red-led {
             type empty;
             description
               "Red LED is lit";
           }
           leaf green-led {
             type empty;
             description
               "Green LED is lit";
           }
           container psm {
             description
               "State of the PSM status LEDs on the craft interface";
             leaf slot {
               type int32;
             }
             leaf red-led {
               type empty;
               description
                 "Red LED is lit";
             }
             leaf green-led {
               type empty;
               description
                 "Green LED is lit";
             }
           }
         }
       }
     }
     container recb-panel {
       description
         "Information about LEDs from the craft interface";
       container ha-led {
         description
           "State of the HA LED on the craft interface";
         leaf red-led {
           type empty;
           description
             "Red LED is lit";
         }
         leaf yellow-led {
           type empty;
           description
             "Yellow LED is lit";
         }
         leaf amber-led {
           type empty;
           description
             "Amber LED is lit";
         }
       }
       container rps-led {
         description
           "State of the RPS LED on the craft interface";
         leaf red-led {
           type empty;
           description
             "Red LED is lit";
         }
         leaf green-led {
           type empty;
           description
             "Green LED is lit";
         }
         leaf led-off {
           type empty;
           description
             "LED is off";
         }
       }
       container mpim1-led {
         description
           "State of the MPIM1 LED on the craft interface";
         leaf green-led {
           type empty;
           description
             "Green LED is lit";
         }
         leaf led-off {
           type empty;
           description
             "LED is off";
         }
       }
       container mpim2-led {
         description
           "State of the MPIM2 LED on the craft interface";
         leaf green-led {
           type empty;
           description
             "Green LED is lit";
         }
         leaf led-off {
           type empty;
           description
             "LED is off";
         }
       }
       container storage-led {
         description
           "State of the external storage LED on the craft interface";
         leaf green-led {
           type empty;
           description
             "Green LED is lit";
         }
         leaf led-off {
           type empty;
           description
             "LED is off";
         }
       }
       container sfb-led {
         description
           "State of the SFB LED on the craft interface";
         leaf red-led {
           type empty;
           description
             "Red LED is lit";
         }
         leaf yellow-led {
           type empty;
           description
             "Yellow LED is lit";
         }
         leaf amber-led {
           type empty;
           description
             "Amber LED is lit";
         }
         leaf blink-led {
           type empty;
           description
             "LED is blinking";
         }
       }
       container cfm-ok-fail-led {
         description
           "State of the CFM Ok/Fail LED on the craft interface";
         leaf red-led {
           type empty;
           description
             "Red LED is lit";
         }
         leaf yellow-led {
           type empty;
           description
             "Yellow LED is lit";
         }
         leaf amber-led {
           type empty;
           description
             "Amber LED is lit";
         }
       }
       container cfm-service-led {
         description
           "State of the CFM Service LED on the craft interface";
         leaf red-led {
           type empty;
           description
             "Red LED is lit";
         }
         leaf yellow-led {
           type empty;
           description
             "Yellow LED is lit";
         }
         leaf amber-led {
           type empty;
           description
             "Amber LED is lit";
         }
       }
       container sysio-status-led {
         description
           "State of the SYSIO Status LED on the craft interface";
         leaf red-led {
           type empty;
           description
             "Red LED is lit";
         }
         leaf yellow-led {
           type empty;
           description
             "Yellow LED is lit";
         }
         leaf amber-led {
           type empty;
           description
             "Amber LED is lit";
         }
         leaf blink-led {
           type empty;
           description
             "LED is blinking";
         }
       }
     }
     container mcs-panel {
       description
         "State of the status LEDs on the faceplate of one or more 
         Miscellaneous Control Subsystems";
       container mcs {
         description
           "State of the status LEDs on the faceplate of a Miscellaneous 
           Control Subsystem";
         leaf slot {
           type int32;
         }
         leaf amber-led {
           type empty;
           description
             "Amber LED is lit";
         }
         leaf green-led {
           type empty;
           description
             "Green LED is lit";
         }
         leaf blue-led {
           type empty;
           description
             "Blue LED is lit";
         }
       }
     }
     container sfm-panel {
       description
         "State of the status LEDs on the faceplate of one or more Switching
         and Forwarding Modules";
       container sfm {
         description
           "State of the status LEDs on the faceplate of a Switching 
           andForwarding Module";
         leaf slot {
           type int32;
         }
         leaf amber-led {
           type empty;
           description
             "Amber LED is lit";
         }
         leaf green-led {
           type empty;
           description
             "Green LED is lit";
         }
         leaf blue-led {
           type empty;
           description
             "Blue LED is lit";
         }
       }
     }
     container pcg-panel {
       description
         "State of the status LEDs on the faceplate of one or more Packet 
         Forwarding Engine Clock Generators";
       container pcg {
         description
           "State of the status LEDs on the faceplate of a Packet Forwarding
           Engine Clock Generator";
         leaf slot {
           type int32;
         }
         leaf amber-led {
           type empty;
           description
             "Amber LED is lit";
         }
         leaf green-led {
           type empty;
           description
             "Green LED is lit";
         }
         leaf blue-led {
           type empty;
           description
             "Blue LED is lit";
         }
       }
     }
     container cb-panel {
       description
         "State of status LEDs on one or more Control Boards";
       list cb {
         key "slot";
         description
           "State of status LEDs on a Control Board";
         leaf slot {
           type int32;
         }
         leaf amber-led {
           type empty;
           description
             "Amber LED is lit";
         }
         leaf green-led {
           type empty;
           description
             "Green LED is lit";
         }
         leaf blue-led {
           type empty;
           description
             "Blue LED is lit";
         }
       }
     }
     container sib-panel {
       description
         "State of the status LEDs on the faceplate of one or more Switch 
         Interface Boards. Some of the LEDs also appear on the craft 
         interface.";
       container sib {
         leaf ok-led {
           type empty;
           description
             "OK LED is lit";
         }
         leaf fail-led {
           type empty;
           description
             "Fail LED is lit";
         }
         leaf active-led {
           type empty;
           description
             "Active LED is lit";
         }
       }
     }
     container scg-panel {
       description
         "State of the status LEDs on the faceplate of one or more SONET 
         ClockGenerators";
       container scg {
         description
           "State of the status LEDs on the faceplate of a SONET Clock 
           Generator";
         leaf slot {
           type int32;
         }
         leaf amber-led {
           type empty;
           description
             "Amber LED is lit";
         }
         leaf green-led {
           type empty;
           description
             "Green LED is lit";
         }
         leaf blue-led {
           type empty;
           description
             "Blue LED is lit";
         }
       }
     }
     container feb-panel {
       description
         "State of the status LEDs on the faceplate of one or more 
         Forwarding Engine Boards";
       container feb {
         description
           "State of the status LEDs on the faceplate of a Forwarding Engine
           Board";
         leaf slot {
           type int32;
         }
         leaf ok-led {
           type empty;
           description
             "OK LED is lit";
         }
         leaf fail-led {
           type empty;
           description
             "Fail LED is lit";
         }
         leaf active-led {
           type empty;
           description
             "Active LED is lit";
         }
       }
     }
     container power-supply-panel {
       description
         "State of the status LEDs on the faceplate of one or more power 
         supplies";
       list power-supply {
         description
           "State of the status LEDs on the faceplate of a power supply";
         leaf slot {
           type int32;
         }
         leaf amber-led {
           type empty;
           description
             "Amber LED is lit";
         }
         leaf green-led {
           type empty;
           description
             "Green LED is lit";
         }
         leaf blue-led {
           type empty;
           description
             "Blue LED is lit";
         }
       }
       container pdu {
         description
           "State of the PDU status LEDs on the craft interface";
         leaf slot {
           type int32;
         }
         leaf red-led {
           type empty;
           description
             "Red LED is lit";
         }
         leaf green-led {
           type empty;
           description
             "Green LED is lit";
         }
         container psm {
           description
             "State of the PSM status LEDs on the craft interface";
           leaf slot {
             type int32;
           }
           leaf red-led {
             type empty;
             description
               "Red LED is lit";
           }
           leaf green-led {
             type empty;
             description
               "Green LED is lit";
           }
         }
       }
     }
     container fan-tray-panel {
       description
         "State of status LEDs on the craft interface for Fan Trays";
       container fan-tray {
         description
           "State of the status LEDs on the craft interface for a fan tray";
         leaf slot {
           type int32;
         }
         leaf red-led {
           type empty;
           description
             "Red LED is lit";
         }
         leaf green-led {
           type empty;
           description
             "Green LED is lit";
         }
       }
     }
   }
   grouping ethernet-switch-information-block {
     leaf summary {
       type string;
     }
     list link-info {
       leaf admin-status {
         type string;
       }
       leaf interface-name {
         type string;
       }
       leaf port-number {
         type int32;
         description
           "Port number on the PIC";
       }
       leaf connected-to {
         type string;
       }
       leaf speed {
         type string;
       }
       leaf duplex {
         type string;
       }
       leaf autonegotiate {
         type string;
       }
       leaf flow-control-tx {
         type string;
       }
       leaf flow-control-rx {
         type string;
       }
       leaf-list error-message {
         type string;
       }
     }
   }
   grouping ethernet-switch-statistics-information-block {
     leaf summary {
       type string;
     }
     list link-up-info {
       leaf ge-summary {
         type string;
       }
       leaf gt-64 {
         type uint64;
       }
       leaf gt-127 {
         type uint64;
       }
       leaf gt-255 {
         type uint64;
       }
       leaf gt-511 {
         type uint64;
       }
       leaf gt-1023 {
         type uint64;
       }
       leaf gt-1518 {
         type uint64;
       }
       leaf gt-2047 {
         type uint64;
       }
       leaf gt-4095 {
         type uint64;
       }
       leaf gt-9216 {
         type uint64;
       }
       leaf gt-mgv {
         type uint64;
       }
       leaf gt-pkt {
         type uint64;
       }
       leaf gt-mca {
         type uint64;
       }
       leaf gt-bca {
         type uint64;
       }
       leaf gt-scl {
         type uint64;
       }
       leaf gt-mcl {
         type uint64;
       }
       leaf gt-lcl {
         type uint64;
       }
       leaf gt-xcl {
         type uint64;
       }
       leaf gt-ncl {
         type uint64;
       }
       leaf gt-xpf {
         type uint64;
       }
       leaf gt-xcf {
         type uint64;
       }
       leaf gt-dfr {
         type uint64;
       }
       leaf gt-edf {
         type uint64;
       }
       leaf gt-ovr {
         type uint64;
       }
       leaf gt-jbr {
         type uint64;
       }
       leaf gt-fcs {
         type uint64;
       }
       leaf gt-frg {
         type uint64;
       }
       leaf gt-byt {
         type uint64;
       }
       leaf gr-64 {
         type uint64;
       }
       leaf gr-127 {
         type uint64;
       }
       leaf gr-255 {
         type uint64;
       }
       leaf gr-511 {
         type uint64;
       }
       leaf gr-1023 {
         type uint64;
       }
       leaf gr-1518 {
         type uint64;
       }
       leaf gr-2047 {
         type uint64;
       }
       leaf gr-4095 {
         type uint64;
       }
       leaf gr-9216 {
         type uint64;
       }
       leaf gr-pkt {
         type uint64;
       }
       leaf gr-mca {
         type uint64;
       }
       leaf gr-bca {
         type uint64;
       }
       leaf gr-fcs {
         type uint64;
       }
       leaf gr-aln {
         type uint64;
       }
       leaf gr-frg {
         type uint64;
       }
       leaf gr-cde {
         type uint64;
       }
       leaf gr-xuo {
         type uint64;
       }
       leaf gr-flr {
         type uint64;
       }
       leaf gr-fcr {
         type uint64;
       }
       leaf gr-und {
         type uint64;
       }
       leaf gr-ovr {
         type uint64;
       }
       leaf gr-jbr {
         type uint64;
       }
       leaf gr-mgv {
         type uint64;
       }
       leaf gr-mtue {
         type uint64;
       }
       leaf gr-xcf {
         type uint64;
       }
       leaf gr-xpf {
         type uint64;
       }
       leaf gr-byt {
         type uint64;
       }
       leaf xe-summary {
         type string;
       }
       leaf it-64 {
         type uint64;
       }
       leaf it-127 {
         type uint64;
       }
       leaf it-255 {
         type uint64;
       }
       leaf it-511 {
         type uint64;
       }
       leaf it-1023 {
         type uint64;
       }
       leaf it-1518 {
         type uint64;
       }
       leaf it-2047 {
         type uint64;
       }
       leaf it-4095 {
         type uint64;
       }
       leaf it-9216 {
         type uint64;
       }
       leaf it-16383 {
         type uint64;
       }
       leaf it-pkt {
         type uint64;
       }
       leaf it-mca {
         type uint64;
       }
       leaf it-bca {
         type uint64;
       }
       leaf it-xpf {
         type uint64;
       }
       leaf it-ovr {
         type uint64;
       }
       leaf it-fcs {
         type uint64;
       }
       leaf it-frg {
         type uint64;
       }
       leaf it-byt {
         type uint64;
       }
       leaf ir-64 {
         type uint64;
       }
       leaf ir-127 {
         type uint64;
       }
       leaf ir-255 {
         type uint64;
       }
       leaf ir-511 {
         type uint64;
       }
       leaf ir-1023 {
         type uint64;
       }
       leaf ir-1518 {
         type uint64;
       }
       leaf ir-2047 {
         type uint64;
       }
       leaf ir-4095 {
         type uint64;
       }
       leaf ir-9216 {
         type uint64;
       }
       leaf ir-16383 {
         type uint64;
       }
       leaf ir-pkt {
         type uint64;
       }
       leaf ir-mca {
         type uint64;
       }
       leaf ir-bca {
         type uint64;
       }
       leaf ir-fcs {
         type uint64;
       }
       leaf ir-frg {
         type uint64;
       }
       leaf ir-xuo {
         type uint64;
       }
       leaf ir-flr {
         type uint64;
       }
       leaf ir-und {
         type uint64;
       }
       leaf ir-ovr {
         type uint64;
       }
       leaf ir-jbr {
         type uint64;
       }
       leaf ir-xcf {
         type uint64;
       }
       leaf ir-xpf {
         type uint64;
       }
       leaf ir-byt {
         type uint64;
       }
       leaf-list error-message {
         type string;
       }
     }
   }
   grouping ethernet-switch-error-information-block {
     leaf summary {
       type string;
     }
     leaf mlt3 {
       type int32;
     }
     leaf lock {
       type int32;
     }
     leaf xmit {
       type int32;
     }
     leaf esd {
       type int32;
     }
     leaf false-carrier {
       type int32;
     }
     leaf disconnects {
       type int32;
     }
     leaf fx-mode {
       type int32;
     }
     leaf-list error-message {
       type string;
     }
   }
   grouping feb-redundancy-information-block {
     list feb-redundancy-group-information {
       description
         "FEB redundancy information for a redundancy group";
       leaf feb-redundancy-group-name {
         type string;
         description
           "FEB redundancy group name";
       }
       leaf feb-redundancy-group-description {
         type string;
         description
           "FEB redundancy group description";
       }
       leaf feb-redundancy-autofailover {
         type string;
         description
           "FEB redundancy autofailover information";
       }
       leaf feb-redundancy-switch-reason {
         type string;
         description
           "FEB redundancy reason for switchover";
       }
       container feb-redundancy-group-information-item {
         description
           "FEB redundancy information for a FEB";
         leaf feb-slot {
           type int32;
           description
             "FEB slot";
         }
         leaf feb-state {
           type string;
           description
             "FEB state";
         }
         leaf redundancy-priority {
           type string;
           description
             "FEB redundancy priority";
         }
         leaf connected-fpcs {
           type string;
           description
             "List of FPCs connected to the FEB in printable form";
         }
         leaf redundancy-state {
           type string;
           description
             "Redundancy state";
         }
         leaf redundancy-state-description {
           type string;
           description
             "Description of redundancy state";
         }
       }
     }
   }
   grouping feb-redundancy-error-information-block {
     list feb-redundancy-group-errors {
       description
         "FEB redundancy error information for a FEB group";
       leaf feb-redundancy-group-name {
         type string;
         description
           "FEB redundancy group name";
       }
       leaf feb-redundancy-group-description {
         type string;
         description
           "FEB redundancy group description";
       }
       container feb-redundancy-group-feb-errors {
         description
           "FEB redundancy error information for a FEB";
         leaf feb-slot {
           type int32;
           description
             "FEB slot";
         }
         leaf feb-state {
           type string;
           description
             "FEB state";
         }
         leaf feb-harderror-state {
           type string;
           description
             "FEB hard error state";
         }
         list feb-redundancy-group-feb-fpc-errors {
           description
             "FEB redundancy error information for an FPC";
           leaf fpc-slot {
             type int32;
             description
               "FPC slot";
           }
           leaf fpc-link-status {
             type string;
             description
               "FPC link status";
           }
         }
         list feb-redundancy-group-feb-fabric-plane-errors {
           description
             "FEB redundancy error information for a fabric plane";
           leaf fabric-plane-number {
             type int32;
             description
               "Fabric plane number";
           }
           leaf fabric-plane-status {
             type int32;
             description
               "Fabric plane status";
           }
         }
       }
     }
   }
   grouping fpc-feb-connectivity-block {
     list fpc-feb-connectivity-item {
       description
         "FEB connectivity information for an FPC";
       leaf fpc-slot {
         type int32;
         description
           "FPC slot";
       }
       leaf fpc-type {
         type string;
         description
           "FPC type";
       }
       leaf fpc-state {
         type string;
         description
           "FPC state";
       }
       leaf feb-slot {
         type int32;
         description
           "FEB slot";
       }
       leaf no-feb-slot {
         type empty;
       }
       leaf feb-state {
         type string;
         description
           "FEB state";
       }
       leaf fpc-link-status {
         type string;
         description
           "FPC link status";
       }
     }
   }
   grouping ioc-npc-connectivity-block {
     list ioc-npc-connectivity-item {
       description
         "NPC connectivity information for an IOC";
       leaf ioc-slot {
         type int32;
       }
       leaf ioc-type {
         type string;
         description
           "IOC type";
       }
       leaf ioc-state {
         type string;
         description
           "IOC state";
       }
       leaf npc-slot {
         type int32;
       }
       leaf no-npc-slot {
         type empty;
       }
       leaf npc-state {
         type string;
       }
       leaf fpc-link-status {
         type string;
         description
           "FPC link status";
       }
     }
   }
   grouping chassis-zones-information-block {
     leaf name {
       type string;
       description
         "Name of this component";
     }
     leaf driving-fru-name {
       type string;
     }
     leaf temperature {
       type string;
       description
         "Temperature of the item";
     }
     leaf zone-status {
       type string;
     }
     leaf comment {
       type string;
     }
     leaf fan-missing-cnt {
       type uint32;
     }
     leaf fan-failed-cnt {
       type uint32;
     }
     leaf fan-dutycycle {
       type uint32;
     }
     leaf fru-name {
       type string;
     }
     leaf fru-temp-status {
       type string;
     }
     leaf fru-temperature {
       type string;
     }
     leaf cooling-fru-name {
       type string;
     }
     leaf fru-fan-status {
       type string;
     }
     leaf fru-comment {
       type string;
     }
     leaf fru-status {
       type string;
     }
   }
   grouping environment-information-block {
     list environment-item {
       key "name";
       leaf class {
         type string;
       }
       leaf name {
         type string;
         description
           "Name of this component";
       }
       leaf status {
         type string;
         description
           "Status of clock synchronization source";
       }
       leaf temperature {
         type string;
         description
           "Temperature of the item";
       }
       leaf comment {
         type string;
       }
       leaf humidity {
         type string;
       }
     }
   }
   grouping environment-component-information-block {
     list environment-component-item {
       key "name";
       description
         "Chassis environment component";
       leaf name {
         type string;
         description
           "Name of this component";
       }
       leaf state {
         type string;
         description
           "Status of the component";
       }
       leaf bus-revision {
         type int32;
         description
           "Bus revision";
       }
       leaf cmb-revision {
         type int32;
         description
           "CMB revision";
       }
       leaf fpga-revision {
         type int32;
         description
           "FPGA revision";
       }
       leaf ac-feed0-voltage {
         type string;
         description
           "AC feed0 voltage";
       }
       leaf ac-feed0-current {
         type string;
         description
           "AC feed0 current";
       }
       leaf ac-feed0-power {
         type string;
         description
           "AC feed0 power";
       }
       leaf ac-feed1-voltage {
         type string;
         description
           "AC feed1 voltage";
       }
       leaf ac-feed1-current {
         type string;
         description
           "AC feed1 current";
       }
       leaf ac-feed1-power {
         type string;
         description
           "AC feed1 power";
       }
       leaf reason {
         type string;
         description
           "Reason";
       }
       leaf frequency {
         type string;
         description
           "Frequency";
       }
       leaf slave-revision {
         type uint32;
         description
           "Slave revision";
       }
       leaf load {
         type string;
         description
           "Load";
       }
       leaf time-used {
         type string;
         description
           "Length of time this component has been used";
       }
       leaf check-input1-alarm {
         type string;
         description
           "Check input1 alarm";
       }
       leaf check-input2-alarm {
         type string;
         description
           "Check input2 alarm";
       }
       leaf ac-input_status {
         type string;
         description
           "AC input status";
       }
       container temperature-reading {
         leaf temperature-name {
           type string;
         }
         leaf temperature {
           type string;
           description
             "Temperature of the item";
         }
       }
       container fan-speed-reading {
         leaf fan-name {
           type string;
         }
         leaf fan-speed {
           type string;
           description
             "Fan speed in RPM";
         }
       }
       container fpga-revision-detail {
         description
           "FPGA revision in detail";
         leaf fpga-revision-name {
           type string;
         }
         leaf fpga-revision-value {
           type string;
         }
       }
       container revision {
         leaf revision-name {
           type string;
           description
             "Revision Name";
         }
         leaf revision-number {
           type uint32;
           description
             "Revision Number";
         }
       }
       container slave-registers-information {
         leaf slave-registers-title {
           type string;
           description
             "Title for the dump of slave registers";
         }
         container slave-registers {
           description
             "Slave register values";
           leaf slave-registers-name {
             type string;
           }
           leaf slave-registers-value {
             type string;
           }
           leaf slave-registers-desc {
             type string;
           }
         }
       }
       container fpga-registers {
         description
           "FPGA register values";
         leaf fpga-registers-type {
           type string;
         }
         leaf fpga-registers-name {
           type string;
         }
         leaf fpga-registers-value {
           type string;
         }
       }
       container power-information {
         leaf voltage-title {
           type string;
           description
             "Title for the display of voltage";
         }
         leaf max-power-consumption-ambient-temp {
           type int32;
         }
         leaf psm-hours-used {
           type uint32;
           description
             "Hours used for this component";
         }
         container power-title {
           leaf power-type {
             type string;
             description
               "Title for the display of power";
           }
           leaf power-state {
             type string;
             description
               "State of power";
           }
         }
         container voltage {
           leaf reference-voltage {
             type string;
             description
               "Voltage of the item in Volts";
           }
           leaf actual-voltage {
             type int32;
             description
               "Voltage of the item in mVlots";
           }
         }
         container current {
           leaf reference-curr {
             type string;
             description
               "Current of the item in Amps";
           }
           leaf actual-curr {
             type int32;
             description
               "Current of the item in mAmps";
           }
         }
         container voltage-current {
           leaf reference-volt-string {
             type string;
             description
               "Voltage of the item in Volts";
           }
           leaf actual-volt-in {
             type int32;
             description
               "Voltage in of the item in mVolts";
           }
           leaf actual-current-in {
             type int32;
             description
               "Current of the item in mAmps";
           }
         }
         container voltage-power {
           leaf reference-volt {
             type string;
             description
               "Voltage of the item in Volts";
           }
           leaf actual-volt {
             type int32;
             description
               "Voltage of the item in mVlots";
           }
           leaf actual-current {
             type int32;
             description
               "Current of the item in mAmps";
           }
           leaf actual-power {
             type int32;
             description
               "Power of the item in mWatts";
           }
         }
         list voltage-power-temperature-only {
           leaf voltage-string {
             type string;
             description
               "Name of the component";
           }
           leaf actual-temperature {
             type int32;
             description
               "Temperature of the item in degree (C)";
           }
         }
         container voltage-power-volt-only {
           leaf reference-volt-only {
             type string;
             description
               "Voltage of the item in Volts";
           }
           leaf actual-volt-only {
             type int32;
             description
               "Voltage of the item in mVlots";
           }
         }
       }
       container pcg-frequency {
         description
           "PCG Frequency";
         leaf pcg-frequency-setting {
           type string;
         }
         leaf pcg-frequency-measurement {
           type string;
         }
       }
       container dc-information {
         leaf dc-feed0-voltage {
           type string;
           description
             "DC feed0 voltage";
         }
         leaf dc-feed0-current {
           type string;
           description
             "DC feed0 current";
         }
         leaf dc-feed0-power {
           type string;
           description
             "DC feed0 power";
         }
         leaf dc-feed1-voltage {
           type string;
           description
             "DC feed1 voltage";
         }
         leaf dc-feed1-current {
           type string;
           description
             "DC feed1 current";
         }
         leaf dc-feed1-power {
           type string;
           description
             "DC feed1 power";
         }
         leaf dc-input {
           type string;
           description
             "DC input state";
         }
         leaf dc-output {
           type string;
           description
             "DC output state";
         }
         leaf ac-input {
           type string;
           description
             "AC input state";
         }
         leaf ac-output {
           type string;
           description
             "AC output state";
         }
         leaf dc-input-status {
           type string;
           description
             "DC input status";
         }
         leaf dc-input1 {
           type string;
           description
             "DC input1 state";
         }
         leaf dc-input2 {
           type string;
           description
             "DC input2 state";
         }
         leaf ac-input1 {
           type string;
           description
             "AC input1 state";
         }
         leaf ac-input2 {
           type string;
           description
             "AC input2 state";
         }
         container dc-detail {
           description
             "Detailed DC information";
           leaf dc-device {
             type string;
           }
           leaf dc-voltage {
             type uint32;
           }
           leaf dc-current {
             type uint32;
           }
           leaf dc-power {
             type uint32;
           }
           leaf dc-load {
             type uint32;
           }
           leaf str-dc-voltage {
             type string;
           }
           leaf str-dc-current {
             type string;
           }
           leaf str-dc-power {
             type string;
           }
           leaf str-dc-load {
             type string;
           }
           leaf str2-dc-voltage {
             type string;
           }
           leaf str2-dc-current {
             type string;
           }
           leaf str2-dc-power {
             type string;
           }
           leaf str2-dc-load {
             type string;
           }
           leaf str3-dc-voltage {
             type string;
           }
           leaf str3-dc-current {
             type string;
           }
           leaf max-power {
             type uint32;
           }
         }
         container dc-in-detail2 {
           description
             "Detailed DC input information";
           leaf dc-in-device2 {
             type string;
           }
           leaf dc-in-voltage-string {
             type string;
           }
           leaf dc-in-current-string {
             type string;
           }
           leaf dc-in-power-string {
             type string;
           }
           leaf dc-in-load-string {
             type string;
           }
         }
         container dc-detail2 {
           description
             "Detailed DC information";
           leaf dc-device2 {
             type string;
           }
           leaf dc-voltage-string {
             type string;
           }
           leaf dc-current-string {
             type string;
           }
           leaf dc-power-string {
             type string;
           }
           leaf dc-load-string {
             type string;
           }
         }
         leaf dc-inp0 {
           type string;
           description
             "DC input0 state";
         }
         leaf dc-inp1 {
           type string;
           description
             "DC input1 state";
         }
         leaf dc2-input-a0 {
           type string;
           description
             "DC2 input a0 state";
         }
         leaf dc2-input-b0 {
           type string;
           description
             "DC2 input b0 state";
         }
         leaf dc2-input-a1 {
           type string;
           description
             "DC2 input a1 state";
         }
         leaf dc2-input-b1 {
           type string;
           description
             "DC2 input b1 state";
         }
         leaf ac-inp0 {
           type string;
           description
             "AC input0 state";
         }
         leaf ac-inp1 {
           type string;
           description
             "AC input1 state";
         }
       }
       container pmbus-table {
         container pmbus-table-entry {
           description
             "Power Management Bus Device information";
           leaf pmbus-device-name {
             type string;
           }
           leaf pmbus-expected-voltage {
             type uint32;
           }
           leaf pmbus-actual-voltage {
             type uint32;
           }
           leaf pmbus-actual-current {
             type uint32;
           }
           leaf pmbus-calculated-power {
             type uint32;
           }
         }
       }
       container airflow-direction {
         leaf airflow {
           type string;
         }
         leaf direction {
           type string;
           description
             "Airflow direction";
         }
       }
       container input-voltage {
         leaf voltage-name {
           type string;
           description
             "Input voltage";
         }
         leaf voltage-value {
           type uint32;
         }
       }
       container output-detail {
         description
           "Detailed power output information";
         leaf output-voltage {
           type uint32;
         }
         leaf output-current {
           type uint32;
           description
             "Output Current in Ampere(A)";
         }
       }
       container pdu-information {
         leaf hours-used {
           type uint32;
           description
             "Hours used for this component";
         }
         leaf pdu-status {
           type string;
         }
         container efuse {
           description
             "PDU efuse information";
           leaf name {
             type string;
             description
               "Name of this component";
           }
           leaf state {
             type string;
             description
               "Status of the component";
           }
         }
         container pdu-firmware {
           description
             "PDU firmware information";
           leaf firmware-name {
             type string;
             description
               "Name of this component";
           }
           leaf firmware-version {
             type string;
             description
               "Firmware version string for this component";
           }
         }
         container pdu-component {
           description
             "PDU specific component information";
           leaf component-name {
             type string;
             description
               "PDU component name";
           }
           leaf component-state {
             type string;
             description
               "PDU component state";
           }
         }
       }
       container psm-information {
         leaf temperature {
           type string;
           description
             "Temperature of the item";
         }
         leaf hours-used {
           type uint32;
           description
             "Hours used for this component";
         }
         leaf firmware-version {
           type string;
           description
             "Firmware version string for this component";
         }
         container psm-status {
           leaf fans {
             type string;
             description
               "Fan status for this component";
           }
           leaf dc-input {
             type string;
             description
               "DC input state";
           }
           leaf dc-input1 {
             type string;
             description
               "DC input1 state";
           }
           leaf dc-input2 {
             type string;
             description
               "DC input2 state";
           }
           leaf ac-input {
             type string;
             description
               "AC input state";
           }
           leaf ac-input1 {
             type string;
             description
               "AC input1 state";
           }
           leaf ac-input2 {
             type string;
             description
               "AC input2 state";
           }
           leaf check-input1-alarm {
             type string;
             description
               "Check input1 alarm";
           }
           leaf check-input2-alarm {
             type string;
             description
               "Check input2 alarm";
           }
           leaf dc-output {
             type string;
             description
               "DC output state";
           }
           leaf ac-output {
             type string;
             description
               "AC output state";
           }
           leaf psm-health-check-status {
             type string;
             description
               "Show health check status of all PSMs";
           }
           leaf dc-inp0 {
             type string;
             description
               "DC input0 state";
           }
           leaf dc-inp1 {
             type string;
             description
               "DC input1 state";
           }
           leaf dc2-input-a0 {
             type string;
             description
               "DC2 input a0 state";
           }
           leaf dc2-input-b0 {
             type string;
             description
               "DC2 input b0 state";
           }
           leaf dc2-input-a1 {
             type string;
             description
               "DC2 input a1 state";
           }
           leaf dc2-input-b1 {
             type string;
             description
               "DC2 input b1 state";
           }
           leaf ac-inp0 {
             type string;
             description
               "AC input0 state";
           }
           leaf ac-inp1 {
             type string;
             description
               "AC input1 state";
           }
           leaf check-input-a0-alarm {
             type string;
             description
               "Check input a0 alarm";
           }
           leaf check-input-b0-alarm {
             type string;
             description
               "Check input b0 alarm";
           }
           leaf check-input-a1-alarm {
             type string;
             description
               "Check input a1 alarm";
           }
           leaf check-input-b1-alarm {
             type string;
             description
               "Check input b1 alarm";
           }
           list psm-input-status {
             leaf psm-input-feed-name {
               type string;
             }
             leaf psm-input-feed-status {
               type string;
             }
           }
           list psm-input-alarm {
             leaf input-feed-alarm-name {
               type string;
             }
             leaf input-feed-alarm-status {
               type string;
             }
           }
         }
         leaf fan-status {
           type string;
           description
             "Fan status for this component";
         }
         leaf firmware-primary-mcu {
           type string;
         }
         leaf firmware-secondary-mcu {
           type string;
         }
         leaf firmware-communication-mcu {
           type string;
         }
         leaf firmware-led-mcu {
           type string;
         }
         leaf firmware-version-psm {
           type string;
         }
         leaf hvdc-mode {
           type string;
           description
             "HVDC mode";
         }
         leaf temperature-name {
           type string;
         }
         container fan-speed-reading-psm {
           leaf fan1-speed {
             type string;
           }
           leaf fan2-speed {
             type string;
           }
         }
       }
       container pem-information {
         leaf fpc-slot {
           type int32;
           description
             "FPC slot";
         }
         leaf pem-slot {
           type uint32;
         }
         leaf pem-state {
           type string;
           description
             "State of power supply unit";
         }
         leaf pem-temperature {
           type uint32;
           description
             "Temperature in (C)";
         }
         leaf input-current {
           type uint32;
           description
             "Input Current in Ampere(A)";
         }
         leaf input-volt {
           type uint32;
           description
             "Input Volt in Volt(V)";
         }
         leaf input-power {
           type uint32;
           description
             "Input Power in Watt(W)";
         }
         leaf output-current {
           type uint32;
           description
             "Output Current in Ampere(A)";
         }
         leaf output-volt {
           type uint32;
           description
             "Output Volt in Volt(V)";
         }
         leaf output-power {
           type uint32;
           description
             "Output Power in Watt(W)";
         }
       }
       leaf ac-input-state {
         type string;
         description
           "Input type";
       }
       leaf dc-input-state {
         type string;
         description
           "Input type";
       }
       leaf ac-input {
         type string;
         description
           "Input type";
       }
       leaf check-input-a0-alarm {
         type string;
         description
           "Check input a0 alarm";
       }
       leaf check-input-b0-alarm {
         type string;
         description
           "Check input b0 alarm";
       }
       leaf check-input-a1-alarm {
         type string;
         description
           "Check input a1 alarm";
       }
       leaf check-input-b1-alarm {
         type string;
         description
           "Check input b1 alarm";
       }
       container feed-info {
         leaf feed-name {
           type string;
         }
         leaf feed-state {
           type string;
         }
       }
       container cowra-registers-information {
         leaf cowra-registers-title {
           type string;
           description
             "Title for the dump of cowra registers";
         }
         container cowra-registers {
           description
             "Cowra register values";
           leaf cowra-registers-name {
             type string;
           }
           leaf cowra-registers-value {
             type string;
           }
         }
       }
       list firmware {
         description
           "Firmware version";
         leaf firmware-name {
           type string;
           description
             "Name of this component";
         }
         leaf firmware-version {
           type string;
           description
             "Firmware version string for this component";
         }
         leaf firmware-version-psm {
           type string;
         }
         leaf firmware-primary-mcu {
           type string;
         }
         leaf firmware-secondary-mcu {
           type string;
         }
         leaf firmware-communication-mcu {
           type string;
         }
         leaf firmware-led-mcu {
           type string;
         }
       }
       container input-detail2 {
         leaf input-feed-name {
           type string;
           description
             "Input Feed Name";
         }
         leaf input-feed-volt {
           type string;
           description
             "Input Feed Voltage";
         }
         leaf input-feed-current {
           type string;
           description
             "Input Feed Current";
         }
         leaf input-feed-power {
           type string;
           description
             "Input Feed Power";
         }
       }
       container ac-pem-input-detail {
         leaf ac-pem-input-volt {
           type string;
           description
             "Input Voltage";
         }
         leaf ac-pem-input-current {
           type string;
           description
             "Input Current";
         }
         leaf ac-pem-input-power {
           type string;
           description
             "Input Power";
         }
       }
       container dc-pem-input-detail {
         leaf dc-pem-input-volt {
           type string;
           description
             "Input Voltage";
         }
         leaf dc-pem-input-current {
           type string;
           description
             "Input Current";
         }
         leaf dc-pem-input-power {
           type string;
           description
             "Input Power";
         }
       }
       container psm-health-check-detail {
         leaf health-check-status {
           type string;
         }
         leaf health-check-state-str {
           type string;
           description
             "Current Health Check State";
         }
         leaf health-check-last-result-str {
           type string;
           description
             "Result of Last Execution";
         }
         leaf health-check-last-exec-str {
           type string;
           description
             "Time of Last Health Check Test Execution";
         }
         leaf health-check-next-sched-run-str {
           type string;
           description
             "Time of Next Scheduled Health Check Test";
         }
       }
     }
   }
   grouping sfb-information-block {
     leaf use-cli-info {
       type string;
     }
     container sfb {
       leaf slot {
         type int32;
       }
       leaf state {
         type string;
         description
           "Status of the component";
       }
       leaf up-time {
         type string;
         description
           "Length of time this component has been operational";
       }
       leaf comment {
         type string;
       }
       leaf slot-type {
         type string;
       }
       leaf destination-error {
         type string;
         description
           "Destination error count";
       }
     }
   }
   grouping firmware-information-block {
     container chassis {
       description
         "Hardware inventory of this chassis";
       leaf name {
         type string;
         description
           "Name of this component";
       }
       leaf version {
         type string;
         description
           "Version of this component";
       }
       leaf part-number {
         type string;
         description
           "Part number of this component";
       }
       leaf serial-number {
         type string;
         description
           "Serial number of this component";
       }
       leaf description {
         type string;
         description
           "Description of this component";
       }
       leaf hardware-incomplete {
         type empty;
       }
       leaf model-number {
         type string;
         description
           "Model number of this component";
       }
       leaf clei-code {
         type string;
         description
           "Common Language Equipment Identifier code of this component";
       }
       container i2c-information {
         leaf jedec-code {
           type string;
         }
         leaf eeprom-version {
           type string;
         }
         leaf part-number {
           type string;
           description
             "Part number of this component";
         }
         leaf serial-number {
           type string;
           description
             "Serial number of this component";
         }
         leaf assembly-identifier {
           type string;
         }
         leaf assembly-version {
           type string;
         }
         leaf manufacture-date {
           type string;
           description
             "Date this component was manufactured";
         }
         leaf assembly-flags {
           type string;
         }
         leaf i2c-version {
           type string;
         }
         leaf clei-code {
           type string;
           description
             "Common Language Equipment Identifier code of this component";
         }
         leaf i2c-identifier {
           type string;
         }
         leaf model-number {
           type string;
           description
             "Model number of this component";
         }
         leaf board-information-record {
           type string;
           description
             "Hex dump of board information record";
         }
         leaf i2c-data {
           type string;
           description
             "Hex dump of I2C data";
         }
       }
       list chassis-module {
         key "name";
         leaf name {
           type string;
           description
             "Name of this component";
         }
         leaf version {
           type string;
           description
             "Version of this component";
         }
         leaf part-number {
           type string;
           description
             "Part number of this component";
         }
         leaf serial-number {
           type string;
           description
             "Serial number of this component";
         }
         leaf description {
           type string;
           description
             "Description of this component";
         }
         leaf ir-mode {
           type string;
           description
             "R/IR mode configured";
         }
         container i2c-information {
           leaf jedec-code {
             type string;
           }
           leaf eeprom-version {
             type string;
           }
           leaf part-number {
             type string;
             description
               "Part number of this component";
           }
           leaf serial-number {
             type string;
             description
               "Serial number of this component";
           }
           leaf assembly-identifier {
             type string;
           }
           leaf assembly-version {
             type string;
           }
           leaf manufacture-date {
             type string;
             description
               "Date this component was manufactured";
           }
           leaf assembly-flags {
             type string;
           }
           leaf i2c-version {
             type string;
           }
           leaf clei-code {
             type string;
             description
               "Common Language Equipment Identifier code of this component";
           }
           leaf i2c-identifier {
             type string;
           }
           leaf model-number {
             type string;
             description
               "Model number of this component";
           }
           leaf board-information-record {
             type string;
             description
               "Hex dump of board information record";
           }
           leaf i2c-data {
             type string;
             description
               "Hex dump of I2C data";
           }
         }
         list firmware {
           leaf firmware-version-psm {
             type string;
           }
           leaf firmware-primary-mcu {
             type string;
           }
           leaf firmware-secondary-mcu {
             type string;
           }
           leaf firmware-communication-mcu {
             type string;
           }
           leaf firmware-led-mcu {
             type string;
           }
           leaf type {
             type string;
             description
               "Type of this component";
           }
           leaf firmware-version {
             type string;
             description
               "Firmware version string for this component";
           }
         }
         list chassis-sub-module {
           key "name";
           leaf name {
             type string;
             description
               "Name of this component";
           }
           leaf version {
             type string;
             description
               "Version of this component";
           }
           leaf part-number {
             type string;
             description
               "Part number of this component";
           }
           leaf serial-number {
             type string;
             description
               "Serial number of this component";
           }
           leaf description {
             type string;
             description
               "Description of this component";
           }
           container i2c-information {
             leaf jedec-code {
               type string;
             }
             leaf eeprom-version {
               type string;
             }
             leaf part-number {
               type string;
               description
                 "Part number of this component";
             }
             leaf serial-number {
               type string;
               description
                 "Serial number of this component";
             }
             leaf assembly-identifier {
               type string;
             }
             leaf assembly-version {
               type string;
             }
             leaf manufacture-date {
               type string;
               description
                 "Date this component was manufactured";
             }
             leaf assembly-flags {
               type string;
             }
             leaf i2c-version {
               type string;
             }
             leaf clei-code {
               type string;
               description
                 "Common Language Equipment Identifier code of this 
                 component";
             }
             leaf i2c-identifier {
               type string;
             }
             leaf model-number {
               type string;
               description
                 "Model number of this component";
             }
             leaf board-information-record {
               type string;
               description
                 "Hex dump of board information record";
             }
             leaf i2c-data {
               type string;
               description
                 "Hex dump of I2C data";
             }
           }
           list firmware {
             leaf firmware-version-psm {
               type string;
             }
             leaf firmware-primary-mcu {
               type string;
             }
             leaf firmware-secondary-mcu {
               type string;
             }
             leaf firmware-communication-mcu {
               type string;
             }
             leaf firmware-led-mcu {
               type string;
             }
           }
           list chassis-sub-sub-module {
             key "name";
             leaf name {
               type string;
               description
                 "Name of this component";
             }
             leaf version {
               type string;
               description
                 "Version of this component";
             }
             leaf part-number {
               type string;
               description
                 "Part number of this component";
             }
             leaf serial-number {
               type string;
               description
                 "Serial number of this component";
             }
             leaf description {
               type string;
               description
                 "Description of this component";
             }
             leaf model-number {
               type string;
               description
                 "Model number of this component";
             }
             leaf clei-code {
               type string;
               description
                 "Common Language Equipment Identifier code of this 
                 component";
             }
             list chassis-sub-sub-sub-module {
               key "name";
               leaf name {
                 type string;
                 description
                   "Name of this component";
               }
               leaf version {
                 type string;
                 description
                   "Version of this component";
               }
               leaf part-number {
                 type string;
                 description
                   "Part number of this component";
               }
               leaf serial-number {
                 type string;
                 description
                   "Serial number of this component";
               }
               leaf description {
                 type string;
                 description
                   "Description of this component";
               }
               leaf model-number {
                 type string;
                 description
                   "Model number of this component";
               }
               leaf clei-code {
                 type string;
                 description
                   "Common Language Equipment Identifier code of this 
                   component";
               }
             }
             container i2c-information {
               leaf jedec-code {
                 type string;
               }
               leaf eeprom-version {
                 type string;
               }
               leaf part-number {
                 type string;
                 description
                   "Part number of this component";
               }
               leaf serial-number {
                 type string;
                 description
                   "Serial number of this component";
               }
               leaf assembly-identifier {
                 type string;
               }
               leaf assembly-version {
                 type string;
               }
               leaf manufacture-date {
                 type string;
                 description
                   "Date this component was manufactured";
               }
               leaf assembly-flags {
                 type string;
               }
               leaf i2c-version {
                 type string;
               }
               leaf clei-code {
                 type string;
                 description
                   "Common Language Equipment Identifier code of this 
                   component";
               }
               leaf i2c-identifier {
                 type string;
               }
               leaf model-number {
                 type string;
                 description
                   "Model number of this component";
               }
               leaf board-information-record {
                 type string;
                 description
                   "Hex dump of board information record";
               }
               leaf i2c-data {
                 type string;
                 description
                   "Hex dump of I2C data";
               }
             }
           }
           leaf model-number {
             type string;
             description
               "Model number of this component";
           }
           leaf clei-code {
             type string;
             description
               "Common Language Equipment Identifier code of this component";
           }
         }
         list chassis-re-disk-module {
           key "name";
           leaf name {
             type string;
             description
               "Name of this component";
           }
           leaf disk-size {
             type int32;
             description
               "Disk size (megabytes)";
           }
           leaf model {
             type string;
           }
           leaf serial-number {
             type string;
             description
               "Serial number of this component";
           }
           leaf description {
             type string;
             description
               "Description of this component";
           }
         }
         list chassis-re-usb-module {
           key "name";
           leaf name {
             type string;
             description
               "Name of this component";
           }
           leaf product {
             type string;
           }
           leaf product-number {
             type int32;
           }
           leaf vendor {
             type string;
           }
           leaf description {
             type string;
             description
               "Description of this component";
           }
         }
         list chassis-re-dimm-module {
           key "name";
           leaf name {
             type string;
             description
               "Name of this component";
           }
           leaf part-number {
             type string;
             description
               "Part number of this component";
           }
           leaf die-rev {
             type string;
             description
               " DIE revision of the DIMM";
           }
           leaf pcb-rev {
             type string;
             description
               "PCB revision ";
           }
           leaf mfr-id {
             type string;
             description
               "Manufacture Id of the DIMM";
           }
         }
         list chassis-compute-node-disk-module {
           key "name";
           leaf name {
             type string;
             description
               "Name of this component";
           }
           leaf disk-size {
             type int32;
             description
               "Disk size (megabytes)";
           }
           leaf model {
             type string;
           }
           leaf serial-number {
             type string;
             description
               "Serial number of this component";
           }
           leaf description {
             type string;
             description
               "Description of this component";
           }
         }
         leaf license-mode {
           type string;
           description
             "PTX R/IR mode configured";
         }
         leaf model-number {
           type string;
           description
             "Model number of this component";
         }
         leaf clei-code {
           type string;
           description
             "Common Language Equipment Identifier code of this component";
         }
       }
     }
     list system-firmware {
       leaf firmware-name {
         type string;
         description
           "Name of this component";
       }
       leaf firmware-type {
         type string;
         description
           "Type of this component";
       }
       leaf firmware-tag {
         type int32;
         description
           "Multiple firmware per FRU delimiter";
       }
       leaf firmware-revision {
         type string;
         description
           "Firmware version for this component";
       }
       leaf firmware-revision-available {
         type string;
         description
           "Firmware version available on disk for this component";
       }
       leaf firmware-status {
         type string;
         description
           "Firmware status for this component";
       }
       container system-module {
         leaf firmware-name {
           type string;
           description
             "Name of this component";
         }
         container firmware-state {
           description
             "Firmware status per component type";
           leaf firmware-type {
             type string;
             description
               "Type of this component";
           }
           leaf firmware-status {
             type string;
             description
               "Firmware status for this component";
           }
         }
       }
       container system-sub-module-firmware-list {
         list system-sub-module-firmware {
           description
             "Firmware sub module";
           leaf firmware-name {
             type string;
             description
               "Name of this component";
           }
           leaf firmware-type {
             type string;
             description
               "Type of this component";
           }
           leaf firmware-tag {
             type int32;
             description
               "Multiple firmware per FRU delimiter";
           }
           leaf firmware-revision {
             type string;
             description
               "Firmware version for this component";
           }
           leaf firmware-revision-available {
             type string;
             description
               "Firmware version available on disk for this component";
           }
           leaf firmware-status {
             type string;
             description
               "Firmware status for this component";
           }
         }
       }
     }
   }
   grouping hardware-version-information-block {
     list chassis-version {
       leaf component-name {
         type string;
         description
           "PDU component name";
       }
       leaf component-version {
         type string;
       }
       list chassis-module-version {
         leaf component-name {
           type string;
           description
             "PDU component name";
         }
         leaf component-version {
           type string;
         }
         list chassis-module-sub-version {
           leaf component-name {
             type string;
             description
               "PDU component name";
           }
           leaf component-version {
             type string;
           }
           list chassis-module-sub-sub-version {
             leaf component-name {
               type string;
               description
                 "PDU component name";
             }
             leaf component-version {
               type string;
             }
           }
         }
       }
     }
   }
   grouping chassis-fabric-utilization-information-block {
     list fpc-fabric-utilization {
       leaf fpc-slot {
         type int32;
         description
           "FPC slot";
       }
       leaf pfe-number {
         type int32;
         description
           "PIC PFE number";
       }
       leaf direction {
         type string;
         description
           "Airflow direction";
       }
       leaf max-limit {
         type uint32;
       }
       leaf used {
         type uint32;
       }
       leaf free {
         type uint32;
       }
       leaf high-watermark {
         type uint32;
       }
       leaf last-wmark-timestamp {
         type string;
       }
       leaf upper-threshold {
         type uint32;
       }
       leaf upper-clear-threshold {
         type uint32;
       }
       leaf threshold-upper-exceed {
         type string;
       }
     }
   }
   grouping fpc-information-block {
     list fpc {
       leaf slot {
         type int32;
       }
       leaf state {
         type string;
         description
           "Status of the component";
       }
       leaf comment {
         type string;
       }
       leaf temperature {
         type string;
         description
           "Temperature of the item";
       }
       leaf memory-rldram-size {
         type int32;
         description
           "RLDRAM";
       }
       leaf memory-xr2-size {
         type int32;
         description
           "XR2";
       }
       leaf memory-ddr-dram-size {
         type int32;
         description
           "DDR DRAM";
       }
       container pic-detail {
         container port-information {
           container port {
             leaf port-number {
               type int32;
               description
                 "Port number on the PIC";
             }
             leaf cable-type {
               type string;
               description
                 "Port cable type";
             }
             leaf fiber-mode {
               type string;
               description
                 "Single or multi-mode";
             }
             leaf sfp-vendor-name {
               type string;
               description
                 "SFP vendor name";
             }
             leaf sfp-vendor-pno {
               type string;
               description
                 "SFP vendor part number";
             }
             leaf wavelength {
               type string;
               description
                 "Wavelength of the optical transceiver";
             }
             leaf sfp-vendor-fw-ver {
               type string;
               description
                 "Vendor firmware version";
             }
             leaf sfp-jnpr-ver {
               type string;
               description
                 "Juniper revision";
             }
             leaf sfp-msa-version {
               type string;
               description
                 "MSA version";
             }
             leaf short-long-port {
               type string;
               description
                 "Short or long Port";
             }
           }
         }
         container package-information {
           container package {
             leaf package-name {
               type string;
             }
           }
         }
         container port-profile-speed-information {
           leaf active-portprofile-cfg {
             type string;
             description
               "Current Port Profile Config";
           }
           container profile-port {
             leaf profile-port-number {
               type int32;
               description
                 "PIC port profile port number";
             }
             leaf current-speed {
               type string;
               description
                 "PIC port current speed";
             }
             leaf default-speed {
               type string;
               description
                 "PIC port default speed";
             }
             leaf port-profile-speed-capability {
               type string;
               description
                 "Port profile speed capabilities";
             }
           }
           container port-profile-note-information {
             leaf note-speed {
               type string;
               description
                 "PIC Note";
             }
           }
           container port-profile-channel-note-information {
             leaf note-channel-speed {
               type string;
               description
                 "PIC channel Note";
             }
           }
         }
         container port-group-speed-information {
           container port1 {
             leaf port-number2 {
               type int32;
               description
                 "PIC pg port number";
             }
             leaf pfe-number1 {
               type int32;
               description
                 "PIC pg PFE number";
             }
             leaf pg-number {
               type int32;
               description
                 "PIC port group number";
             }
             leaf speed-capability1 {
               type string;
               description
                 "Port speed capabilities";
             }
           }
         }
         container port-speed-information {
           list port {
             key "port-number1";
             leaf port-number1 {
               type int32;
               description
                 "PIC port number";
             }
             leaf pfe-number {
               type int32;
               description
                 "PIC PFE number";
             }
             leaf speed-capability {
               type string;
               description
                 "Port speed capabilities";
             }
           }
         }
         container pic-error-information {
           container error {
             leaf errnumber {
               type int32;
               description
                 "Serial No";
             }
             leaf errmsg {
               type string;
               description
                 "Configuration Errors";
             }
           }
         }
         container fec-error-information {
           container error {
             leaf errnumber {
               type int32;
               description
                 "Serial No";
             }
             leaf errmsg {
               type string;
               description
                 "Configuration Errors";
             }
           }
         }
         leaf slot {
           type int32;
         }
         leaf pic-slot {
           type int32;
         }
         leaf pic-type {
           type string;
         }
         leaf comment {
           type string;
         }
         leaf asic-type {
           type string;
           description
             "Type of ASIC on the PIC";
         }
         leaf account-layer2-overhead {
           type string;
           description
             "Account Layer2 Overhead Knob Status";
         }
         leaf state {
           type string;
           description
             "Status of the component";
         }
         leaf pic-version {
           type string;
           description
             "PIC hardware version";
         }
         leaf cpu-sw-version {
           type string;
           description
             "Version of operating system running on the PIC";
         }
         leaf cpu-rom-version {
           type string;
           description
             "PIC ROM version";
         }
         leaf cpu-total {
           type int32;
           description
             "Percentage of CPU utilized";
         }
         leaf cpu-interrupt {
           type int32;
           description
             "Percentage of CPU utilized by interrupt processing";
         }
         leaf memory-dram-size {
           type string;
           description
             "DRAM";
         }
         leaf memory-buffer-utilization {
           type int32;
           description
             "Percentage of buffer memory utilized";
         }
         leaf memory-heap-utilization {
           type int32;
           description
             "Percentage of heap memory utilized";
         }
         leaf up-time {
           type string;
           description
             "Length of time this component has been operational";
         }
         leaf pic-package {
           type string;
         }
         leaf pic-clock-sync {
           type string;
           description
             "PIC Clock Synchronization";
         }
         leaf pic-multirate-mode {
           type string;
         }
         leaf pic-channelization-mode {
           type string;
           description
             "PIC Channelization Mode";
         }
         leaf configured-mode {
           type string;
         }
         leaf control-cores {
           type int32;
         }
         leaf data-cores {
           type int32;
         }
         leaf object-cache-size {
           type int32;
         }
         leaf policy-db-size {
           type int32;
         }
         leaf forwarding-db-size {
           type int32;
         }
         leaf wired-process-mem-size {
           type int32;
         }
         leaf wired-max-processes {
           type int32;
         }
         container pic-transport-information {
           leaf pic-transport-admin-state {
             type string;
           }
           leaf pic-transport-oper-state {
             type string;
           }
         }
         leaf slc-slot {
           type int32;
           description
             "SLC id number";
         }
       }
       list mic {
         leaf comment {
           type string;
         }
         leaf mic-slot {
           type int32;
         }
         leaf mic-state {
           type string;
         }
         leaf mic-type {
           type string;
         }
       }
       list pfe-info-values {
         key "pfeid";
         leaf ppfe-id {
           type string;
         }
         leaf pfe-instance {
           type int32;
         }
         leaf pfeid {
           type int32;
         }
         leaf pfe-state {
           type string;
         }
         leaf pfe-temp-perf-throt {
           type string;
         }
         leaf pfe-temp-volt-reduction {
           type string;
         }
       }
       list pfeid-info-values {
         key "pfeid";
         leaf pfe-instance {
           type int32;
         }
         leaf ppfe-id {
           type string;
         }
         leaf pfe-state {
           type string;
         }
         leaf pfe-temp-perf-throt {
           type string;
         }
         leaf pfe-temp-volt-reduction {
           type string;
         }
         leaf pfeid {
           type int32;
         }
       }
       list scope-level {
       }
       container fpc-slc-error-information {
         list scope-level {
         }
       }
       list fpc-error {
         list fpc-error-group-detail {
           leaf fpc-error-group-name {
             type string;
           }
           leaf fpc-error-group-occurred {
             type int32;
           }
           leaf fpc-error-group-cleared {
             type int32;
           }
           leaf fpc-error-group-error-id {
             type int32;
           }
         }
       }
       leaf cpu-total {
         type int32;
         description
           "Percentage of CPU utilized";
       }
       leaf cpu-interrupt {
         type int32;
         description
           "Percentage of CPU utilized by interrupt processing";
       }
       leaf cpu-1min-avg {
         type int32;
         description
           "Percentage of one min average CPU utilized";
       }
       leaf cpu-5min-avg {
         type int32;
         description
           "Percentage of five min average CPU utilized";
       }
       leaf cpu-15min-avg {
         type int32;
         description
           "Percentage of fifteen min average CPU utilized";
       }
       leaf memory-dram-size {
         type string;
         description
           "DRAM";
       }
       leaf memory-heap-utilization {
         type int32;
         description
           "Percentage of heap memory utilized";
       }
       leaf memory-buffer-utilization {
         type int32;
         description
           "Percentage of buffer memory utilized";
       }
       leaf error-code {
         type int32;
         description
           "Code resulting from major or minor error";
       }
       leaf logical-slot {
         type int32;
       }
       leaf cpu-less-info-str {
         type string;
         description
           "Flexible PIC Concentrator (FPC) without CPU";
       }
       leaf memory-sram-size {
         type int32;
         description
           "SRAM";
       }
       leaf memory-sdram-size {
         type int32;
         description
           "SDRAM";
       }
       leaf memory-notification-sdram-size {
         type int32;
         description
           "Notification SDRAM";
       }
       leaf asic-information {
         type string;
       }
       leaf start-time {
         type string;
         description
           "Time this component was started";
       }
       leaf up-time {
         type string;
         description
           "Length of time this component has been operational";
       }
       leaf max-power-consumption {
         type int32;
       }
       leaf memory-hbm-size {
         type int32;
         description
           "HBM";
       }
       leaf last-reboot-reason {
         type string;
         description
           "Last reboot reason of routing engine";
       }
       leaf max-mpc-base-power-consumption {
         type int32;
       }
       leaf max-mic0-power-consumption {
         type int32;
       }
       leaf max-mic1-power-consumption {
         type int32;
       }
       leaf max-mic2-power-consumption {
         type int32;
       }
       leaf max-mic3-power-consumption {
         type int32;
       }
       leaf max-mpc-total-power-consumption {
         type int32;
       }
       leaf fips-capable {
         type string;
         description
           "Does the FPC support FIPS";
       }
       leaf fips-mode {
         type string;
         description
           "Is the FPC in FIPS mode";
       }
       leaf configured-bandwidth {
         type int32;
       }
       leaf operating-bandwidth {
         type int32;
       }
       leaf high-performance-mode-support {
         type string;
         description
           "Is high-performance mode supported";
       }
       leaf pics-in-high-performance-mode {
         type string;
         description
           "PFEs in high-performance mode";
       }
       leaf fpc-pfe-type {
         type string;
       }
       list fpc-pfe-information {
         leaf fpc-pfe-num {
           type int32;
         }
         leaf fpc-pfe-power-state {
           type string;
         }
         leaf fpc-pfe-bandwidth {
           type string;
         }
         leaf fpc-pfe-slc {
           type int32;
           description
             "SLC id number";
         }
       }
       container fpc-slc-information {
         leaf fpc-slc-slot {
           type int32;
           description
             "SLC id number";
         }
         leaf fpc-slc-state {
           type string;
           description
             "SLC state";
         }
         leaf fpc-slc-error-code {
           type int32;
           description
             "Code resulting from major or minor error";
         }
         leaf fpc-slc-version {
           type string;
         }
         leaf fpc-slc-cpu-cores {
           type int32;
           description
             "Cpu cores assigned to SLC";
         }
         leaf fpc-slc-memory-dram-size {
           type string;
           description
             "DRAM";
         }
         leaf fpc-slc-memory-rldram-size {
           type int32;
           description
             "RLDRAM";
         }
         leaf fpc-slc-memory-xr2-size {
           type int32;
           description
             "XR2";
         }
         leaf fpc-slc-memory-ddr-dram-size {
           type int32;
           description
             "DDR DRAM";
         }
         leaf fpc-slc-memory-hbm-size {
           type int32;
           description
             "HBM";
         }
         leaf fpc-slc-start-time {
           type string;
           description
             "Time this component was started";
         }
         leaf fpc-slc-up-time {
           type string;
           description
             "Length of time this component has been operational";
         }
         leaf fpc-slc-comment {
           type string;
         }
         leaf fpc-slc-configured-bandwidth {
           type int32;
         }
         leaf fpc-slc-operating-bandwidth {
           type int32;
         }
         leaf fpc-slot {
           type int32;
           description
             "FPC slot";
         }
         leaf fpc-slc-temperature {
           type int32;
           description
             "Temperature in (C)";
         }
         leaf fpc-slc-cpu-total {
           type int32;
           description
             "Percentage of CPU utilized";
         }
         leaf fpc-slc-cpu-interrupt {
           type int32;
           description
             "Percentage of CPU utilized by interrupt processing";
         }
         leaf fpc-slc-cpu-1min-avg {
           type int32;
           description
             "Percentage of one min average CPU utilized";
         }
         leaf fpc-slc-cpu-5min-avg {
           type int32;
           description
             "Percentage of five min average CPU utilized";
         }
         leaf fpc-slc-cpu-15min-avg {
           type int32;
           description
             "Percentage of fifteen min average CPU utilized";
         }
         leaf fpc-slc-memory-heap-utilization {
           type int32;
           description
             "Percentage of heap memory utilized";
         }
         leaf fpc-slc-memory-buffer-utilization {
           type int32;
           description
             "Percentage of buffer memory utilized";
         }
         leaf fpc-slc-gnf-id {
           type string;
           description
             "Gnf id assigned to SLC";
         }
       }
       leaf description {
         type string;
         description
           "Description of this component";
       }
       list pic {
         leaf pic-slot {
           type int32;
         }
         leaf pic-state {
           type string;
         }
         leaf pic-type {
           type string;
         }
         leaf comment {
           type string;
         }
       }
       leaf gnf-id {
         type string;
       }
       container slc {
         leaf slc-id {
           type int32;
           description
             "SLC id number";
         }
         leaf slc-state {
           type string;
           description
             "SLC state";
         }
         leaf slc-info {
           type string;
           description
             "SLC config info";
         }
         leaf slc-gnf-id {
           type int32;
           description
             "Gnf id assigned to SLC";
         }
       }
     }
     leaf fpc-slot {
       type int32;
       description
         "FPC slot";
     }
     leaf fpc-status {
       type string;
       description
         "FPC status";
     }
     leaf fpc-power-limit {
       type string;
       description
         "FPC power limit";
     }
     leaf fpc-power {
       type string;
       description
         "Total FPC power consumption";
     }
     leaf fpc-priority {
       type string;
       description
         "Priority options";
     }
     leaf fpc-firmware-version {
       type string;
       description
         "POE firmware version";
     }
   }
   grouping fpc-ether-types-information-block {
     list ether {
       leaf slot {
         type int32;
       }
       leaf ether-slot {
         type int32;
       }
       leaf ether-type-default {
         type int32;
       }
       leaf ether-type-configurable {
         type string;
       }
       leaf ether-type-active {
         type int32;
       }
       leaf comment {
         type string;
       }
     }
   }
   grouping fpc-port-information-block {
     list fpc {
       key "slot";
       leaf slot {
         type int32;
       }
       leaf port-num {
         type int32;
       }
       leaf port-config-map {
         type string;
       }
       leaf port-map {
         type string;
       }
       list mic {
         leaf comment {
           type string;
         }
       }
       container pic-detail {
         container port-information {
         }
         container port-profile-speed-information {
         }
         container package-information {
           container package {
             leaf package-name {
               type string;
             }
           }
         }
         container port-group-speed-information {
         }
         container port-speed-information {
         }
         container pic-error-information {
         }
         container fec-error-information {
         }
       }
       list pfe-info-values {
         leaf ppfe-id {
           type string;
         }
       }
       list pfeid-info-values {
         leaf pfe-instance {
           type int32;
         }
         leaf ppfe-id {
           type string;
         }
         leaf pfe-state {
           type string;
         }
         leaf pfe-temp-perf-throt {
           type string;
         }
         leaf pfe-temp-volt-reduction {
           type string;
         }
       }
       list scope-level {
       }
       container fpc-slc-error-information {
         list scope-level {
         }
       }
       list fpc-error {
         list fpc-error-group-detail {
           leaf fpc-error-group-name {
             type string;
           }
           leaf fpc-error-group-occurred {
             type int32;
           }
           leaf fpc-error-group-cleared {
             type int32;
           }
           leaf fpc-error-group-error-id {
             type int32;
           }
         }
       }
     }
   }
   grouping fpc-error-information-block {
     list fpc {
       leaf slot {
         type int32;
       }
       leaf minor-level-occured {
         type int32;
       }
       leaf minor-level-cleared {
         type int32;
       }
       leaf minor-level-threshold {
         type int32;
       }
       leaf minor-level-action-taken {
         type int32;
       }
       leaf minor-level-action {
         type string;
       }
       leaf major-level-occured {
         type int32;
       }
       leaf major-level-cleared {
         type int32;
       }
       leaf major-level-threshold {
         type int32;
       }
       leaf major-level-action-taken {
         type int32;
       }
       leaf major-level-action {
         type string;
       }
       leaf fatal-level-occured {
         type int32;
       }
       leaf fatal-level-cleared {
         type int32;
       }
       leaf fatal-level-threshold {
         type int32;
       }
       leaf fatal-level-action-taken {
         type int32;
       }
       leaf fatal-level-action {
         type string;
       }
       leaf fpc-pfe-state {
         type string;
       }
       leaf memory-rldram-size {
         type int32;
         description
           "RLDRAM";
       }
       leaf memory-xr2-size {
         type int32;
         description
           "XR2";
       }
       leaf memory-ddr-dram-size {
         type int32;
         description
           "DDR DRAM";
       }
       container pic-detail {
         container port-information {
         }
         container package-information {
           container package {
             leaf package-name {
               type string;
             }
           }
         }
         container port-profile-speed-information {
         }
         container port-group-speed-information {
         }
         container port-speed-information {
         }
         container pic-error-information {
         }
         container fec-error-information {
         }
       }
       list mic {
         leaf comment {
           type string;
         }
       }
       list pfe-info-values {
         leaf ppfe-id {
           type string;
         }
       }
       list pfeid-info-values {
         leaf pfe-instance {
           type int32;
         }
         leaf ppfe-id {
           type string;
         }
         leaf pfe-state {
           type string;
         }
         leaf pfe-temp-perf-throt {
           type string;
         }
         leaf pfe-temp-volt-reduction {
           type string;
         }
       }
       list scope-level {
         leaf scope {
           type string;
           description
             "Error scope";
         }
         list category-level {
           leaf category {
             type string;
             description
               "Error category";
           }
           leaf minor-level-occurred {
             type uint32;
           }
           leaf minor-level-cleared {
             type uint32;
           }
           leaf minor-level-threshold {
             type uint32;
           }
           leaf minor-level-action-taken {
             type uint32;
           }
           leaf minor-level-action {
             type string;
           }
           leaf major-level-occurred {
             type uint32;
           }
           leaf major-level-cleared {
             type uint32;
           }
           leaf major-level-threshold {
             type uint32;
           }
           leaf major-level-action-taken {
             type uint32;
           }
           leaf major-level-action {
             type string;
           }
           leaf fatal-level-occurred {
             type uint32;
           }
           leaf fatal-level-cleared {
             type uint32;
           }
           leaf fatal-level-threshold {
             type uint32;
           }
           leaf fatal-level-action-taken {
             type uint32;
           }
           leaf fatal-level-action {
             type string;
           }
         }
       }
       container fpc-slc-error-information {
         leaf slot {
           type int32;
         }
         leaf fpc-slc-error-slot {
           type int32;
           description
             "SLC id number";
         }
         leaf slc-fpc-pfe-state {
           type string;
         }
         list scope-level {
           leaf scope {
             type string;
             description
               "Error scope";
           }
           list category-level {
             leaf category {
               type string;
               description
                 "Error category";
             }
             leaf minor-level-occurred {
               type uint32;
             }
             leaf minor-level-cleared {
               type uint32;
             }
             leaf minor-level-threshold {
               type uint32;
             }
             leaf minor-level-action-taken {
               type uint32;
             }
             leaf minor-level-action {
               type string;
             }
             leaf major-level-occurred {
               type uint32;
             }
             leaf major-level-cleared {
               type uint32;
             }
             leaf major-level-threshold {
               type uint32;
             }
             leaf major-level-action-taken {
               type uint32;
             }
             leaf major-level-action {
               type string;
             }
             leaf fatal-level-occurred {
               type uint32;
             }
             leaf fatal-level-cleared {
               type uint32;
             }
             leaf fatal-level-threshold {
               type uint32;
             }
             leaf fatal-level-action-taken {
               type uint32;
             }
             leaf fatal-level-action {
               type string;
             }
           }
         }
       }
       list fpc-error {
         list fpc-error-group-detail {
           leaf fpc-error-group-name {
             type string;
           }
           leaf fpc-error-group-occurred {
             type int32;
           }
           leaf fpc-error-group-cleared {
             type int32;
           }
           leaf fpc-error-group-error-id {
             type int32;
           }
           leaf fpc-error-group-description {
             type string;
           }
           leaf fpc-error-group-threshold {
             type int32;
           }
         }
         leaf pfe-id {
           type string;
         }
         list fpc-error-group {
           leaf fpc-error-group-name {
             type string;
           }
           leaf fpc-error-group-occurred {
             type int32;
           }
           leaf fpc-error-group-cleared {
             type int32;
           }
           leaf fpc-error-group-action {
             type string;
           }
           leaf fpc-error-group-threshold {
             type int32;
           }
           leaf fpc-error-group-error-id {
             type int32;
           }
         }
       }
     }
   }
   grouping fpc-optical-information-block {
     leaf fpc-optical-prod-mb {
       type string;
       description
         "Optical module main board product name";
     }
     leaf fpc-optical-prod-edfa {
       type string;
       description
         "Optical module EDFA product name";
     }
     leaf fpc-optical-prod-wss {
       type string;
       description
         "Optical module WSS product name";
     }
     leaf fpc-optical-prod-ocm {
       type string;
       description
         "Optical module OCM product name";
     }
     leaf fpc-optical-mod-mb {
       type string;
       description
         "Optical module main board module type";
     }
     leaf fpc-optical-mod-edfa {
       type string;
       description
         "Optical module EDFA module type";
     }
     leaf fpc-optical-mod-wss {
       type string;
       description
         "Optical module WSS module type";
     }
     leaf fpc-optical-mod-ocm {
       type string;
       description
         "Optical module OCM module type";
     }
     leaf fpc-optical-boot-edfa {
       type string;
       description
         "Optical module EDFA boot version";
     }
     leaf fpc-optical-boot-ocm {
       type string;
       description
         "Optical module OCM boot version";
     }
     leaf fpc-optical-sw-mb {
       type string;
       description
         "Optical module main board software version";
     }
     leaf fpc-optical-fw-mb {
       type string;
       description
         "Optical module main board firmware version";
     }
     leaf fpc-optical-fw-edfa {
       type string;
       description
         "Optical module EDFA firmware version";
     }
     leaf fpc-optical-fw-wss {
       type string;
       description
         "Optical module WSS firmware version";
     }
     leaf fpc-optical-fw-ocm {
       type string;
       description
         "Optical module OCM firmware version";
     }
     leaf fpc-optical-fpga-mb {
       type string;
       description
         "Optical module main board FPGA version";
     }
     leaf fpc-optical-fpga-edfa {
       type string;
       description
         "Optical module EDFA FPGA version";
     }
     leaf fpc-optical-cpld-mb {
       type string;
       description
         "Optical module main board CPLD version";
     }
     leaf fpc-optical-hw-mb {
       type string;
       description
         "Optical module main board hardware version";
     }
     leaf fpc-optical-hw-edfa {
       type string;
       description
         "Optical module EDFA hardware version";
     }
     leaf fpc-optical-hw-wss {
       type string;
       description
         "Optical module WSS hardware version";
     }
     leaf fpc-optical-hw-ocm {
       type string;
       description
         "Optical module OCM hardware version";
     }
     leaf fpc-optical-pcb-mb {
       type string;
       description
         "Optical module main board PCB revision";
     }
     leaf fpc-optical-pcb-edfa {
       type string;
       description
         "Optical module EDFA PCB revision";
     }
     leaf fpc-optical-pcb-wss {
       type string;
       description
         "Optical module WSS PCB revision";
     }
     leaf fpc-optical-pcb-ocm {
       type string;
       description
         "Optical module OCM PCB revision";
     }
     leaf fpc-optical-pn-mb {
       type string;
       description
         "Optical module main board part number";
     }
     leaf fpc-optical-pn-edfa {
       type string;
       description
         "Optical module EDFA part number";
     }
     leaf fpc-optical-pn-wss {
       type string;
       description
         "Optical module WSS part number";
     }
     leaf fpc-optical-pn-ocm {
       type string;
       description
         "Optical module OCM part number";
     }
     leaf fpc-optical-sn-mb {
       type string;
       description
         "Optical module main board serial number";
     }
     leaf fpc-optical-sn-edfa {
       type string;
       description
         "Optical module EDFA serial number";
     }
     leaf fpc-optical-sn-wss {
       type string;
       description
         "Optical module WSS serial number";
     }
     leaf fpc-optical-sn-ocm {
       type string;
       description
         "Optical module OCM serial number";
     }
     leaf fpc-optical-mdate-mb {
       type string;
       description
         "Optical module main board manufacture date";
     }
     leaf fpc-optical-mdate-edfa {
       type string;
       description
         "Optical module EDFA manufacture date";
     }
     leaf fpc-optical-mdate-wss {
       type string;
       description
         "Optical module WSS manufacture date";
     }
     leaf fpc-optical-mdate-ocm {
       type string;
       description
         "Optical module OCM manufacture date";
     }
     leaf fpc-optical-cdate-mb {
       type string;
       description
         "Optical module main board calibration date";
     }
     leaf fpc-optical-cdate-edfa {
       type string;
       description
         "Optical module EDFA calibration date";
     }
     leaf fpc-optical-cdate-wss {
       type string;
       description
         "Optical module WSS calibration date";
     }
     leaf fpc-optical-cdate-ocm {
       type string;
       description
         "Optical module OCM calibration date";
     }
     leaf fpc-optical-ocm-awg {
       type string;
       description
         "Optical module OCM channel 0 AWG port power";
     }
     leaf fpc-optical-ocm-e2out {
       type string;
       description
         "Optical module OCM channel 0 E2 output port power";
     }
     leaf fpc-optical-channel {
       type string;
       description
         "Optical module OCM channel";
     }
     leaf fpc-optical-channel-awg {
       type string;
       description
         "Optical module OCM channel AWG";
     }
     leaf fpc-optical-channel-e2out {
       type string;
       description
         "Optical module OCM channel E2OUT";
     }
     leaf fpc-optical-status-uptime {
       type string;
       description
         "Optical module operational uptime";
     }
     leaf fpc-optical-status-edfa1-temp {
       type string;
       description
         "Optical module operational EDFA 1 case temperature";
     }
     leaf fpc-optical-status-edfa1-pump {
       type string;
       description
         "Optical module operational EDFA 1 pump temperature";
     }
     leaf fpc-optical-status-edfa1-coil {
       type string;
       description
         "Optical module operational EDFA 1 coil temperature";
     }
     leaf fpc-optical-status-edfa2-temp {
       type string;
       description
         "Optical module operational EDFA 2 case temperature";
     }
     leaf fpc-optical-status-edfa2-pump {
       type string;
       description
         "Optical module operational EDFA 2 pump temperature";
     }
     leaf fpc-optical-status-edfa2-coil {
       type string;
       description
         "Optical module operational EDFA 2 coil temperature";
     }
     leaf fpc-optical-status-wss-vol {
       type string;
       description
         "Optical module operational WSS voltage";
     }
     leaf fpc-optical-status-wss-temp {
       type string;
       description
         "Optical module operational WSS temperature";
     }
     leaf fpc-optical-status-ocm-temp {
       type string;
       description
         "Optical module operational OCM temperature";
     }
     leaf fpc-optical-status-osc-status {
       type string;
       description
         "Optical module operational OSC status";
     }
     leaf fpc-optical-alarm {
       type string;
       description
         "Optical module alarm status";
     }
     leaf fpc-optical-alarm-edfa1 {
       type string;
       description
         "Optical module EDFA1 alarm status";
     }
     leaf fpc-optical-alarm-edfa2 {
       type string;
       description
         "Optical module EDFA2 alarm status";
     }
     leaf fpc-optical-alarm-wss {
       type string;
       description
         "Optical module WSS alarm status";
     }
     leaf fpc-optical-edfa1-gains {
       type string;
       description
         "Optical module EDFA1 gain setting save";
     }
     leaf fpc-optical-edfa2-gains {
       type string;
       description
         "Optical module EDFA2 gain setting save";
     }
     leaf fpc-optical-edfa1-tilt {
       type string;
       description
         "Optical module EDFA1 gain tilt";
     }
     leaf fpc-optical-edfa2-tilt {
       type string;
       description
         "Optical module EDFA2 gain tilt";
     }
     leaf fpc-optical-edfa1-ilos-ut {
       type string;
       description
         "Optical module EDFA1 input LOS upper threshold";
     }
     leaf fpc-optical-edfa2-ilos-ut {
       type string;
       description
         "Optical module EDFA2 input LOS upper threshold";
     }
     leaf fpc-optical-edfa1-ilos-lt {
       type string;
       description
         "Optical module EDFA1 input LOS lower threshold";
     }
     leaf fpc-optical-edfa2-ilos-lt {
       type string;
       description
         "Optical module EDFA2 input LOS lower threshold";
     }
     leaf fpc-optical-edfa1-olos-ut {
       type string;
       description
         "Optical module EDFA1 output LOS upper threshold";
     }
     leaf fpc-optical-edfa2-olos-ut {
       type string;
       description
         "Optical module EDFA2 output LOS upper threshold";
     }
     leaf fpc-optical-edfa1-olos-lt {
       type string;
       description
         "Optical module EDFA1 output LOS lower threshold";
     }
     leaf fpc-optical-edfa2-olos-lt {
       type string;
       description
         "Optical module EDFA2 output LOS lower threshold";
     }
     leaf fpc-optical-edfa1-gain {
       type string;
       description
         "Optical module EDFA1 gain setting";
     }
     leaf fpc-optical-edfa2-gain {
       type string;
       description
         "Optical module EDFA2 gain setting";
     }
     leaf fpc-optical-edfa1-output {
       type string;
       description
         "Optical module EDFA1 output enable";
     }
     leaf fpc-optical-edfa2-output {
       type string;
       description
         "Optical module EDFA2 output enable";
     }
     leaf fpc-optical-edfa1-autolos {
       type string;
       description
         "Optical module EDFA1 auto LOS enable";
     }
     leaf fpc-optical-edfa2-autolos {
       type string;
       description
         "Optical module EDFA2 auto LOS enable";
     }
     leaf fpc-optical-edfa1-mode {
       type string;
       description
         "Optical module EDFA1 mode";
     }
     leaf fpc-optical-edfa2-mode {
       type string;
       description
         "Optical module EDFA2 mode";
     }
     leaf fpc-optical-edfa1-plim {
       type string;
       description
         "Optical module EDFA1 plim power";
     }
     leaf fpc-optical-edfa2-plim {
       type string;
       description
         "Optical module EDFA2 plim power";
     }
     leaf fpc-optical-ila-edfa-info {
       type string;
       description
         "Optical ila edfa information";
     }
     leaf fpc-optical-ila-edfa-index {
       type string;
       description
         "Optical ila edfa index";
     }
     leaf fpc-optical-ila-edfa-mfg-info {
       type string;
       description
         "Optical ila edfa manufacture info";
     }
     leaf fpc-optical-ila-edfa-module-type {
       type string;
       description
         "Optical ila edfa module type";
     }
     leaf fpc-optical-ila-edfa-part-number {
       type string;
       description
         "Optical ila edfa part number";
     }
     leaf fpc-optical-ila-edfa-serial-number {
       type string;
       description
         "Optical ila edfa serial number";
     }
     leaf fpc-optical-ila-edfa-mfg-date {
       type string;
       description
         "Optical ila edfa manufacture date";
     }
     leaf fpc-optical-ila-edfa-cali-date {
       type string;
       description
         "Optical ila edfa calibration date";
     }
     leaf fpc-optical-ila-edfa-firmware-ver {
       type string;
       description
         "Optical ila edfa firmware version";
     }
     leaf fpc-optical-ila-edfa-hardware-ver {
       type string;
       description
         "Optical ila edfa hardware version";
     }
     leaf fpc-optical-ila-edfa-mode {
       type string;
       description
         "Optical ila edfa mode";
     }
     leaf fpc-optical-ila-edfa-gain-setting {
       type string;
       description
         "Optical ila edfa gain setting";
     }
     leaf fpc-optical-ila-edfa-tilt {
       type string;
       description
         "Optical ila edfa tilt";
     }
     leaf fpc-optical-ila-edfa-work-status {
       type string;
       description
         "Optical ila edfa work status";
     }
     leaf fpc-optical-ila-edfa-apr-enable {
       type string;
       description
         "Optical ila edfa apr enable";
     }
     leaf fpc-optical-ila-edfa-work-range {
       type string;
       description
         "Optical ila edfa work range";
     }
     leaf fpc-optical-ila-edfa-actual-gain {
       type string;
       description
         "Optical ila edfa actual gain";
     }
     leaf fpc-optical-ila-edfa-case-temp {
       type string;
       description
         "Optical ila edfa case temperature";
     }
     leaf fpc-optical-ila-edfa-pump-temp {
       type string;
       description
         "Optical ila edfa pump temperature";
     }
     leaf fpc-optical-ila-edfa-asc {
       type string;
       description
         "Optical ila edfa asc";
     }
     leaf fpc-optical-ila-edfa-upstream-output-power {
       type string;
       description
         "Optical ila edfa upstream output power";
     }
     leaf fpc-optical-ila-edfa-input-power {
       type string;
       description
         "Optical ila edfa input power";
     }
     leaf fpc-optical-ila-edfa-output-power {
       type string;
       description
         "Optical ila edfa output power";
     }
     leaf fpc-optical-ila-edfa-downstream-input-power {
       type string;
       description
         "Optical ila edfa downstream input power";
     }
     leaf fpc-optical-ila-edfa-input-los-threshold {
       type string;
       description
         "Optical ila edfa input los threshold";
     }
     leaf fpc-optical-ila-edfa-output-los-threshold {
       type string;
       description
         "Optical ila edfa output los threshold";
     }
     leaf fpc-optical-topology-wavelength {
       type string;
       description
         "Optical module topology";
     }
     leaf fpc-optical-port {
       type string;
       description
         "Optical module WSS port";
     }
     leaf fpc-optical-frequency {
       type string;
       description
         "Optical module frequency";
     }
     leaf fpc-optical-ocm-lout {
       type string;
       description
         "Optical module OCM channel 0 line out port power";
     }
     leaf fpc-optical-wss-port {
       type string;
       description
         "Optical module WSS channel 0 port";
     }
     leaf fpc-optical-wss-attn {
       type string;
       description
         "Optical module WSS channel 0 attenuation";
     }
     leaf fpc-optical-pm-slot {
       type string;
       description
         "Optical module PM FPC slot";
     }
     leaf fpc-optical-pm-timestamp {
       type string;
       description
         "Optical module PM timestamp";
     }
     leaf fpc-optical-pm-suspect-flag {
       type string;
       description
         "Optical module PM suspect flag";
     }
     leaf fpc-optical-pm-suspect-reason {
       type string;
       description
         "Optical module PM suspect reason";
     }
     leaf fpc-optical-pm-osc-txpwr-cur {
       type string;
       description
         "Optical module PM OSC Tx power current";
     }
     leaf fpc-optical-pm-osc-txpwr-min {
       type string;
       description
         "Optical module PM OSC Tx power min";
     }
     leaf fpc-optical-pm-osc-txpwr-max {
       type string;
       description
         "Optical module PM OSC Tx power max";
     }
     leaf fpc-optical-pm-osc-txpwr-avg {
       type string;
       description
         "Optical module PM OSC Tx power avg";
     }
     leaf fpc-optical-pm-osc-txpwr-min-tca-th {
       type string;
       description
         "Optical module PM OSC Tx power TCA min threshold";
     }
     leaf fpc-optical-pm-osc-txpwr-max-tca-th {
       type string;
       description
         "Optical module PM OSC Tx power TCA max threshold";
     }
     leaf fpc-optical-pm-osc-txpwr-min-tca-en {
       type string;
       description
         "Optical module PM OSC Tx power TCA min enable";
     }
     leaf fpc-optical-pm-osc-txpwr-max-tca-en {
       type string;
       description
         "Optical module PM OSC Tx power TCA max enable";
     }
     leaf fpc-optical-pm-osc-txpwr-min-tca-state {
       type string;
       description
         "Optical module PM OSC Tx power TCA min state";
     }
     leaf fpc-optical-pm-osc-txpwr-max-tca-state {
       type string;
       description
         "Optical module PM OSC Tx power TCA max state";
     }
     leaf fpc-optical-pm-osc-rxpwr-cur {
       type string;
       description
         "Optical module PM OSC Rx power current";
     }
     leaf fpc-optical-pm-osc-rxpwr-min {
       type string;
       description
         "Optical module PM OSC Rx power min";
     }
     leaf fpc-optical-pm-osc-rxpwr-max {
       type string;
       description
         "Optical module PM OSC Rx power max";
     }
     leaf fpc-optical-pm-osc-rxpwr-avg {
       type string;
       description
         "Optical module PM OSC Rx power avg";
     }
     leaf fpc-optical-pm-osc-rxpwr-min-tca-th {
       type string;
       description
         "Optical module PM OSC Rx power TCA min threshold";
     }
     leaf fpc-optical-pm-osc-rxpwr-max-tca-th {
       type string;
       description
         "Optical module PM OSC Rx power TCA max threshold";
     }
     leaf fpc-optical-pm-osc-rxpwr-min-tca-en {
       type string;
       description
         "Optical module PM OSC Rx power TCA min enable";
     }
     leaf fpc-optical-pm-osc-rxpwr-max-tca-en {
       type string;
       description
         "Optical module PM OSC Rx power TCA max enable";
     }
     leaf fpc-optical-pm-osc-rxpwr-min-tca-state {
       type string;
       description
         "Optical module PM OSC Rx power TCA min state";
     }
     leaf fpc-optical-pm-osc-rxpwr-max-tca-state {
       type string;
       description
         "Optical module PM OSC Rx power TCA max state";
     }
     leaf fpc-optical-pm-osc-los-cur {
       type string;
       description
         "Optical module PM OSC LOS current";
     }
     leaf fpc-optical-pm-osc-los-min {
       type string;
       description
         "Optical module PM OSC LOS min";
     }
     leaf fpc-optical-pm-osc-los-max {
       type string;
       description
         "Optical module PM OSC LOS max";
     }
     leaf fpc-optical-pm-osc-los-avg {
       type string;
       description
         "Optical module PM OSC LOS avg";
     }
     leaf fpc-optical-pm-osc-los-min-tca-th {
       type string;
       description
         "Optical module PM OSC LOS TCA min threshold";
     }
     leaf fpc-optical-pm-osc-los-max-tca-th {
       type string;
       description
         "Optical module PM OSC LOS TCA max threshold";
     }
     leaf fpc-optical-pm-osc-los-min-tca-en {
       type string;
       description
         "Optical module PM OSC LOS TCA min enable";
     }
     leaf fpc-optical-pm-osc-los-max-tca-en {
       type string;
       description
         "Optical module PM OSC LOS TCA max enable";
     }
     leaf fpc-optical-pm-osc-los-min-tca-state {
       type string;
       description
         "Optical module PM OSC LOS TCA min state";
     }
     leaf fpc-optical-pm-osc-los-max-tca-state {
       type string;
       description
         "Optical module PM OSC LOS TCA max state";
     }
     leaf fpc-optical-pm-lout-voa-cur {
       type string;
       description
         "Optical module PM LOUT VOA attenuation current";
     }
     leaf fpc-optical-pm-lout-voa-min {
       type string;
       description
         "Optical module PM LOUT VOA attenuation min";
     }
     leaf fpc-optical-pm-lout-voa-max {
       type string;
       description
         "Optical module PM LOUT VOA attenuation max";
     }
     leaf fpc-optical-pm-lout-voa-avg {
       type string;
       description
         "Optical module PM LOUT VOA attenuation avg";
     }
     leaf fpc-optical-pm-lout-voa-min-tca-th {
       type string;
       description
         "Optical module PM LOUT VOA attenuation TCA min threshold";
     }
     leaf fpc-optical-pm-lout-voa-max-tca-th {
       type string;
       description
         "Optical module PM LOUT VOA attenuation TCA max threshold";
     }
     leaf fpc-optical-pm-lout-voa-min-tca-en {
       type string;
       description
         "Optical module PM LOUT VOA attenuation TCA min enable";
     }
     leaf fpc-optical-pm-lout-voa-max-tca-en {
       type string;
       description
         "Optical module PM LOUT VOA attenuation TCA max enable";
     }
     leaf fpc-optical-pm-lout-voa-min-tca-state {
       type string;
       description
         "Optical module PM LOUT VOA attenuation TCA min state";
     }
     leaf fpc-optical-pm-lout-voa-max-tca-state {
       type string;
       description
         "Optical module PM LOUT VOA attenuation TCA max state";
     }
     leaf fpc-optical-pm-edfa1-inpwr-cur {
       type string;
       description
         "Optical module PM EDFA1 input power current";
     }
     leaf fpc-optical-pm-edfa1-inpwr-min {
       type string;
       description
         "Optical module PM EDFA1 input power min";
     }
     leaf fpc-optical-pm-edfa1-inpwr-max {
       type string;
       description
         "Optical module PM EDFA1 input power max";
     }
     leaf fpc-optical-pm-edfa1-inpwr-avg {
       type string;
       description
         "Optical module PM EDFA1 input power avg";
     }
     leaf fpc-optical-pm-edfa1-inpwr-min-tca-th {
       type string;
       description
         "Optical module PM EDFA1 input power TCA min threshold";
     }
     leaf fpc-optical-pm-edfa1-inpwr-max-tca-th {
       type string;
       description
         "Optical module PM EDFA1 input power TCA max threshold";
     }
     leaf fpc-optical-pm-edfa1-inpwr-min-tca-en {
       type string;
       description
         "Optical module PM EDFA1 input power TCA min enable";
     }
     leaf fpc-optical-pm-edfa1-inpwr-max-tca-en {
       type string;
       description
         "Optical module PM EDFA1 input power TCA max enable";
     }
     leaf fpc-optical-pm-edfa1-inpwr-min-tca-state {
       type string;
       description
         "Optical module PM EDFA1 input power TCA min state";
     }
     leaf fpc-optical-pm-edfa1-inpwr-max-tca-state {
       type string;
       description
         "Optical module PM EDFA1 input power TCA max state";
     }
     leaf fpc-optical-pm-edfa1-outpwr-cur {
       type string;
       description
         "Optical module PM EDFA1 output power current";
     }
     leaf fpc-optical-pm-edfa1-outpwr-min {
       type string;
       description
         "Optical module PM EDFA1 output power min";
     }
     leaf fpc-optical-pm-edfa1-outpwr-max {
       type string;
       description
         "Optical module PM EDFA1 output power max";
     }
     leaf fpc-optical-pm-edfa1-outpwr-avg {
       type string;
       description
         "Optical module PM EDFA1 output power avg";
     }
     leaf fpc-optical-pm-edfa1-outpwr-min-tca-th {
       type string;
       description
         "Optical module PM EDFA1 output power TCA min threshold";
     }
     leaf fpc-optical-pm-edfa1-outpwr-max-tca-th {
       type string;
       description
         "Optical module PM EDFA1 output power TCA max threshold";
     }
     leaf fpc-optical-pm-edfa1-outpwr-min-tca-en {
       type string;
       description
         "Optical module PM EDFA1 output power TCA min enable";
     }
     leaf fpc-optical-pm-edfa1-outpwr-max-tca-en {
       type string;
       description
         "Optical module PM EDFA1 output power TCA max enable";
     }
     leaf fpc-optical-pm-edfa1-outpwr-min-tca-state {
       type string;
       description
         "Optical module PM EDFA1 output power TCA min state";
     }
     leaf fpc-optical-pm-edfa1-outpwr-max-tca-state {
       type string;
       description
         "Optical module PM EDFA1 output power TCA max state";
     }
     leaf fpc-optical-pm-edfa1-sigpwr-cur {
       type string;
       description
         "Optical module PM EDFA1 signal power current";
     }
     leaf fpc-optical-pm-edfa1-sigpwr-min {
       type string;
       description
         "Optical module PM EDFA1 signal power min";
     }
     leaf fpc-optical-pm-edfa1-sigpwr-max {
       type string;
       description
         "Optical module PM EDFA1 signal power max";
     }
     leaf fpc-optical-pm-edfa1-sigpwr-avg {
       type string;
       description
         "Optical module PM EDFA1 signal power avg";
     }
     leaf fpc-optical-pm-edfa1-sigpwr-min-tca-th {
       type string;
       description
         "Optical module PM EDFA1 signal power TCA min threshold";
     }
     leaf fpc-optical-pm-edfa1-sigpwr-max-tca-th {
       type string;
       description
         "Optical module PM EDFA1 signal power TCA max threshold";
     }
     leaf fpc-optical-pm-edfa1-sigpwr-min-tca-en {
       type string;
       description
         "Optical module PM EDFA1 signal power TCA min enable";
     }
     leaf fpc-optical-pm-edfa1-sigpwr-max-tca-en {
       type string;
       description
         "Optical module PM EDFA1 signal power TCA max enable";
     }
     leaf fpc-optical-pm-edfa1-sigpwr-min-tca-state {
       type string;
       description
         "Optical module PM EDFA1 signal power TCA min state";
     }
     leaf fpc-optical-pm-edfa1-sigpwr-max-tca-state {
       type string;
       description
         "Optical module PM EDFA1 signal power TCA max state";
     }
     leaf fpc-optical-pm-edfa1-pump-cur {
       type string;
       description
         "Optical module PM EDFA1 pump current current";
     }
     leaf fpc-optical-pm-edfa1-pump-min {
       type string;
       description
         "Optical module PM EDFA1 pump current min";
     }
     leaf fpc-optical-pm-edfa1-pump-max {
       type string;
       description
         "Optical module PM EDFA1 pump current max";
     }
     leaf fpc-optical-pm-edfa1-pump-avg {
       type string;
       description
         "Optical module PM EDFA1 pump current avg";
     }
     leaf fpc-optical-pm-edfa1-pump-min-tca-th {
       type string;
       description
         "Optical module PM EDFA1 pump current TCA min threshold";
     }
     leaf fpc-optical-pm-edfa1-pump-max-tca-th {
       type string;
       description
         "Optical module PM EDFA1 pump current TCA max threshold";
     }
     leaf fpc-optical-pm-edfa1-pump-min-tca-en {
       type string;
       description
         "Optical module PM EDFA1 pump current TCA min enable";
     }
     leaf fpc-optical-pm-edfa1-pump-max-tca-en {
       type string;
       description
         "Optical module PM EDFA1 pump current TCA max enable";
     }
     leaf fpc-optical-pm-edfa1-pump-min-tca-state {
       type string;
       description
         "Optical module PM EDFA1 pump current TCA min state";
     }
     leaf fpc-optical-pm-edfa1-pump-max-tca-state {
       type string;
       description
         "Optical module PM EDFA1 pump current TCA max state";
     }
     leaf fpc-optical-pm-edfa2-inpwr-cur {
       type string;
       description
         "Optical module PM EDFA2 input power current";
     }
     leaf fpc-optical-pm-edfa2-inpwr-min {
       type string;
       description
         "Optical module PM EDFA2 input power min";
     }
     leaf fpc-optical-pm-edfa2-inpwr-max {
       type string;
       description
         "Optical module PM EDFA2 input power max";
     }
     leaf fpc-optical-pm-edfa2-inpwr-avg {
       type string;
       description
         "Optical module PM EDFA2 input power avg";
     }
     leaf fpc-optical-pm-edfa2-inpwr-min-tca-th {
       type string;
       description
         "Optical module PM EDFA2 input power TCA min threshold";
     }
     leaf fpc-optical-pm-edfa2-inpwr-max-tca-th {
       type string;
       description
         "Optical module PM EDFA2 input power TCA max threshold";
     }
     leaf fpc-optical-pm-edfa2-inpwr-min-tca-en {
       type string;
       description
         "Optical module PM EDFA2 input power TCA min enable";
     }
     leaf fpc-optical-pm-edfa2-inpwr-max-tca-en {
       type string;
       description
         "Optical module PM EDFA2 input power TCA max enable";
     }
     leaf fpc-optical-pm-edfa2-inpwr-min-tca-state {
       type string;
       description
         "Optical module PM EDFA2 input power TCA min state";
     }
     leaf fpc-optical-pm-edfa2-inpwr-max-tca-state {
       type string;
       description
         "Optical module PM EDFA2 input power TCA max state";
     }
     leaf fpc-optical-pm-edfa2-outpwr-cur {
       type string;
       description
         "Optical module PM EDFA2 output power current";
     }
     leaf fpc-optical-pm-edfa2-outpwr-min {
       type string;
       description
         "Optical module PM EDFA2 output power min";
     }
     leaf fpc-optical-pm-edfa2-outpwr-max {
       type string;
       description
         "Optical module PM EDFA2 output power max";
     }
     leaf fpc-optical-pm-edfa2-outpwr-avg {
       type string;
       description
         "Optical module PM EDFA2 output power avg";
     }
     leaf fpc-optical-pm-edfa2-outpwr-min-tca-th {
       type string;
       description
         "Optical module PM EDFA2 output power TCA min threshold";
     }
     leaf fpc-optical-pm-edfa2-outpwr-max-tca-th {
       type string;
       description
         "Optical module PM EDFA2 output power TCA max threshold";
     }
     leaf fpc-optical-pm-edfa2-outpwr-min-tca-en {
       type string;
       description
         "Optical module PM EDFA2 output power TCA min enable";
     }
     leaf fpc-optical-pm-edfa2-outpwr-max-tca-en {
       type string;
       description
         "Optical module PM EDFA2 output power TCA max enable";
     }
     leaf fpc-optical-pm-edfa2-outpwr-min-tca-state {
       type string;
       description
         "Optical module PM EDFA2 output power TCA min state";
     }
     leaf fpc-optical-pm-edfa2-outpwr-max-tca-state {
       type string;
       description
         "Optical module PM EDFA2 output power TCA max state";
     }
     leaf fpc-optical-pm-edfa2-sigpwr-cur {
       type string;
       description
         "Optical module PM EDFA2 signal power current";
     }
     leaf fpc-optical-pm-edfa2-sigpwr-min {
       type string;
       description
         "Optical module PM EDFA2 signal power min";
     }
     leaf fpc-optical-pm-edfa2-sigpwr-max {
       type string;
       description
         "Optical module PM EDFA2 signal power max";
     }
     leaf fpc-optical-pm-edfa2-sigpwr-avg {
       type string;
       description
         "Optical module PM EDFA2 signal power avg";
     }
     leaf fpc-optical-pm-edfa2-sigpwr-min-tca-th {
       type string;
       description
         "Optical module PM EDFA2 signal power TCA min threshold";
     }
     leaf fpc-optical-pm-edfa2-sigpwr-max-tca-th {
       type string;
       description
         "Optical module PM EDFA2 signal power TCA max threshold";
     }
     leaf fpc-optical-pm-edfa2-sigpwr-min-tca-en {
       type string;
       description
         "Optical module PM EDFA2 signal power TCA min enable";
     }
     leaf fpc-optical-pm-edfa2-sigpwr-max-tca-en {
       type string;
       description
         "Optical module PM EDFA2 signal power TCA max enable";
     }
     leaf fpc-optical-pm-edfa2-sigpwr-min-tca-state {
       type string;
       description
         "Optical module PM EDFA2 signal power TCA min state";
     }
     leaf fpc-optical-pm-edfa2-sigpwr-max-tca-state {
       type string;
       description
         "Optical module PM EDFA2 signal power TCA max state";
     }
     leaf fpc-optical-pm-edfa2-pump-cur {
       type string;
       description
         "Optical module PM EDFA2 pump current current";
     }
     leaf fpc-optical-pm-edfa2-pump-min {
       type string;
       description
         "Optical module PM EDFA2 pump current min";
     }
     leaf fpc-optical-pm-edfa2-pump-max {
       type string;
       description
         "Optical module PM EDFA2 pump current max";
     }
     leaf fpc-optical-pm-edfa2-pump-avg {
       type string;
       description
         "Optical module PM EDFA2 pump current avg";
     }
     leaf fpc-optical-pm-edfa2-pump-min-tca-th {
       type string;
       description
         "Optical module PM EDFA2 pump current TCA min threshold";
     }
     leaf fpc-optical-pm-edfa2-pump-max-tca-th {
       type string;
       description
         "Optical module PM EDFA2 pump current TCA max threshold";
     }
     leaf fpc-optical-pm-edfa2-pump-min-tca-en {
       type string;
       description
         "Optical module PM EDFA2 pump current TCA min enable";
     }
     leaf fpc-optical-pm-edfa2-pump-max-tca-en {
       type string;
       description
         "Optical module PM EDFA2 pump current TCA max enable";
     }
     leaf fpc-optical-pm-edfa2-pump-min-tca-state {
       type string;
       description
         "Optical module PM EDFA2 pump current TCA min state";
     }
     leaf fpc-optical-pm-edfa2-pump-max-tca-state {
       type string;
       description
         "Optical module PM EDFA2 pump current TCA max state";
     }
     leaf fpc-optical-pm-powermon-awg-cur {
       type string;
       description
         "Optical module PM power monitor AWG port current";
     }
     leaf fpc-optical-pm-powermon-awg-min {
       type string;
       description
         "Optical module PM power monitor AWG port min";
     }
     leaf fpc-optical-pm-powermon-awg-max {
       type string;
       description
         "Optical module PM power monitor AWG port max";
     }
     leaf fpc-optical-pm-powermon-awg-avg {
       type string;
       description
         "Optical module PM power monitor AWG port avg";
     }
     leaf fpc-optical-pm-powermon-awg-min-tca-th {
       type string;
       description
         "Optical module PM power monitor AWG port TCA min threshold";
     }
     leaf fpc-optical-pm-powermon-awg-max-tca-th {
       type string;
       description
         "Optical module PM power monitor AWG port TCA max threshold";
     }
     leaf fpc-optical-pm-powermon-awg-min-tca-en {
       type string;
       description
         "Optical module PM power monitor AWG port TCA min enable";
     }
     leaf fpc-optical-pm-powermon-awg-max-tca-en {
       type string;
       description
         "Optical module PM power monitor AWG port TCA max enable";
     }
     leaf fpc-optical-pm-powermon-awg-min-tca-state {
       type string;
       description
         "Optical module PM power monitor AWG port TCA min state";
     }
     leaf fpc-optical-pm-powermon-awg-max-tca-state {
       type string;
       description
         "Optical module PM power monitor AWG port TCA max state";
     }
     leaf fpc-optical-pm-powermon-expin-cur {
       type string;
       description
         "Optical module PM power monitor Express In port current";
     }
     leaf fpc-optical-pm-powermon-expin-min {
       type string;
       description
         "Optical module PM power monitor Express In port min";
     }
     leaf fpc-optical-pm-powermon-expin-max {
       type string;
       description
         "Optical module PM power monitor Express In port max";
     }
     leaf fpc-optical-pm-powermon-expin-avg {
       type string;
       description
         "Optical module PM power monitor Express In port avg";
     }
     leaf fpc-optical-pm-powermon-expin-min-tca-th {
       type string;
       description
         "Optical module PM power monitor Express In port TCA min threshold";
     }
     leaf fpc-optical-pm-powermon-expin-max-tca-th {
       type string;
       description
         "Optical module PM power monitor Express In port TCA max threshold";
     }
     leaf fpc-optical-pm-powermon-expin-min-tca-en {
       type string;
       description
         "Optical module PM power monitor Express In port TCA min enable";
     }
     leaf fpc-optical-pm-powermon-expin-max-tca-en {
       type string;
       description
         "Optical module PM power monitor Express In port TCA max enable";
     }
     leaf fpc-optical-pm-powermon-expin-min-tca-state {
       type string;
       description
         "Optical module PM power monitor Express In port TCA min state";
     }
     leaf fpc-optical-pm-powermon-expin-max-tca-state {
       type string;
       description
         "Optical module PM power monitor Express In port TCA max state";
     }
     leaf fpc-optical-channel-lout {
       type string;
       description
         "Optical module OCM channel LOUT";
     }
     leaf fpc-optical-pm-ocm-lout-min {
       type string;
       description
         "Optical module OCM channel 0 min power";
     }
     leaf fpc-optical-pm-ocm-lout-max {
       type string;
       description
         "Optical module OCM channel 0 max power";
     }
     leaf fpc-optical-pm-ocm-lout-avg {
       type string;
       description
         "Optical module OCM channel 0 avg power";
     }
     leaf fpc-optical-pm-ocm-lout-min-tca-th {
       type string;
       description
         "Optical module OCM channel 0 min TCA threshold";
     }
     leaf fpc-optical-pm-ocm-lout-max-tca-th {
       type string;
       description
         "Optical module OCM channel 0 max TCA threshold";
     }
     leaf fpc-optical-pm-ocm-lout-min-tca-en {
       type string;
       description
         "Optical module OCM channel 0 min TCA enable";
     }
     leaf fpc-optical-pm-ocm-lout-max-tca-en {
       type string;
       description
         "Optical module OCM channel 0 max TCA enable";
     }
     leaf fpc-optical-pm-ocm-lout-min-tca-state {
       type string;
       description
         "Optical module OCM channel 0 min TCA state";
     }
     leaf fpc-optical-pm-ocm-lout-max-tca-state {
       type string;
       description
         "Optical module OCM channel 0 max TCA state";
     }
     leaf fpc-optical-topology-express-in-state {
       type string;
       description
         "Optical module topology state";
     }
     leaf fpc-optical-topology-express-in-connected-to {
       type string;
       description
         "Optical module topology state";
     }
     leaf fpc-optical-topology-expansion-state {
       type string;
       description
         "Optical module topology state";
     }
     leaf fpc-optical-topology-expansion-connected-to {
       type string;
       description
         "Optical module topology connected-to";
     }
     leaf fpc-optical-topology-wavelength-state {
       type string;
       description
         "Optical module topology state";
     }
     leaf fpc-optical-topology-wavelength-connected-to {
       type string;
       description
         "Optical module topology state";
     }
     leaf fpc-optical-amplifier-topology-name {
       type string;
       description
         "Optical module amplifier topology name";
     }
     leaf fpc-optical-amplifier-topology-ipaddr {
       type string;
       description
         "Optical module amplifier topology ip address";
     }
     leaf fpc-optical-amplifier-topology-reachable {
       type string;
       description
         "Optical module amplifier topology reachability";
     }
     leaf fpc-optical-amplifier-topology-connected-to {
       type string;
       description
         "Optical module amplifier topology connected-to";
     }
     leaf fpc-optical-ila-summary-ila-num {
       type string;
       description
         "Optical module ila summary ila number";
     }
     leaf fpc-optical-ila-summary-ila-name {
       type string;
       description
         "Optical module ila summary ila name";
     }
     leaf fpc-optical-ila-summary-position {
       type string;
       description
         "Optical module ila summary ila position";
     }
     leaf fpc-optical-ila-summary-ip-address {
       type string;
       description
         "Optical module ila summary ila ip address";
     }
     leaf fpc-optical-ila-summary-mfg-name {
       type string;
       description
         "Optical module ila summary ila manufactory name";
     }
     leaf fpc-optical-ila-summary-mfg-date {
       type string;
       description
         "Optical module ila summary ila manufactory date";
     }
     leaf fpc-optical-ila-summary-part-num {
       type string;
       description
         "Optical module ila summary ila part number";
     }
     leaf fpc-optical-ila-summary-serial-num {
       type string;
       description
         "Optical module ila summary ila serial number";
     }
     leaf fpc-optical-ila-summary-calibration-date {
       type string;
       description
         "Optical module ila summary ila calibration date";
     }
     leaf fpc-optical-ila-summary-firmware-ver {
       type string;
       description
         "Optical module ila summary ila firmware version";
     }
     leaf fpc-optical-ila-summary-hardware-ver {
       type string;
       description
         "Optical module ila summary ila hardware version";
     }
     leaf fpc-optical-ila-summary-fpga-ver {
       type string;
       description
         "Optical module ila summary ila fpga version";
     }
     leaf fpc-optical-ila-summary-x86cpld-ver {
       type string;
       description
         "Optical module ila summary ila x86cpld version";
     }
     leaf fpc-optical-ila-summary-board-cpld-ver {
       type string;
       description
         "Optical module ila summary ila board cpld version";
     }
     leaf fpc-optical-ila-summary-system-date {
       type string;
       description
         "Optical module ila summary ila system date";
     }
     leaf fpc-optical-ila-summary-system-time {
       type string;
       description
         "Optical module ila summary system time";
     }
     leaf fpc-optical-ila-summary-up-time {
       type string;
       description
         "Optical module ila summary ila up time";
     }
     leaf fpc-optical-ila-summary-ipv4-info {
       type string;
       description
         "Optical module ila summary ipv4 address/mask/gateway";
     }
     leaf fpc-optical-ila-summary-mac-address {
       type string;
       description
         "Optical module ila summary ila MAC address";
     }
     leaf fpc-optical-ila-summary-board-temp {
       type string;
       description
         "Optical module ila summary board temperature";
     }
     leaf fpc-optical-ila-summary-temp-thre {
       type string;
       description
         "Optical module ila summary temperature threshold";
     }
     leaf fpc-optical-ila-summary-pwr-fan-plug-status {
       type string;
       description
         "Optical module ila summary power fan plug status";
     }
     leaf fpc-optical-ila-summary-fan-speed {
       type string;
       description
         "Optical module ila summary fan speed";
     }
     leaf fpc-optical-ila-summary-system-mode {
       type string;
       description
         "Optical module ila summary system mode";
     }
     leaf fpc-optical-ila-summary-firmware-upgrade-status {
       type string;
       description
         "Optical module ila summary firmware upgrade status";
     }
     leaf fpc-optical-ila-voa-info {
       type string;
       description
         "Optical module ila voa information";
     }
     leaf fpc-optical-ila-voa-index {
       type string;
       description
         "Optical module ila voa index";
     }
     leaf fpc-optical-ila-voa-attenuation {
       type string;
       description
         "Optical module ila voa index";
     }
     leaf fpc-optical-ila-osc-info {
       type string;
       description
         "Optical module ila osc information";
     }
     leaf fpc-optical-ila-osc-index {
       type string;
       description
         "Optical module ila osc index";
     }
     leaf fpc-optical-ila-osc-mfg-node {
       type string;
       description
         "Optical ila OSC manufacture node";
     }
     leaf fpc-optical-ila-osc-enable {
       type string;
       description
         "Optical ila OSC enable";
     }
     leaf fpc-optical-ila-osc-add-power-value {
       type string;
       description
         "Optical ila OSC add power value";
     }
     leaf fpc-optical-ila-osc-drop-power-value {
       type string;
       description
         "Optical ila OSC drop power value";
     }
     leaf fpc-optical-ila-osc-add-los-thr {
       type string;
       description
         "Optical ila OSC add los threshold";
     }
     leaf fpc-optical-ila-osc-drop-los-thr {
       type string;
       description
         "Optical ila OSC drop los threshold";
     }
     leaf fpc-optical-ila-alarm-board-temp-abnormal {
       type string;
       description
         "Optical ila alarm board temperatur abnormal";
     }
     leaf fpc-optical-ila-alarm-communication-abnormal {
       type string;
       description
         "Optical ila alarm communication abnormal";
     }
     leaf fpc-optical-ila-alarm-fan0-online-abnormal {
       type string;
       description
         "Optical ila alarm fan0 online abnormal";
     }
     leaf fpc-optical-ila-alarm-fan1-online-abnormal {
       type string;
       description
         "Optical ila alarm fan1 online abnormal";
     }
     leaf fpc-optical-ila-alarm-fan2-online-abnormal {
       type string;
       description
         "Optical ila alarm fan2 online abnormal";
     }
     leaf fpc-optical-ila-alarm-fan0-speed-abnormal {
       type string;
       description
         "Optical ila alarm fan0 speed abnormal";
     }
     leaf fpc-optical-ila-alarm-fan1-speed-abnormal {
       type string;
       description
         "Optical ila alarm fan1 speed abnormal";
     }
     leaf fpc-optical-ila-alarm-fan2-speed-abnormal {
       type string;
       description
         "Optical ila alarm fan2 speed abnormal";
     }
     leaf fpc-optical-ila-alarm-software-version-abnormal {
       type string;
       description
         "Optical ila alarm software version abnormal";
     }
     leaf fpc-optical-ila-alarm-ac-power-abnormal {
       type string;
       description
         "Optical ila alarm ac power abnormal";
     }
     leaf fpc-optical-ila-alarm-dc-power-abnormal {
       type string;
       description
         "Optical ila alarm dc power abnormal";
     }
     leaf fpc-optical-ila-alarm-table-err {
       type string;
       description
         "Optical ila alarm table error";
     }
     leaf fpc-optical-ila-alarm-edfa-ab-case-temp {
       type string;
       description
         "Optical ila alarm edfa ab case temperature";
     }
     leaf fpc-optical-ila-alarm-edfa-ab-rfl {
       type string;
       description
         "Optical ila alarm edfa ab RFL";
     }
     leaf fpc-optical-ila-alarm-edfa-ab-oop {
       type string;
       description
         "Optical ila alarm edfa ab OOP";
     }
     leaf fpc-optical-ila-alarm-edfa-ab-oog {
       type string;
       description
         "Optical ila alarm edfa ab OOG";
     }
     leaf fpc-optical-ila-alarm-edfa-ab-pump0-eol {
       type string;
       description
         "Optical ila alarm edfa ab pump 0 EOL";
     }
     leaf fpc-optical-ila-alarm-edfa-ab-pump1-eol {
       type string;
       description
         "Optical ila alarm edfa ab pump 1 EOL";
     }
     leaf fpc-optical-ila-alarm-edfa-ab-pump0-temp-abnormal {
       type string;
       description
         "Optical ila alarm edfa ab pump 0 temp abmornal";
     }
     leaf fpc-optical-ila-alarm-edfa-ab-pump1-temp-abnormal {
       type string;
       description
         "Optical ila alarm edfa ab pump 1 temp abmornal";
     }
     leaf fpc-optical-ila-alarm-edfa-ab-input-los {
       type string;
       description
         "Optical ila alarm edfa ab input LOS";
     }
     leaf fpc-optical-ila-alarm-edfa-ab-output-alarm {
       type string;
       description
         "Optical ila alarm edfa ab output alarm";
     }
     leaf fpc-optical-ila-alarm-edfa-ab-cali-tbl-err {
       type string;
       description
         "Optical ila alarm edfa ab cali table error";
     }
     leaf fpc-optical-ila-alarm-edfa-ba-case-temp {
       type string;
       description
         "Optical ila alarm edfa ba case temperature";
     }
     leaf fpc-optical-ila-alarm-edfa-ba-rfl {
       type string;
       description
         "Optical ila alarm edfa ba RFL";
     }
     leaf fpc-optical-ila-alarm-edfa-ba-oop {
       type string;
       description
         "Optical ila alarm edfa ba OOP";
     }
     leaf fpc-optical-ila-alarm-edfa-ba-oog {
       type string;
       description
         "Optical ila alarm edfa ba OOG";
     }
     leaf fpc-optical-ila-alarm-edfa-ba-pump0-eol {
       type string;
       description
         "Optical ila alarm edfa ba pump 0 EOL";
     }
     leaf fpc-optical-ila-alarm-edfa-ba-pump1-eol {
       type string;
       description
         "Optical ila alarm edfa ba pump 1 EOL";
     }
     leaf fpc-optical-ila-alarm-edfa-ba-pump0-temp-abnormal {
       type string;
       description
         "Optical ila alarm edfa ba pump 0 temp abmornal";
     }
     leaf fpc-optical-ila-alarm-edfa-ba-pump1-temp-abnormal {
       type string;
       description
         "Optical ila alarm edfa ba pump 1 temp abmornal";
     }
     leaf fpc-optical-ila-alarm-edfa-ba-input-los {
       type string;
       description
         "Optical ila alarm edfa ba input LOS";
     }
     leaf fpc-optical-ila-alarm-edfa-ba-output-alarm {
       type string;
       description
         "Optical ila alarm edfa ba output alarm";
     }
     leaf fpc-optical-ila-alarm-edfa-ba-cali-tbl-err {
       type string;
       description
         "Optical ila alarm edfa ba cali table error";
     }
     leaf fpc-optical-ila-alarm-osc-a-add-power-alarm {
       type string;
       description
         "Optical ila alarm osc a add power alarm";
     }
     leaf fpc-optical-ila-alarm-osc-a-drop-power-alarm {
       type string;
       description
         "Optical ila alarm osc a drop power alarm";
     }
     leaf fpc-optical-ila-alarm-osc-b-add-power-alarm {
       type string;
       description
         "Optical ila alarm osc b add power alarm";
     }
     leaf fpc-optical-ila-alarm-osc-b-drop-power-alarm {
       type string;
       description
         "Optical ila alarm osc b drop power alarm";
     }
   }
   grouping global-pfe-id-information-block {
     list header-info-line {
       leaf header-info {
         type string;
       }
     }
     list fpc-global-pfe-id-info-line {
       leaf slot {
         type int32;
       }
       leaf global-pfe-id-info {
         type string;
       }
     }
   }
   grouping adc-information-block {
     list adc {
       leaf slot {
         type int32;
       }
       leaf state {
         type string;
         description
           "Status of the component";
       }
       leaf temperature {
         type string;
         description
           "Temperature of the item";
       }
       leaf start-time {
         type string;
         description
           "Time this component was started";
       }
       leaf up-time {
         type string;
         description
           "Length of time this component has been operational";
       }
       leaf comment {
         type string;
       }
       leaf use-cli-info {
         type string;
       }
       leaf gnf-id {
         type string;
       }
     }
   }
   grouping spmb-information-block {
     list spmb {
       leaf slot {
         type int32;
       }
       leaf state {
         type string;
         description
           "Status of the component";
       }
       leaf cpu-total {
         type int32;
         description
           "Percentage of CPU utilized";
       }
       leaf cpu-interrupt {
         type int32;
         description
           "Percentage of CPU utilized by interrupt processing";
       }
       leaf memory-heap-utilization {
         type int32;
         description
           "Percentage of heap memory utilized";
       }
       leaf memory-buffer-utilization {
         type int32;
         description
           "Percentage of buffer memory utilized";
       }
       leaf start-time {
         type string;
         description
           "Time this component was started";
       }
       leaf up-time {
         type string;
         description
           "Length of time this component has been operational";
       }
     }
   }
   grouping sib-information-block {
     leaf use-cli-info {
       type string;
     }
     container sib {
       leaf slot {
         type int32;
       }
       leaf state {
         type string;
         description
           "Status of the component";
       }
       leaf link-error {
         type string;
         description
           "Link error count";
       }
       leaf destination-error {
         type string;
         description
           "Destination error count";
       }
       leaf up-time {
         type string;
         description
           "Length of time this component has been operational";
       }
       leaf comment {
         type string;
       }
       leaf ok-led {
         type empty;
         description
           "OK LED is lit";
       }
       leaf fail-led {
         type empty;
         description
           "Fail LED is lit";
       }
       leaf active-led {
         type empty;
         description
           "Active LED is lit";
       }
       leaf sib-cable-errors {
         type string;
         description
           "SIB cable errors";
       }
       leaf slot-type {
         type string;
       }
       leaf sib-type {
         type string;
       }
       leaf sib-link-state {
         type string;
         description
           "SIB fabric link state";
       }
       leaf sib-link-errors {
         type string;
         description
           "SIB fabric link errors";
       }
       leaf temperature {
         type string;
         description
           "Temperature of the item";
       }
       leaf start-time {
         type string;
         description
           "Time this component was started";
       }
       leaf sib-errors {
         type string;
         description
           "SIB errors";
       }
     }
   }
   grouping spmb-error-information-block {
     list spmb {
       leaf slot {
         type int32;
       }
       leaf minor-level-occured {
         type uint32;
       }
       leaf minor-level-cleared {
         type uint32;
       }
       leaf minor-level-threshold {
         type uint32;
       }
       leaf minor-level-action-taken {
         type uint32;
       }
       leaf minor-level-action {
         type string;
       }
       leaf major-level-occured {
         type uint32;
       }
       leaf major-level-cleared {
         type uint32;
       }
       leaf major-level-threshold {
         type uint32;
       }
       leaf major-level-action-taken {
         type uint32;
       }
       leaf major-level-action {
         type string;
       }
       leaf fatal-level-occured {
         type uint32;
       }
       leaf fatal-level-cleared {
         type uint32;
       }
       leaf fatal-level-threshold {
         type uint32;
       }
       leaf fatal-level-action-taken {
         type uint32;
       }
       leaf fatal-level-action {
         type string;
       }
     }
   }
   grouping fru-information-block {
     container fru {
       leaf slot {
         type int32;
       }
       leaf state {
         type string;
         description
           "Status of the component";
       }
       leaf up-time {
         type string;
         description
           "Length of time this component has been operational";
       }
       leaf comment {
         type string;
       }
       list error-module {
         container device-entry {
           leaf error-timestamp {
             type int32;
             description
               "Error Timestamp";
           }
         }
       }
     }
   }
   grouping chassis-lcc-mode-information-block {
     container lcc-mode-information {
       leaf slot {
         type int32;
       }
       leaf lcc-mode {
         type string;
         description
           "LCC mode";
       }
     }
   }
   grouping psd-information-block {
     container psd {
       leaf slot {
         type int32;
       }
       leaf description {
         type string;
         description
           "Description of this component";
       }
       leaf state {
         type string;
         description
           "Status of the component";
       }
       leaf up-time {
         type string;
         description
           "Length of time this component has been operational";
       }
       leaf comment {
         type string;
       }
     }
   }
   grouping gnf-information-block {
     container gnf {
       leaf slot {
         type int32;
       }
       leaf description {
         type string;
         description
           "Description of this component";
       }
       leaf state {
         type string;
         description
           "Status of the component";
       }
       leaf up-time {
         type string;
         description
           "Length of time this component has been operational";
       }
       leaf comment {
         type string;
       }
     }
   }
   grouping gnf-fpcs-information-block {
     container gnf-fpc {
       leaf slot {
         type int32;
       }
       leaf gnf-fpcs {
         type string;
       }
     }
   }
   grouping gnf-description-block {
     container gnf-desc-tag {
       leaf gnf-slot {
         type int32;
       }
       leaf gnf-desc {
         type string;
       }
       leaf gnf-state {
         type string;
       }
       leaf gnf-fpcs {
         type string;
       }
       leaf gnf-slcs {
         type string;
       }
       leaf gnf-fpcs-online {
         type string;
       }
       leaf gnf-slcs-online {
         type string;
       }
       leaf bsys-name {
         type string;
       }
       leaf bsys-sw {
         type string;
       }
       leaf gnf-sw {
         type string;
       }
       leaf gnf-chassis {
         type string;
       }
       leaf bsys-master-re {
         type string;
       }
       leaf up-time {
         type string;
         description
           "Length of time this component has been operational";
       }
       container gnf-re-info {
         leaf gnf-re-slot {
           type int32;
         }
         leaf gnf-re-state {
           type string;
         }
         leaf gnf-re-model {
           type string;
         }
         leaf gnf-re-host-name {
           type string;
         }
       }
     }
   }
   grouping afs-information-block {
     container gnf-af {
       leaf slot {
         type int32;
       }
       leaf af-name {
         type string;
       }
       leaf peer-af-name {
         type string;
       }
       leaf peer-slot {
         type uint32;
       }
     }
   }
   grouping jnu-satellites-information-block {
     list satellite-information {
       leaf satellite-ip {
         type string;
         description
           "Satellite name or ip";
       }
       leaf alive {
         type string;
         description
           "Ping";
       }
       leaf satellite-model {
         type string;
         description
           "Satellite model";
       }
       leaf satellite-version {
         type string;
         description
           "Junos version";
       }
     }
   }
   grouping jnu-role-information-block {
     leaf role {
       type string;
       description
         "JNU Role";
     }
   }
   grouping chassis-fabric-mesh-topo-information-block {
     container mesh-feb-asic {
       leaf mtopo-header-msg {
         type string;
       }
       leaf mslot {
         type string;
       }
       leaf masic {
         type string;
       }
       leaf mcore {
         type string;
       }
     }
     container mesh-topo {
       leaf mesh-topo-link-in {
         type string;
       }
       leaf mesh-topo-link-in-state {
         type string;
       }
       leaf mesh-topo-link-out {
         type string;
       }
       leaf mesh-topo-link-out-state {
         type string;
       }
     }
   }
   grouping chassis-fabric-mesh-feb-information-block {
     container mesh-feb {
       leaf fslot {
         type string;
       }
       leaf funit {
         type string;
       }
       leaf fasic {
         type string;
       }
       leaf fcore {
         type string;
       }
       leaf fplane {
         type string;
       }
       leaf flink-state {
         type string;
       }
     }
   }
   grouping fm-fpc-state-information-block {
     list fm-fpc-ln {
       list fm-pfe-ln {
         list fm-sib-ln {
           leaf sib-slot {
             type int32;
             description
               "SIB slot number";
           }
           leaf sib-core {
             type int32;
           }
           leaf sib-plane {
             type int32;
           }
           leaf pfe-core-link-state {
             type string;
           }
           leaf sib-fm-state {
             type string;
           }
           leaf sib-asic {
             type int32;
           }
           leaf ln-name {
             type string;
           }
         }
         leaf pfe-slot {
           type int32;
         }
         container fm-plane-ln {
           leaf plane-slot {
             type uint32;
           }
           leaf plane-fm-state {
             type string;
           }
         }
         container fm-link-ln {
           leaf link {
             type uint32;
           }
           leaf link-fm-state {
             type string;
           }
         }
       }
       leaf slot {
         type int32;
       }
     }
     list fm-fpc-ln1 {
       leaf fpc-slot1 {
         type int32;
       }
       list fm-pfe-ln1 {
         leaf pfe-slot1 {
           type int32;
         }
         list fm-pfe-core-ln {
           leaf sib-slot {
             type int32;
             description
               "SIB slot number";
           }
           leaf sib-core {
             type int32;
           }
           leaf sib-plane {
             type int32;
           }
           leaf pfe-core-link-state {
             type string;
           }
           leaf sib-asic {
             type int32;
           }
           leaf ln-name {
             type string;
           }
         }
         list fm-pfe-core-ln-extended {
           leaf sib-slot {
             type int32;
             description
               "SIB slot number";
           }
           leaf sib-core {
             type int32;
           }
           leaf sib-asic {
             type int32;
           }
           leaf sib-plane {
             type int32;
           }
           leaf pfe-core-link-state {
             type string;
           }
           leaf ln-name {
             type string;
           }
         }
       }
     }
     leaf comment {
       type string;
     }
   }
   grouping fm-bandwidth-degradation-block {
     container fm-bandwidth-degradation-line {
       leaf slot {
         type int32;
       }
       leaf state {
         type string;
         description
           "Status of the component";
       }
       leaf comment {
         type string;
       }
       leaf planes-for-line-rate {
         type uint32;
       }
       leaf configured-degradation {
         type string;
       }
       leaf current-degradation {
         type string;
       }
       leaf time-degrad-triggered {
         type string;
       }
       leaf sublc-slot {
         type string;
       }
     }
   }
   grouping fm-fabric-destinations-state-block {
     list fm-dest-fpc-ln {
       description
         "Fabric destinations state for fpc";
       leaf fm-slot {
         type uint32;
         description
           "FPC slot";
       }
       list fm-dest-pfe-ln {
         description
           "Fabric destinations state for pfe";
         leaf fm-pfe-slot {
           type uint32;
           description
             "PFE slot";
         }
         list fm-dest-plane-ln {
           description
             "Fabric destinations state for plane";
           leaf fm-plane-slot {
             type uint32;
             description
               "Plane slot";
           }
           container fm-dest-fabric-destinations-ln {
             leaf fm-fabric-destination-status {
               type string;
               description
                 "Destinations status information";
             }
           }
         }
       }
     }
   }
   grouping fm-plane-location-information-block {
     container fm-plane-location {
       leaf plane {
         type string;
         description
           "Plane information";
       }
       leaf sib-f13-slot {
         type string;
         description
           "F13 SIB information";
       }
       leaf sib-f2-slot {
         type string;
         description
           "F2 SIB information";
       }
       leaf sib-l-slot {
         type string;
         description
           "LCC SIB information";
       }
       leaf plane-slot {
         type uint32;
       }
       leaf cb-slot {
         type uint32;
       }
       leaf sfb-plane {
         type uint32;
       }
       leaf sfb-slot {
         type uint32;
       }
       leaf sib-slot {
         type int32;
         description
           "SIB slot number";
       }
       leaf planes {
         type string;
         description
           "Planes associated with the SIB";
       }
       leaf plane-number {
         type uint32;
         description
           "Planes number";
       }
       leaf fab-fru-slot {
         type int32;
         description
           "Fabric FRU slot number";
       }
     }
   }
   grouping fm-topology-block {
     container fm-topo-link-src-des {
       leaf fm-topo-link-msg {
         type string;
       }
       container fm-topo-link-src {
         leaf fm-topo-link-src-in {
           type string;
         }
         leaf fm-topo-link-src-out {
           type string;
         }
         leaf hsl2-state-src {
           type string;
         }
       }
       container fm-topo-link-des {
         leaf fm-topo-link-des-in {
           type string;
         }
         leaf fm-topo-link-des-out {
           type string;
         }
         leaf hsl2-state-des {
           type string;
         }
       }
     }
     container fm-topo-link-io {
       leaf fm-topo-link-header-message {
         type string;
         description
           "Header messages for this command";
       }
       container fm-topo-link-sib {
         leaf fm-topo-link-sibnum {
           type int32;
           description
             "SIB number";
         }
         leaf fm-topo-link-sib-message {
           type string;
           description
             "SIB messages";
         }
         container fm-topo-link-fchip {
           leaf fm-topo-link-fchipnum {
             type int32;
             description
               "FCHIP number";
           }
           container fm-topo-link-fcore {
             leaf fm-topo-link-fcorenum {
               type int32;
               description
                 "FCORE number";
             }
             leaf fm-topo-link-detail-message {
               type string;
               description
                 "Link detail messages";
             }
             container fm-topo-link-source {
               leaf fm-topo-link-in {
                 type string;
                 description
                   "In-link name";
               }
               leaf link-state-source {
                 type string;
                 description
                   "In-link state";
               }
             }
             container fm-topo-link-destination {
               leaf fm-topo-link-out {
                 type string;
                 description
                   "Out-link name";
               }
               leaf link-state-destination {
                 type string;
                 description
                   "Out-link state";
               }
             }
             list fm-topo-link-entry {
               description
                 "Link entry";
               container fm-topo-link-source {
                 description
                   "Source link detail";
                 leaf fm-topo-link-in {
                   type string;
                   description
                     "In-link name";
                 }
                 leaf link-state-source {
                   type string;
                   description
                     "In-link state";
                 }
               }
               container fm-topo-link-destination {
                 description
                   "Destination link detail";
                 leaf fm-topo-link-out {
                   type string;
                   description
                     "Out-link name";
                 }
                 leaf link-state-destination {
                   type string;
                   description
                     "Out-link state";
                 }
               }
             }
           }
         }
       }
     }
     container fm-topo-link {
       leaf fm-topo-sib {
         type string;
         description
           "SIB information";
       }
       leaf fm-topo-dbl-line {
         type string;
         description
           "Under line of the header";
       }
       leaf fm-topo-fail-msg {
         type string;
         description
           "Details of the failure";
       }
       container fm-topo-link-details {
         leaf fm-topo-link-type {
           type string;
           description
             "Type of the link";
         }
         leaf fm-topo-sib-source {
           type string;
           description
             "Source sib";
         }
         leaf fm-topo-sib-dest {
           type string;
           description
             "Destination sib";
         }
         leaf source-pfe-xc-link {
           type string;
           description
             "Source pfe link";
         }
         leaf dest-pfe-xc-link {
           type string;
           description
             "Destination pfe link";
         }
         leaf vcsel-status {
           type string;
           description
             "VCSEL status";
         }
         leaf hsl2-channel {
           type string;
           description
             "HSL2 channel number";
         }
         leaf hsl2-status {
           type string;
           description
             "HSL2 channel status";
         }
         container fm-topo-link-in-out {
           leaf fm-topo-link-type {
             type string;
             description
               "Type of the link";
           }
         }
         container fm-topo-link-details-head-lcc {
           leaf fm-topo-sib-source {
             type string;
             description
               "Source sib";
           }
           leaf fm-topo-sib-dest {
             type string;
             description
               "Destination sib";
           }
         }
         container fm-topo-link-details-lcc {
           leaf source-pfe-xc-link {
             type string;
             description
               "Source pfe link";
           }
           leaf dest-pfe-xc-link {
             type string;
             description
               "Destination pfe link";
           }
           leaf vcsel-status {
             type string;
             description
               "VCSEL status";
           }
           leaf hsl2-channel {
             type string;
             description
               "HSL2 channel number";
           }
           leaf hsl2-status {
             type string;
             description
               "HSL2 channel status";
           }
         }
         container fm-topo-link-details-head-sfc {
           leaf fm-topo-sib-source {
             type string;
             description
               "Source sib";
           }
           leaf fm-topo-sib-dest {
             type string;
             description
               "Destination sib";
           }
         }
         container fm-topo-link-details-sfc {
           leaf source-pfe-xc-link {
             type string;
             description
               "Source pfe link";
           }
           leaf dest-pfe-xc-link {
             type string;
             description
               "Destination pfe link";
           }
           leaf vcsel-status {
             type string;
             description
               "VCSEL status";
           }
           leaf hsl2-channel {
             type string;
             description
               "HSL2 channel number";
           }
           leaf hsl2-status {
             type string;
             description
               "HSL2 channel status";
           }
         }
       }
       container fm-topo-link-information {
         leaf fm-topo-sib {
           type string;
           description
             "SIB information";
         }
         leaf fm-topo-dbl-line {
           type string;
           description
             "Under line of the header";
         }
         container fm-topo-link-fail {
           leaf fm-topo-sib {
             type string;
             description
               "SIB information";
           }
           leaf fm-topo-fail-msg {
             type string;
             description
               "Details of the failure";
           }
         }
         container fm-topo-link-details {
           leaf fm-topo-link-type {
             type string;
             description
               "Type of the link";
           }
           leaf fm-topo-sib-source {
             type string;
             description
               "Source sib";
           }
           leaf fm-topo-sib-dest {
             type string;
             description
               "Destination sib";
           }
           leaf source-pfe-xc-link {
             type string;
             description
               "Source pfe link";
           }
           leaf dest-pfe-xc-link {
             type string;
             description
               "Destination pfe link";
           }
           leaf vcsel-status {
             type string;
             description
               "VCSEL status";
           }
           leaf hsl2-channel {
             type string;
             description
               "HSL2 channel number";
           }
           leaf hsl2-status {
             type string;
             description
               "HSL2 channel status";
           }
           container fm-topo-link-in-out {
             leaf fm-topo-link-type {
               type string;
               description
                 "Type of the link";
             }
           }
           container fm-topo-link-details-head-lcc {
             leaf fm-topo-sib-source {
               type string;
               description
                 "Source sib";
             }
             leaf fm-topo-sib-dest {
               type string;
               description
                 "Destination sib";
             }
           }
           container fm-topo-link-details-lcc {
             leaf source-pfe-xc-link {
               type string;
               description
                 "Source pfe link";
             }
             leaf dest-pfe-xc-link {
               type string;
               description
                 "Destination pfe link";
             }
             leaf vcsel-status {
               type string;
               description
                 "VCSEL status";
             }
             leaf hsl2-channel {
               type string;
               description
                 "HSL2 channel number";
             }
             leaf hsl2-status {
               type string;
               description
                 "HSL2 channel status";
             }
           }
           container fm-topo-link-details-head-sfc {
             leaf fm-topo-sib-source {
               type string;
               description
                 "Source sib";
             }
             leaf fm-topo-sib-dest {
               type string;
               description
                 "Destination sib";
             }
           }
           container fm-topo-link-details-sfc {
             leaf source-pfe-xc-link {
               type string;
               description
                 "Source pfe link";
             }
             leaf dest-pfe-xc-link {
               type string;
               description
                 "Destination pfe link";
             }
             leaf vcsel-status {
               type string;
               description
                 "VCSEL status";
             }
             leaf hsl2-channel {
               type string;
               description
                 "HSL2 channel number";
             }
             leaf hsl2-status {
               type string;
               description
                 "HSL2 channel status";
             }
           }
         }
       }
       container fm-topo-link-information-sgl {
         container fm-topo-link-fail-sgl {
           leaf fm-topo-sib {
             type string;
             description
               "SIB information";
           }
           leaf fm-topo-fail-msg {
             type string;
             description
               "Details of the failure";
           }
         }
         container fm-topo-link-details {
           leaf fm-topo-link-type {
             type string;
             description
               "Type of the link";
           }
           leaf fm-topo-sib-source {
             type string;
             description
               "Source sib";
           }
           leaf fm-topo-sib-dest {
             type string;
             description
               "Destination sib";
           }
           leaf source-pfe-xc-link {
             type string;
             description
               "Source pfe link";
           }
           leaf dest-pfe-xc-link {
             type string;
             description
               "Destination pfe link";
           }
           leaf vcsel-status {
             type string;
             description
               "VCSEL status";
           }
           leaf hsl2-channel {
             type string;
             description
               "HSL2 channel number";
           }
           leaf hsl2-status {
             type string;
             description
               "HSL2 channel status";
           }
           container fm-topo-link-in-out {
             leaf fm-topo-link-type {
               type string;
               description
                 "Type of the link";
             }
           }
           container fm-topo-link-details-head-lcc {
             leaf fm-topo-sib-source {
               type string;
               description
                 "Source sib";
             }
             leaf fm-topo-sib-dest {
               type string;
               description
                 "Destination sib";
             }
           }
           container fm-topo-link-details-lcc {
             leaf source-pfe-xc-link {
               type string;
               description
                 "Source pfe link";
             }
             leaf dest-pfe-xc-link {
               type string;
               description
                 "Destination pfe link";
             }
             leaf vcsel-status {
               type string;
               description
                 "VCSEL status";
             }
             leaf hsl2-channel {
               type string;
               description
                 "HSL2 channel number";
             }
             leaf hsl2-status {
               type string;
               description
                 "HSL2 channel status";
             }
           }
           container fm-topo-link-details-head-sfc {
             leaf fm-topo-sib-source {
               type string;
               description
                 "Source sib";
             }
             leaf fm-topo-sib-dest {
               type string;
               description
                 "Destination sib";
             }
           }
           container fm-topo-link-details-sfc {
             leaf source-pfe-xc-link {
               type string;
               description
                 "Source pfe link";
             }
             leaf dest-pfe-xc-link {
               type string;
               description
                 "Destination pfe link";
             }
             leaf vcsel-status {
               type string;
               description
                 "VCSEL status";
             }
             leaf hsl2-channel {
               type string;
               description
                 "HSL2 channel number";
             }
             leaf hsl2-status {
               type string;
               description
                 "HSL2 channel status";
             }
           }
         }
       }
     }
     container fm-topo-map {
       container fm-topo-map-ln {
         leaf fm-fpc-slot {
           type uint32;
         }
         leaf fm-pfe-slot {
           type uint32;
           description
             "PFE slot";
         }
         leaf fm-cb-slot {
           type uint32;
         }
         leaf port {
           type uint32;
         }
         leaf link-state {
           type string;
         }
       }
     }
     container fm-topo-link-io-b2b {
       leaf fm-topo-link-header-message {
         type string;
         description
           "Header messages for this command";
       }
       container fm-topo-link-fpc {
         leaf fm-topo-link-fpcnum {
           type int32;
           description
             "FPC number";
         }
         leaf fm-topo-link-fpc-message {
           type string;
           description
             "FPC messages";
         }
         container fm-topo-link-fpfe {
           leaf fm-topo-link-fpfenum {
             type int32;
             description
               "FPFE number";
           }
           container fm-topo-link-fcore {
             leaf fm-topo-link-detail-message {
               type string;
               description
                 "Link detail messages";
             }
             list fm-topo-link-entry {
               description
                 "Link entry";
               container fm-topo-link-source {
                 description
                   "Source link detail";
                 leaf fm-topo-link-in {
                   type string;
                   description
                     "In-link name";
                 }
                 leaf link-state-source {
                   type string;
                   description
                     "In-link state";
                 }
               }
               container fm-topo-link-destination {
                 description
                   "Destination link detail";
                 leaf fm-topo-link-out {
                   type string;
                   description
                     "Out-link name";
                 }
                 leaf link-state-destination {
                   type string;
                   description
                     "Out-link state";
                 }
               }
             }
           }
         }
       }
     }
   }
   grouping fm-optical-links-state-information-block {
     container fm-optical-links-state {
       leaf lcc-opt-name {
         type string;
         description
           "Lcc optics name";
       }
       leaf opt-link-state {
         type string;
       }
       leaf sc-opt-name {
         type string;
         description
           "Sc optics name";
       }
       leaf opt-link-state-str {
         type string;
       }
       leaf opt-link-mandatory-str {
         type string;
         description
           "Cable mandatory or non-mandatory";
       }
       leaf cbl-mapped-fpcs {
         type string;
         description
           "Fpcs mapped to this cable";
       }
       leaf cbl-chan-hsl-state {
         type string;
         description
           "Cable chan hsl state";
       }
       leaf cbl-misconn-info {
         type string;
         description
           "Cable Misconnected Info details if cable is misconnected";
       }
     }
   }
   grouping fm-optics-port-information-block {
     container fm-optics-port-info-state {
       leaf optics-sib-name {
         type string;
         description
           "SIB name";
       }
       leaf optics-port {
         type uint32;
         description
           "Port";
       }
       leaf optics-cable-state {
         type string;
         description
           "Cable State";
       }
       leaf optics-cable-type {
         type string;
         description
           "Module Type";
       }
       leaf optics-cbl-fault-reason {
         type string;
         description
           "Optics Fault reason";
       }
       leaf comment {
         type string;
       }
       leaf optics-module-alarm {
         type string;
         description
           "Optics Module Alarms";
       }
       leaf optics-chan-alarm {
         type string;
         description
           "Optics Channel Alarms ";
       }
       leaf optics-vendor-name {
         type string;
         description
           "Optics Vendor Name";
       }
       leaf optics-fw-ver {
         type string;
         description
           "Optics Firmware Version";
       }
       leaf optics-port-tx-rx {
         type string;
         description
           "Tx or Rx side";
       }
       leaf optics-module-alarm-info {
         type string;
         description
           "Optics Module Alarms Info";
       }
       leaf optics-temp-source {
         type string;
         description
           "Temperature monitor source";
       }
       leaf optics-temp {
         type int32;
         description
           "Temperature";
       }
       leaf optics-volt-source {
         type string;
         description
           "Voltage monitor source";
       }
       leaf optics-volt {
         type string;
         description
           "Voltage";
       }
       leaf optics-chan-name {
         type string;
         description
           "Channel name";
       }
       leaf optics-chan-alarm-info {
         type string;
         description
           "Optics Channel Alarms Info";
       }
       leaf optics-chan-bias-current {
         type string;
         description
           "Channel Bias current";
       }
       leaf optics-chan-power {
         type string;
         description
           "Channel optical power";
       }
     }
     leaf optics-header {
       type string;
       description
         "Optics header";
     }
   }
   grouping fm-plane-state-information-block {
     leaf comment {
       type string;
     }
     container fmp-plane {
       leaf slot {
         type int32;
       }
       leaf state {
         type string;
         description
           "Status of the component";
       }
       leaf fru-name {
         type string;
       }
       leaf fru-slot {
         type int32;
         description
           "FRU slot number";
       }
       leaf pfe-slot {
         type int32;
       }
       leaf pfe-link-status {
         type string;
         description
           "PFE link status information";
       }
       leaf lcc-adc-slot {
         type int32;
         description
           "ADC slot number";
       }
       container fru-plane-info {
         leaf fru-name {
           type string;
         }
         leaf fru-slot {
           type int32;
           description
             "FRU slot number";
         }
         container pfe-plane-info {
           leaf pfe-slot {
             type int32;
           }
           leaf pfe-link-status {
             type string;
             description
               "PFE link status information";
           }
         }
       }
       leaf link-error {
         type string;
         description
           "Link error count";
       }
       leaf destination-error {
         type string;
         description
           "Destination error count";
       }
       leaf up-time {
         type string;
         description
           "Length of time this component has been operational";
       }
       leaf plane-cable-errors {
         type string;
         description
           "Number of cable errors in the plane";
       }
       leaf plane-state {
         type string;
         description
           "Plane state information";
       }
       leaf sib-name {
         type string;
         description
           "SIB name";
       }
       leaf sibs-slot {
         type string;
         description
           "Chassis SIB slot number";
       }
       leaf sib-f13-name {
         type string;
         description
           "F13 SIB name";
       }
       leaf f13-slot {
         type int32;
         description
           "F13 slot number";
       }
       leaf even-odd {
         type string;
         description
           "Even or Odd part of SIB F13";
       }
       leaf lcc-slot {
         type int32;
         description
           "LCC slot number";
       }
       leaf sibl-slot {
         type int32;
         description
           "LCC SIB slot number";
       }
       leaf sibl-link-state {
         type string;
         description
           "LCC SIB link state information";
       }
       leaf sgasic-number {
         type int32;
         description
           "SG number on SFC";
       }
       leaf sgasic-port-number {
         type int32;
         description
           "SG port number on SFC";
       }
       leaf sgasic-port-link-state {
         type string;
         description
           "SG port link status on SFC";
       }
       leaf sibs-lcc-pfe-slot {
         type int32;
         description
           "SFC PFE slot number";
       }
       leaf sibs-lcc-pfe-link-state {
         type string;
         description
           "SFC PFE link state information";
       }
       leaf sib-f2-name {
         type string;
         description
           "F2 SIB name";
       }
       leaf sibs2-slot {
         type string;
         description
           "Chassis F2 SIB slot number";
       }
       leaf f2-link-state {
         type string;
         description
           "F2 link state information";
       }
       leaf lcc-sib-link-state {
         type string;
         description
           "LCC SIB link state information";
       }
       leaf lcc-sgasic-number {
         type int32;
         description
           "SG number on LCC";
       }
       leaf lcc-sgasic-port-number {
         type int32;
         description
           "SG port number on LCC";
       }
       leaf lcc-sgasic-port-link-state {
         type string;
         description
           "SG port link status on LCC";
       }
       leaf sibl-lcc-pfe-slot {
         type int32;
         description
           "LCC PFE slot number";
       }
       leaf sibl-lcc-pfe-link-state {
         type string;
         description
           "LCC PFE link state information";
       }
       leaf lcc-fpc-slot {
         type int32;
         description
           "FPC slot number";
       }
       leaf lcc-pfe-slot {
         type int32;
         description
           "PFE slot number";
       }
       leaf lcc-pfe-link-state {
         type string;
         description
           "PFE link state information";
       }
     }
     leaf fabric-header {
       type string;
       description
         "Fabric header";
     }
   }
   grouping fm-state-information-block {
     leaf comment {
       type string;
     }
     container fm-state-item {
       leaf plane-slot {
         type uint32;
       }
       leaf state {
         type string;
         description
           "Status of the component";
       }
       leaf up-time {
         type string;
         description
           "Length of time this component has been operational";
       }
       leaf link-error {
         type string;
         description
           "Link error count";
       }
       leaf link-tf {
         type string;
         description
           "Count of training failure links";
       }
       leaf local-reachability-error {
         type string;
         description
           "Local Reachability error count";
       }
       leaf remote-reachability-error {
         type string;
         description
           "Remote Reachability error count";
       }
     }
   }
   grouping fm-ext-state-information-block {
     leaf comment {
       type string;
     }
     container fm-ext-state-item {
       leaf plane-slot {
         type uint32;
       }
       leaf state {
         type string;
         description
           "Status of the component";
       }
       leaf link-error {
         type string;
         description
           "Link error count";
       }
       leaf link-tf {
         type string;
         description
           "Count of training failure links";
       }
       leaf destination-error {
         type string;
         description
           "Destination error count";
       }
       leaf up-time {
         type string;
         description
           "Length of time this component has been operational";
       }
       leaf local-destination-error {
         type string;
         description
           "Local Destination error count";
       }
       leaf remote-destination-error {
         type string;
         description
           "Remote Destination error count";
       }
     }
   }
   grouping fm-state-legend-block {
     leaf comment {
       type string;
     }
   }
   grouping fm-sib-state-information-block {
     list fms-sib-ln {
       leaf sib-slot {
         type int32;
         description
           "SIB slot number";
       }
       leaf sib-fms-state1 {
         type string;
       }
       list fms-core-ln {
         leaf sib-core {
           type int32;
         }
         leaf sib-plane {
           type int32;
         }
         leaf sib-fms-core-state {
           type string;
         }
         list fms-core-fpc-ln {
           leaf slot {
             type int32;
           }
           list fms-core-pfe-ln {
             leaf pfe-slot {
               type int32;
             }
             leaf fms-core-pfe-link-state {
               type string;
             }
             leaf ln-name {
               type string;
             }
           }
         }
         list fms-core-fpc-ln-extended {
           list fms-core-pfe-ln-extended {
             leaf pfe-slot {
               type int32;
             }
             leaf fms-core-pfe-link-state {
               type string;
             }
             leaf ln-name {
               type string;
             }
           }
           leaf fpc-slot-ext {
             type int32;
           }
         }
         leaf sib-asic {
           type int32;
         }
       }
       leaf sib-fm-state {
         type string;
       }
       list fms-fpc-ln {
         leaf slot {
           type int32;
         }
         list fms-pfe-ln {
           leaf pfe-slot {
             type int32;
           }
           leaf fms-pfe-link-state {
             type string;
           }
         }
       }
       list fms-lcc-ln {
         leaf lcc-slot {
           type int32;
           description
             "LCC slot number";
         }
         leaf fms-lcc-link-state {
           type string;
         }
       }
       container fms-scc-ln {
         leaf fms-scc-link-type {
           type string;
         }
         leaf fms-scc-link-state {
           type string;
         }
       }
     }
     list fms-sib-ln1 {
       leaf sib-slot {
         type int32;
         description
           "SIB slot number";
       }
       leaf sib-fms-state1 {
         type string;
       }
       list fms-core-ln {
         leaf sib-core {
           type int32;
         }
         leaf sib-plane {
           type int32;
         }
         leaf sib-fms-core-state {
           type string;
         }
         list fms-core-fpc-ln {
           leaf slot {
             type int32;
           }
           list fms-core-pfe-ln {
             leaf pfe-slot {
               type int32;
             }
             leaf fms-core-pfe-link-state {
               type string;
             }
             leaf ln-name {
               type string;
             }
           }
         }
         list fms-core-fpc-ln-extended {
           list fms-core-pfe-ln-extended {
             leaf pfe-slot {
               type int32;
             }
             leaf fms-core-pfe-link-state {
               type string;
             }
             leaf ln-name {
               type string;
             }
           }
           leaf fpc-slot-ext {
             type int32;
           }
         }
         leaf sib-asic {
           type int32;
         }
       }
     }
   }
   grouping fm-topo-tracepath-link-block {
     container fm-topo-tracepath-link-output {
       leaf link-tracepath {
         type string;
         description
           "Tracepath Output";
       }
     }
   }
   grouping fm-topo-tracepath-fpc-block {
     container fm-topo-tracepath-fpc-output {
       leaf fpc-tracepath {
         type string;
         description
           "Tracepath Output";
       }
     }
   }
   grouping chassis-fabric-spray-weight-information-block {
     leaf device-id {
       type string;
       description
         "Device ID";
     }
     leaf chassis-type {
       type string;
       description
         "Chassis type";
     }
     list chassis-fabric-spray-weight-card-information {
       leaf card-pos {
         type string;
         description
           "Card position";
       }
       leaf card-slot {
         type uint32;
         description
           "Card slot";
       }
       leaf card-type {
         type string;
         description
           "Card type";
       }
     }
     list chassis-fabric-spray-weight-chip-information {
       leaf chip-type {
         type string;
         description
           "Chip type";
       }
       leaf chip-num {
         type uint32;
         description
           "Chip number";
       }
     }
     list chassis-fabric-spray-weights-on-two-links {
       leaf vpfe-id {
         type uint32;
         description
           "VPFE ID";
       }
       leaf spray-weight0 {
         type uint32;
         description
           "Spray weight";
       }
       leaf spray-weight1 {
         type uint32;
         description
           "Spray weight";
       }
     }
     list chassis-fabric-spray-weights-on-four-links {
       leaf vpfe-id {
         type uint32;
         description
           "VPFE ID";
       }
       leaf spray-weight0 {
         type uint32;
         description
           "Spray weight";
       }
       leaf spray-weight1 {
         type uint32;
         description
           "Spray weight";
       }
       leaf spray-weight2 {
         type uint32;
         description
           "Spray weight";
       }
       leaf spray-weight3 {
         type uint32;
         description
           "Spray weight";
       }
     }
     list chassis-fabric-spray-weights-on-eight-links {
       leaf vpfe-id {
         type uint32;
         description
           "VPFE ID";
       }
       leaf spray-weight0 {
         type uint32;
         description
           "Spray weight";
       }
       leaf spray-weight1 {
         type uint32;
         description
           "Spray weight";
       }
       leaf spray-weight2 {
         type uint32;
         description
           "Spray weight";
       }
       leaf spray-weight3 {
         type uint32;
         description
           "Spray weight";
       }
       leaf spray-weight4 {
         type uint32;
         description
           "Spray weight";
       }
       leaf spray-weight5 {
         type uint32;
         description
           "Spray weight";
       }
       leaf spray-weight6 {
         type uint32;
         description
           "Spray weight";
       }
       leaf spray-weight7 {
         type uint32;
         description
           "Spray weight";
       }
     }
     list chassis-fabric-spray-weights-on-eight-links-value {
       leaf spray-weight0 {
         type uint32;
         description
           "Spray weight";
       }
       leaf spray-weight1 {
         type uint32;
         description
           "Spray weight";
       }
       leaf spray-weight2 {
         type uint32;
         description
           "Spray weight";
       }
       leaf spray-weight3 {
         type uint32;
         description
           "Spray weight";
       }
       leaf spray-weight4 {
         type uint32;
         description
           "Spray weight";
       }
       leaf spray-weight5 {
         type uint32;
         description
           "Spray weight";
       }
       leaf spray-weight6 {
         type uint32;
         description
           "Spray weight";
       }
       leaf spray-weight7 {
         type uint32;
         description
           "Spray weight";
       }
       leaf vpfe-id {
         type uint32;
         description
           "VPFE ID";
       }
     }
     list chassis-fabric-spray-weight-cumulative {
       leaf vpfe-id {
         type uint32;
         description
           "VPFE ID";
       }
       leaf spray-cumulative-weight {
         type uint32;
         description
           "Cumulative spray weight";
       }
       leaf spray-max-links-to-destination {
         type uint32;
         description
           "Maximum number of links to destionation";
       }
       leaf spray-destination-mask {
         type uint32;
         description
           "Destination mask";
       }
     }
     list chassis-fabric-information-internal {
       leaf chassis-id {
         type uint32;
         description
           "Chassis ID";
       }
       leaf min-chip-id {
         type uint32;
         description
           "Minimum chip ID";
       }
       leaf max-chip-id {
         type uint32;
         description
           "Maximum chip ID";
       }
     }
     list chassis-fabric-spray-weight-chip-information-internal {
       leaf chip-id {
         type uint32;
         description
           "Chip ID";
       }
       leaf chip-type {
         type string;
         description
           "Chip type";
       }
     }
   }
   grouping chassis-fabric-information-block {
     leaf device-id {
       type string;
       description
         "Device ID";
     }
     leaf chassis-type {
       type string;
       description
         "Chassis type";
     }
     leaf management-status {
       type string;
       description
         "Management status";
     }
     leaf hw-status {
       type string;
       description
         "Hardware status";
     }
     list chassis-fabric-links-header {
       leaf fm-space-tab {
         type string;
         description
           "Space tab";
       }
     }
     list chassis-fabric-ccpc-incoming-links-header {
       leaf card-detail {
         type string;
         description
           "Card detail";
       }
       leaf card-slot-num {
         type string;
         description
           "Card slot number";
       }
     }
     list chassis-fabric-ccpc-outgoing-links-header {
       leaf card-detail {
         type string;
         description
           "Card detail";
       }
       leaf card-slot-num {
         type string;
         description
           "Card slot number";
       }
     }
     list chassis-fabric-tor-incoming-links-header {
       leaf fm-space-tab {
         type string;
         description
           "Space tab";
       }
     }
     list chassis-fabric-tor-outgoing-links-header {
       leaf fm-space-tab {
         type string;
         description
           "Space tab";
       }
     }
     container chassis-fabric-links {
       list link-by-link-information {
         leaf src-link {
           type string;
           description
             "Source link";
         }
         leaf dst-link {
           type string;
           description
             "Destination link";
         }
         leaf hw-status {
           type string;
           description
             "Hardware status";
         }
       }
     }
     list chassis-fabric-information-internal {
       leaf chassis-id {
         type uint32;
         description
           "Chassis ID";
       }
       leaf min-chip-id {
         type uint32;
         description
           "Minimum chip ID";
       }
       leaf max-chip-id {
         type uint32;
         description
           "Maximum chip ID";
       }
     }
     list chassis-fabric-card-information-internal {
       leaf card-pos {
         type string;
         description
           "Card position";
       }
       leaf card-slot {
         type uint32;
         description
           "Card slot";
       }
       leaf card-type {
         type string;
         description
           "Card type";
       }
       leaf management-status {
         type string;
         description
           "Management status";
       }
       leaf hw-status {
         type string;
         description
           "Hardware status";
       }
       leaf min-chip-id {
         type uint32;
         description
           "Minimum chip ID";
       }
       leaf max-chip-id {
         type uint32;
         description
           "Maximum chip ID";
       }
     }
     list chassis-fabric-chip-information-internal {
       leaf chip-id {
         type uint32;
         description
           "Chip ID";
       }
       leaf chip-type {
         type string;
         description
           "Chip type";
       }
       leaf management-status {
         type string;
         description
           "Management status";
       }
       leaf hw-status {
         type string;
         description
           "Hardware status";
       }
     }
     list chassis-fabric-chip-in-links-internal {
       leaf src-chip {
         type uint32;
         description
           "Source chip";
       }
       leaf src-port {
         type uint32;
         description
           "Source port";
       }
       leaf dst-chip {
         type uint32;
         description
           "Destination chip";
       }
       leaf dst-port {
         type uint32;
         description
           "Destination port";
       }
       leaf management-status {
         type string;
         description
           "Management status";
       }
       leaf hw-status {
         type string;
         description
           "Hardware status";
       }
     }
     list chassis-fabric-chip-out-links-internal {
       leaf src-chip {
         type uint32;
         description
           "Source chip";
       }
       leaf src-port {
         type uint32;
         description
           "Source port";
       }
       leaf dst-chip {
         type uint32;
         description
           "Destination chip";
       }
       leaf dst-port {
         type uint32;
         description
           "Destination port";
       }
       leaf management-status {
         type string;
         description
           "Management status";
       }
       leaf hw-status {
         type string;
         description
           "Hardware status";
       }
     }
     list chassis-fabric-chip-up-links-internal {
       leaf src-chip {
         type uint32;
         description
           "Source chip";
       }
       leaf src-port {
         type uint32;
         description
           "Source port";
       }
       leaf dst-chip {
         type uint32;
         description
           "Destination chip";
       }
       leaf dst-port {
         type uint32;
         description
           "Destination port";
       }
     }
     list chassis-fabric-chip-down-links-internal {
       leaf src-chip {
         type uint32;
         description
           "Source chip";
       }
       leaf src-port {
         type uint32;
         description
           "Source port";
       }
       leaf dst-chip {
         type uint32;
         description
           "Destination chip";
       }
       leaf dst-port {
         type uint32;
         description
           "Destination port";
       }
     }
     list chassis-fabric-chip-error-links-internal {
       leaf src-chip {
         type uint32;
         description
           "Source chip";
       }
       leaf src-port {
         type uint32;
         description
           "Source port";
       }
       leaf dst-chip {
         type uint32;
         description
           "Destination chip";
       }
       leaf dst-port {
         type uint32;
         description
           "Destination port";
       }
     }
   }
   grouping chassis-fabric-information-device-block {
     leaf device-id {
       type string;
       description
         "Device ID";
     }
     leaf chassis-type {
       type string;
       description
         "Chassis type";
     }
     leaf management-status {
       type string;
       description
         "Management status";
     }
     leaf hw-status {
       type string;
       description
         "Hardware status";
     }
     list chassis-fabric-information-internal {
       leaf chassis-id {
         type uint32;
         description
           "Chassis ID";
       }
       leaf min-chip-id {
         type uint32;
         description
           "Minimum chip ID";
       }
       leaf max-chip-id {
         type uint32;
         description
           "Maximum chip ID";
       }
     }
   }
   grouping chassis-fabric-connectivity-information-block {
     list chassis-fabric-device-connectivity {
       leaf device-id {
         type string;
         description
           "Device ID";
       }
       leaf chassis-type {
         type string;
         description
           "Chassis type";
       }
       list chassis-fabric-links-header {
         leaf fm-space-tab {
           type string;
           description
             "Space tab";
         }
       }
       container chassis-fabric-incoming-links {
         list chassis-fabric-ccpc-incoming-links-header {
           leaf card-detail {
             type string;
             description
               "Card detail";
           }
           leaf card-slot-num {
             type string;
             description
               "Card slot number";
           }
         }
         list chassis-fabric-tor-incoming-links-header {
           leaf fm-space-tab {
             type string;
             description
               "Space tab";
           }
         }
         container chassis-fabric-links {
           list link-by-link-information {
             leaf src-link {
               type string;
               description
                 "Source link";
             }
             leaf dst-link {
               type string;
               description
                 "Destination link";
             }
             leaf hw-status {
               type string;
               description
                 "Hardware status";
             }
           }
         }
       }
       container chassis-fabric-outgoing-links {
         list chassis-fabric-ccpc-outgoing-links-header {
           leaf card-detail {
             type string;
             description
               "Card detail";
           }
           leaf card-slot-num {
             type string;
             description
               "Card slot number";
           }
         }
         list chassis-fabric-tor-outgoing-links-header {
           leaf fm-space-tab {
             type string;
             description
               "Space tab";
           }
         }
         container chassis-fabric-links {
           list link-by-link-information {
             leaf src-link {
               type string;
               description
                 "Source link";
             }
             leaf dst-link {
               type string;
               description
                 "Destination link";
             }
             leaf hw-status {
               type string;
               description
                 "Hardware status";
             }
           }
         }
       }
     }
   }
   grouping fm-unreachable-dest-information-block {
     leaf slot {
       type int32;
     }
     list fm-fpc-line {
       description
         "Fabric reachability state for FPC";
       leaf pfe-slot {
         type int32;
       }
       list fm-pfe-line {
         description
           "Fabric reachability state for PFE";
         leaf fpc-pfe-unreach-dests {
           type string;
           description
             "Display unreachable destination FPC/PFEs list";
         }
       }
     }
   }
   grouping fm-fabric-reachability-information-block {
     leaf fab-reach-status {
       type string;
     }
     leaf fab-reach-resolute {
       type string;
     }
     container fab-reachability-detect {
       leaf unreach-dests {
         type string;
       }
       leaf detect-time {
         type string;
         description
           "Time of unreachability detection";
       }
       leaf unreachability-reason {
         type string;
       }
     }
     container fab-reachability-action {
       leaf current-act {
         type string;
       }
       leaf act-reason {
         type string;
       }
       leaf init-phase {
         type string;
       }
       leaf current-phase {
         type string;
       }
       leaf current-phase-status {
         type string;
       }
       leaf act-start-time {
         type string;
         description
           "Fabric reachability action started";
       }
       leaf act-end-time {
         type string;
         description
           "Time fabric reachability action completed";
       }
       leaf plane-restart-phase-status {
         type string;
       }
       leaf plane-restart-start-time {
         type string;
         description
           "Plane restart start time";
       }
       leaf plane-restart-list {
         type string;
       }
       leaf plane-timeout-list {
         type string;
         description
           "Planes timed out on event";
       }
       leaf plane-restart-planes-offline {
         type string;
       }
       leaf plane-restart-planes-offline-time {
         type string;
         description
           "Time plane made offline";
       }
       leaf plane-restart-planes-online {
         type string;
       }
       leaf plane-restart-planes-online-time {
         type string;
         description
           "Time plane made online";
       }
       leaf plane-restart-end-time {
         type string;
         description
           "Plane restart end time";
       }
       leaf pfe-offline-current {
         type string;
         description
           "PFEs being disabled";
       }
       leaf pfe-restart-action-list {
         type string;
       }
       leaf pfe-restart-offline-current {
         type string;
       }
       leaf pfe-restart-online-current {
         type string;
       }
       leaf pfe-restart-offline-start-time {
         type string;
         description
           "Offline PFE stage start time";
       }
       leaf pfe-restart-offline-end-time {
         type string;
         description
           "PFE restart offline stage end time";
       }
       leaf pfe-restart-online-start-time {
         type string;
         description
           "Offline PFE stage start time";
       }
       leaf pfe-restart-online-end-time {
         type string;
         description
           "PFE restart online end time";
       }
       leaf plane-fpc-restart-phase-status {
         type string;
       }
       leaf plane-fpc-restart-start-time {
         type string;
         description
           "Plane and FPC restart phase start time";
       }
       leaf fpc-offline-start-time {
         type string;
         description
           "Offline FPC stage start time";
       }
       leaf fpc-action-list {
         type string;
       }
       leaf fpc-offline-timeout-list {
         type string;
         description
           "FPCs timed out on offline event";
       }
       leaf fpc-offline-current {
         type int32;
       }
       leaf fpc-offline-time {
         type string;
         description
           "Time FPC made offline";
       }
       leaf fpc-offline-end-time {
         type string;
         description
           "Offline FPC stage end time";
       }
       leaf fpc-online-start-time {
         type string;
         description
           "FPC online stage start time";
       }
       leaf fpc-online-list {
         type string;
       }
       leaf fpc-online-timeout-list {
         type string;
         description
           "FPCs timed out on online event";
       }
       leaf fpc-online-current {
         type int32;
       }
       leaf fpc-online-time {
         type string;
         description
           "Time FPC made online";
       }
       leaf fpc-online-end-time {
         type string;
         description
           "FPC online stage end time";
       }
       leaf fpc-restart-list {
         type string;
         description
           "FPCs restart list";
       }
       leaf fpc-restart-time {
         type string;
         description
           "FPC restart time";
       }
       leaf plane-fpc-restart-phase-end-time {
         type string;
         description
           "Plane and FPC restart phase end time";
       }
       leaf fpc-offline-list {
         type string;
       }
       leaf fpc-offline-phase-status {
         type string;
       }
       leaf fpc-offline-phase-start-time {
         type string;
         description
           "FPC offline phase start time";
       }
       leaf fpc-offline-phase-end-time {
         type string;
         description
           "FPC offline phase end time";
       }
       leaf plane-skipped-list {
         type string;
       }
       leaf fpc-restart-phase-status {
         type string;
         description
           "Status of FPC restart phase";
       }
       leaf fpc-restart-phase-start-time {
         type string;
         description
           "FPC restart phase start time";
       }
       leaf fpc-timeout-list {
         type string;
         description
           "FPCs timed out";
       }
       leaf fpc-skipped-list {
         type string;
         description
           "FPCs skipped restart";
       }
       leaf fpc-restart-phase-end-time {
         type string;
         description
           "FPC restart phase end time";
       }
       leaf pfe-offline-phase-status {
         type string;
         description
           "Status of PFE offline phase";
       }
       leaf pfe-offline-phase-start-time {
         type string;
         description
           "PFE disable phase start time";
       }
       leaf pfe-disable-start-time {
         type string;
         description
           "PFE disable action start time";
       }
       leaf ifd-disable-start-time {
         type string;
         description
           "IFD disable action start time";
       }
       leaf pfe-offline-phase-fpc-offline {
         type string;
         description
           "FPC slots for which PFEs are being disabled";
       }
       leaf pfe-offline-phase-end-time {
         type string;
         description
           "PFE disable phase end time";
       }
       leaf pfe-restart-phase-status {
         type string;
         description
           "Status of PFE restart phase";
       }
       leaf pfe-restart-phase-start-time {
         type string;
         description
           "PFE restart phase start time";
       }
       leaf pfe-restart-list {
         type string;
         description
           "PFE restart list";
       }
       leaf pfe-restart-timeout-list {
         type string;
         description
           "PFE timed out";
       }
       leaf pfe-restart-skipped-list {
         type string;
         description
           "PFEs skipped restart";
       }
       leaf pfe-restart-offline-list {
         type string;
         description
           "PFE restart offline list";
       }
       leaf pfe-restart-offline-time {
         type string;
         description
           "PFE restart offline end time";
       }
       leaf pfe-restart-online-list {
         type string;
         description
           "PFE restart online list";
       }
       leaf pfe-restart-online-time {
         type string;
         description
           "Time PFE made online";
       }
       leaf pfe-restart-offline-online-list {
         type string;
         description
           "PFE restart offline/online list";
       }
       leaf pfe-restart-phase-end-time {
         type string;
         description
           "FPC restart phase end time";
       }
     }
   }
   grouping fm-fabric-events-information-block {
     list fabric-events-q {
       leaf evt-msg {
         type string;
       }
       list evt-line {
         leaf evt-type {
           type string;
         }
         leaf evt-slot {
           type string;
         }
         leaf evt-aux-slot {
           type string;
         }
         leaf evt-sub-slot {
           type string;
         }
       }
     }
   }
   grouping fm-fabric-events-history-block {
     list event-line {
       leaf event-type {
         type string;
       }
       leaf event-fpc-slot {
         type string;
       }
       leaf event-stage {
         type string;
       }
       leaf event-aux-slot {
         type string;
       }
       leaf event-sub-slot {
         type string;
       }
       leaf event-time {
         type string;
         description
           "Event timestamp";
       }
     }
   }
   grouping fm-degraded-fabric-state-information-block {
     list fm-fpc-line {
       description
         "Fabric reachability state for FPC";
       leaf deg-fpc-slot {
         type int32;
         description
           "FPC slot";
       }
       list fm-pfe-line {
         description
           "Fabric reachability state for PFE";
         leaf deg-pfe-slot {
           type int32;
           description
             "PFE slot";
         }
         list fm-pfe-sib-line {
           description
             "Fabric state for FE per SIB/Plane";
           leaf deg-sib-slot {
             type int32;
             description
               "SIB slot";
           }
           leaf deg-sib-plane {
             type int32;
             description
               "Plane number";
           }
           leaf deg-link-error-list {
             type string;
             description
               "List of destinations with Link Err";
           }
           leaf deg-dest-error-list {
             type string;
             description
               "List of destinations with Destination Err";
           }
         }
       }
     }
   }
   grouping fm-fru-errors-block {
     leaf fm-fru-first-error-header {
       type int32;
       description
         "First error logs header";
     }
     leaf fm-fru-last-error-header {
       type int32;
       description
         "Last error logs header";
     }
     list fm-first-error-ln {
       leaf fm-first-error-time {
         type string;
       }
       leaf fm-first-error-detail {
         type string;
       }
     }
     list fm-last-error-ln {
       leaf fm-last-error-time {
         type string;
       }
       leaf fm-last-error-detail {
         type string;
       }
     }
   }
   grouping fm-fru-errors-recent-block {
     leaf fm-fru-recent-error-header {
       type int32;
       description
         "Recent error logs header";
     }
     list fm-error-ln-recent {
       leaf fm-recent-error-time {
         type string;
       }
       leaf fm-recent-error-detail {
         type string;
       }
     }
   }
   grouping fm-fru-errors-oldest-block {
     leaf fm-fru-oldest-error-header {
       type int32;
       description
         "Recent error logs header";
     }
     list fm-error-ln-oldest {
       leaf fm-oldest-error-time {
         type string;
       }
       leaf fm-oldest-error-detail {
         type string;
       }
     }
   }
   grouping fm-fru-errors-all-block {
     leaf fm-fru-all-error-header {
       type int32;
       description
         "All error logs header";
     }
     list fm-error-ln-all {
       leaf fm-all-error-time {
         type string;
       }
       leaf fm-all-error-detail {
         type string;
       }
     }
   }
   grouping fm-fru-errors-plane-history-block {
     leaf fm-fru-plane-history-error-header {
       type int32;
       description
         "Plane history error logs header";
     }
     list fm-error-ln-plane-history {
       leaf fm-plane-history-error-time {
         type string;
       }
       leaf fm-plane-history-error-detail {
         type string;
       }
     }
   }
   grouping fm-fpc-stream-information-block {
     list header-info-line {
       leaf header-info {
         type string;
       }
     }
     list fpc-low-stream-info-line {
       leaf slot {
         type int32;
       }
       leaf low-stream-info {
         type string;
       }
     }
     list high-stream-info-line {
       leaf high-stream-info {
         type string;
       }
     }
   }
   grouping chassis-inventory-block {
     container chassis {
       description
         "Hardware inventory of this chassis";
       leaf name {
         type string;
         description
           "Name of this component";
       }
       leaf version {
         type string;
         description
           "Version of this component";
       }
       leaf part-number {
         type string;
         description
           "Part number of this component";
       }
       leaf serial-number {
         type string;
         description
           "Serial number of this component";
       }
       leaf description {
         type string;
         description
           "Description of this component";
       }
       leaf hardware-incomplete {
         type empty;
       }
       leaf model-number {
         type string;
         description
           "Model number of this component";
       }
       leaf clei-code {
         type string;
         description
           "Common Language Equipment Identifier code of this component";
       }
       container i2c-information {
         leaf jedec-code {
           type string;
         }
         leaf eeprom-version {
           type string;
         }
         leaf part-number {
           type string;
           description
             "Part number of this component";
         }
         leaf serial-number {
           type string;
           description
             "Serial number of this component";
         }
         leaf assembly-identifier {
           type string;
         }
         leaf assembly-version {
           type string;
         }
         leaf manufacture-date {
           type string;
           description
             "Date this component was manufactured";
         }
         leaf assembly-flags {
           type string;
         }
         leaf i2c-version {
           type string;
         }
         leaf clei-code {
           type string;
           description
             "Common Language Equipment Identifier code of this component";
         }
         leaf i2c-identifier {
           type string;
         }
         leaf model-number {
           type string;
           description
             "Model number of this component";
         }
         leaf board-information-record {
           type string;
           description
             "Hex dump of board information record";
         }
         leaf i2c-data {
           type string;
           description
             "Hex dump of I2C data";
         }
       }
       list chassis-module {
         key "name";
         leaf name {
           type string;
           description
             "Name of this component";
         }
         leaf version {
           type string;
           description
             "Version of this component";
         }
         leaf part-number {
           type string;
           description
             "Part number of this component";
         }
         leaf serial-number {
           type string;
           description
             "Serial number of this component";
         }
         leaf description {
           type string;
           description
             "Description of this component";
         }
         leaf ir-mode {
           type string;
           description
             "R/IR mode configured";
         }
         container i2c-information {
           leaf jedec-code {
             type string;
           }
           leaf eeprom-version {
             type string;
           }
           leaf part-number {
             type string;
             description
               "Part number of this component";
           }
           leaf serial-number {
             type string;
             description
               "Serial number of this component";
           }
           leaf assembly-identifier {
             type string;
           }
           leaf assembly-version {
             type string;
           }
           leaf manufacture-date {
             type string;
             description
               "Date this component was manufactured";
           }
           leaf assembly-flags {
             type string;
           }
           leaf i2c-version {
             type string;
           }
           leaf clei-code {
             type string;
             description
               "Common Language Equipment Identifier code of this component";
           }
           leaf i2c-identifier {
             type string;
           }
           leaf model-number {
             type string;
             description
               "Model number of this component";
           }
           leaf board-information-record {
             type string;
             description
               "Hex dump of board information record";
           }
           leaf i2c-data {
             type string;
             description
               "Hex dump of I2C data";
           }
         }
         list firmware {
           leaf firmware-version-psm {
             type string;
           }
           leaf firmware-primary-mcu {
             type string;
           }
           leaf firmware-secondary-mcu {
             type string;
           }
           leaf firmware-communication-mcu {
             type string;
           }
           leaf firmware-led-mcu {
             type string;
           }
           leaf type {
             type string;
             description
               "Type of this component";
           }
           leaf firmware-version {
             type string;
             description
               "Firmware version string for this component";
           }
         }
         list chassis-sub-module {
           key "name";
           leaf name {
             type string;
             description
               "Name of this component";
           }
           leaf version {
             type string;
             description
               "Version of this component";
           }
           leaf part-number {
             type string;
             description
               "Part number of this component";
           }
           leaf serial-number {
             type string;
             description
               "Serial number of this component";
           }
           leaf description {
             type string;
             description
               "Description of this component";
           }
           container i2c-information {
             leaf jedec-code {
               type string;
             }
             leaf eeprom-version {
               type string;
             }
             leaf part-number {
               type string;
               description
                 "Part number of this component";
             }
             leaf serial-number {
               type string;
               description
                 "Serial number of this component";
             }
             leaf assembly-identifier {
               type string;
             }
             leaf assembly-version {
               type string;
             }
             leaf manufacture-date {
               type string;
               description
                 "Date this component was manufactured";
             }
             leaf assembly-flags {
               type string;
             }
             leaf i2c-version {
               type string;
             }
             leaf clei-code {
               type string;
               description
                 "Common Language Equipment Identifier code of this 
                 component";
             }
             leaf i2c-identifier {
               type string;
             }
             leaf model-number {
               type string;
               description
                 "Model number of this component";
             }
             leaf board-information-record {
               type string;
               description
                 "Hex dump of board information record";
             }
             leaf i2c-data {
               type string;
               description
                 "Hex dump of I2C data";
             }
           }
           list firmware {
             leaf firmware-version-psm {
               type string;
             }
             leaf firmware-primary-mcu {
               type string;
             }
             leaf firmware-secondary-mcu {
               type string;
             }
             leaf firmware-communication-mcu {
               type string;
             }
             leaf firmware-led-mcu {
               type string;
             }
           }
           list chassis-sub-sub-module {
             key "name";
             leaf name {
               type string;
               description
                 "Name of this component";
             }
             leaf version {
               type string;
               description
                 "Version of this component";
             }
             leaf part-number {
               type string;
               description
                 "Part number of this component";
             }
             leaf serial-number {
               type string;
               description
                 "Serial number of this component";
             }
             leaf description {
               type string;
               description
                 "Description of this component";
             }
             leaf model-number {
               type string;
               description
                 "Model number of this component";
             }
             leaf clei-code {
               type string;
               description
                 "Common Language Equipment Identifier code of this 
                 component";
             }
             list chassis-sub-sub-sub-module {
               key "name";
               leaf name {
                 type string;
                 description
                   "Name of this component";
               }
               leaf version {
                 type string;
                 description
                   "Version of this component";
               }
               leaf part-number {
                 type string;
                 description
                   "Part number of this component";
               }
               leaf serial-number {
                 type string;
                 description
                   "Serial number of this component";
               }
               leaf description {
                 type string;
                 description
                   "Description of this component";
               }
               leaf model-number {
                 type string;
                 description
                   "Model number of this component";
               }
               leaf clei-code {
                 type string;
                 description
                   "Common Language Equipment Identifier code of this 
                   component";
               }
             }
             container i2c-information {
               leaf jedec-code {
                 type string;
               }
               leaf eeprom-version {
                 type string;
               }
               leaf part-number {
                 type string;
                 description
                   "Part number of this component";
               }
               leaf serial-number {
                 type string;
                 description
                   "Serial number of this component";
               }
               leaf assembly-identifier {
                 type string;
               }
               leaf assembly-version {
                 type string;
               }
               leaf manufacture-date {
                 type string;
                 description
                   "Date this component was manufactured";
               }
               leaf assembly-flags {
                 type string;
               }
               leaf i2c-version {
                 type string;
               }
               leaf clei-code {
                 type string;
                 description
                   "Common Language Equipment Identifier code of this 
                   component";
               }
               leaf i2c-identifier {
                 type string;
               }
               leaf model-number {
                 type string;
                 description
                   "Model number of this component";
               }
               leaf board-information-record {
                 type string;
                 description
                   "Hex dump of board information record";
               }
               leaf i2c-data {
                 type string;
                 description
                   "Hex dump of I2C data";
               }
             }
           }
           leaf model-number {
             type string;
             description
               "Model number of this component";
           }
           leaf clei-code {
             type string;
             description
               "Common Language Equipment Identifier code of this component";
           }
         }
         list chassis-re-disk-module {
           key "name";
           leaf name {
             type string;
             description
               "Name of this component";
           }
           leaf disk-size {
             type int32;
             description
               "Disk size (megabytes)";
           }
           leaf model {
             type string;
           }
           leaf serial-number {
             type string;
             description
               "Serial number of this component";
           }
           leaf description {
             type string;
             description
               "Description of this component";
           }
         }
         list chassis-re-usb-module {
           key "name";
           leaf name {
             type string;
             description
               "Name of this component";
           }
           leaf product {
             type string;
           }
           leaf product-number {
             type int32;
           }
           leaf vendor {
             type string;
           }
           leaf description {
             type string;
             description
               "Description of this component";
           }
         }
         list chassis-re-dimm-module {
           key "name";
           leaf name {
             type string;
             description
               "Name of this component";
           }
           leaf part-number {
             type string;
             description
               "Part number of this component";
           }
           leaf die-rev {
             type string;
             description
               " DIE revision of the DIMM";
           }
           leaf pcb-rev {
             type string;
             description
               "PCB revision ";
           }
           leaf mfr-id {
             type string;
             description
               "Manufacture Id of the DIMM";
           }
         }
         list chassis-compute-node-disk-module {
           key "name";
           leaf name {
             type string;
             description
               "Name of this component";
           }
           leaf disk-size {
             type int32;
             description
               "Disk size (megabytes)";
           }
           leaf model {
             type string;
           }
           leaf serial-number {
             type string;
             description
               "Serial number of this component";
           }
           leaf description {
             type string;
             description
               "Description of this component";
           }
         }
         leaf license-mode {
           type string;
           description
             "PTX R/IR mode configured";
         }
         leaf model-number {
           type string;
           description
             "Model number of this component";
         }
         leaf clei-code {
           type string;
           description
             "Common Language Equipment Identifier code of this component";
         }
       }
     }
   }
   grouping reswatch-config-information-block {
     leaf reswatch-enable {
       type string;
     }
     leaf reswatch-cpu-statistics-count {
       type string;
     }
     leaf reswatch-jkl-statistics-count {
       type string;
     }
     leaf reswatch-red-enable {
       type string;
     }
     leaf reswatch-red-cpu-threshold {
       type string;
     }
     leaf reswatch-red-jkl-threshold {
       type string;
     }
     leaf reswatch-red-snmp-enable {
       type string;
     }
     leaf reswatch-orange-enable {
       type string;
     }
     leaf reswatch-orange-threshold {
       type string;
     }
   }
   grouping power-budget-information-block {
     leaf psu-slot {
       type int32;
       description
         "PSU slot";
     }
     leaf-list psu-type {
       type string;
       description
         "PSU type";
     }
     leaf power-supplied-psu {
       type int32;
       description
         "Power supplied by that PSU";
     }
     leaf power-supply-state {
       type string;
       description
         "State of PSU";
     }
     leaf total-power-supplied {
       type int32;
       description
         "Total Power supplied by all Online PSUs";
     }
     leaf-list psu-redundancy-config {
       type string;
       description
         "PSU redundancy Config";
     }
     leaf base-power {
       type int32;
       description
         "Reserved Power for the chassis";
     }
     leaf line-card-slot {
       type int32;
       description
         "Line card slot";
     }
     leaf-list line-card-type {
       type string;
       description
         "Line card type";
     }
     leaf line-card-power {
       type int32;
       description
         "Power used by that line card";
     }
     leaf line-card-poe-power {
       type int32;
       description
         "Power allocated for PoE per FPC";
     }
     leaf line-card-priority {
       type int32;
       description
         "Priority of the FPC";
     }
     leaf actual-power-used {
       type int32;
       description
         "Actual Power consumed by the chassis";
     }
     leaf total-poe-power-allocated {
       type int32;
       description
         "Total power allocated for Power over Ethernet(PoE)";
     }
     leaf power-available-redundant-case {
       type int32;
       description
         "Power available for use in redundant (N+1) case";
     }
     leaf total-power-available {
       type int32;
       description
         "Power available for use in non redundant (N) case";
     }
     list power-budget {
       key "line-card-slot";
       leaf total-power-supplied {
         type int32;
         description
           "Total Power supplied by all Online PSUs";
       }
       leaf-list psu-redundancy-config {
         type string;
         description
           "PSU redundancy Config";
       }
       leaf base-power {
         type int32;
         description
           "Reserved Power for the chassis";
       }
       leaf line-card-slot {
         type int32;
         description
           "Line card slot";
       }
       leaf-list line-card-type {
         type string;
         description
           "Line card type";
       }
       leaf line-card-power {
         type int32;
         description
           "Power used by that line card";
       }
       leaf line-card-poe-power {
         type int32;
         description
           "Power allocated for PoE per FPC";
       }
       leaf line-card-priority {
         type int32;
         description
           "Priority of the FPC";
       }
       leaf actual-power-used {
         type int32;
         description
           "Actual Power consumed by the chassis";
       }
       leaf total-poe-power-allocated {
         type int32;
         description
           "Total power allocated for Power over Ethernet(PoE)";
       }
       leaf power-available-redundant-case {
         type int32;
         description
           "Power available for use in redundant (N+1) case";
       }
       leaf total-power-available {
         type int32;
         description
           "Power available for use in non redundant (N) case";
       }
       list power-supply {
         key "psu-slot";
         description
           "State of the status LEDs on the faceplate of a power supply";
         leaf psu-slot {
           type int32;
           description
             "PSU slot";
         }
         leaf-list psu-type {
           type string;
           description
             "PSU type";
         }
         leaf power-supplied-psu {
           type int32;
           description
             "Power supplied by that PSU";
         }
         leaf power-supply-state {
           type string;
           description
             "State of PSU";
         }
         leaf slot {
           type int32;
         }
         leaf amber-led {
           type empty;
           description
             "Amber LED is lit";
         }
         leaf green-led {
           type empty;
           description
             "Green LED is lit";
         }
         leaf blue-led {
           type empty;
           description
             "Blue LED is lit";
         }
       }
       leaf fan-tray-slot {
         type int32;
         description
           "Fan Tray slot";
       }
       leaf-list fan-tray-type {
         type string;
         description
           "Fan Tray type";
       }
       leaf fan-tray-base-power {
         type int32;
         description
           "Fan Tray base power";
       }
       leaf fan-tray-actual-power {
         type empty;
         description
           "Actual Power consumed by Fan Tray";
       }
       leaf line-card-actual-power {
         type empty;
         description
           "Power actually used by that line card";
       }
       leaf actual-poe-power-used {
         type int32;
         description
           "Power used for Power over Ethernet (PoE)";
       }
       leaf total-poe-power-available {
         type int32;
         description
           "Total power available for Power over Ethernet (PoE)";
       }
     }
     leaf fan-tray-slot {
       type int32;
       description
         "Fan Tray slot";
     }
     leaf-list fan-tray-type {
       type string;
       description
         "Fan Tray type";
     }
     leaf fan-tray-base-power {
       type int32;
       description
         "Fan Tray base power";
     }
     leaf fan-tray-actual-power {
       type empty;
       description
         "Actual Power consumed by Fan Tray";
     }
     leaf line-card-actual-power {
       type empty;
       description
         "Power actually used by that line card";
     }
     leaf actual-poe-power-used {
       type int32;
       description
         "Power used for Power over Ethernet (PoE)";
     }
     leaf total-poe-power-available {
       type int32;
       description
         "Total power available for Power over Ethernet (PoE)";
     }
   }
   grouping chassis-ae-lb-information-block {
     leaf chassis-ae-lb-state {
       type string;
       description
         "Chassis Multicast Loadbalancing setting";
     }
     leaf chassis-ae-lb-mode {
       type string;
       description
         "Chassis Multicast Loadbalancing mode";
     }
   }
   grouping rps-chassis-information-block {
     list rps-member-list {
       leaf rps-member-id {
         type int32;
       }
       leaf rps-backup-status {
         type string;
       }
       leaf rps-serial-number {
         type string;
       }
       leaf rps-port-number {
         type int32;
       }
     }
   }
   grouping chassis-mac-addresses-block {
     list chassis-mac-addresses-edge-info {
       container re-mac-address {
         leaf re-fc-mac-base {
           type string;
         }
         leaf re-fc-mac-count {
           type string;
         }
         leaf re-vlan-mac {
           type string;
         }
       }
       list fpc-mac-address {
         key "name";
         leaf name {
           type string;
           description
             "Name of this component";
         }
         leaf fpc-mac-base {
           type string;
         }
         leaf fpc-mac-count {
           type string;
         }
       }
     }
     list mac-address-information {
       leaf public-base-address {
         type string;
       }
       leaf public-count {
         type string;
       }
       leaf private-base-address {
         type string;
       }
       leaf private-count {
         type string;
       }
     }
     container external-mac-address-information {
       leaf external-base-address {
         type string;
       }
       leaf external-count {
         type string;
       }
       leaf external-available {
         type string;
       }
     }
   }
   grouping raid-information-block {
     leaf raid-status {
       type string;
     }
     list raid-members {
       leaf raid-member-device {
         type string;
       }
       leaf raid-member-format {
         type string;
       }
       leaf raid-member-name {
         type string;
       }
       leaf raid-member-type {
         type string;
       }
       leaf raid-member-status {
         type string;
       }
       leaf raid-member-size {
         type string;
       }
       leaf raid-member-offset {
         type string;
       }
     }
   }
   grouping route-engine-information-block {
     list route-engine {
       leaf slot {
         type int32;
       }
       leaf physical-slot {
         type int32;
       }
       leaf mastership-state {
         type string;
         description
           "Current state of mastership on this Routing Engine";
       }
       leaf mastership-priority {
         type string;
         description
           "Configured priority for mastership on this Routing Engine";
       }
       leaf temperature {
         type string;
         description
           "Temperature of the item";
       }
       leaf cpu-temperature {
         type string;
       }
       leaf memory-dram-size {
         type string;
         description
           "DRAM";
       }
       leaf memory-installed-size {
         type string;
         description
           "Installed RAM";
       }
       leaf memory-buffer-utilization {
         type int32;
         description
           "Percentage of buffer memory utilized";
       }
       leaf memory-system-total {
         type int32;
         description
           "Display the total system memory";
       }
       leaf memory-system-total-used {
         type int32;
         description
           "Display overall utilization of system memory";
       }
       leaf memory-system-total-util {
         type int32;
         description
           "Display overall %utilization of system memory";
       }
       leaf memory-control-plane {
         type int32;
         description
           "Display the total memory with control plane";
       }
       leaf memory-control-plane-used {
         type int32;
         description
           "Display the memory utilization of control plane mem";
       }
       leaf memory-control-plane-util {
         type int32;
         description
           "Display the %memory utilization of control plane mem";
       }
       leaf memory-data-plane {
         type int32;
         description
           "Display the total memory preallocated for data plane";
       }
       leaf memory-data-plane-used {
         type int32;
         description
           "Display the memory utilization of data plane mem";
       }
       leaf memory-data-plane-util {
         type int32;
         description
           "Display the %memory utilization of data plane mem";
       }
       leaf control-plane-cpu-count {
         type int32;
         description
           "Display the number of CPUS dedicated for control-plane";
       }
       leaf data-plane-cpu-count {
         type int32;
         description
           "Display the number of CPUS dedicated for data-plane";
       }
       leaf cpu-user {
         type int32;
         description
           "Percentage of CPU utilized by user processes";
       }
       leaf cpu-real-time {
         type int32;
         description
           "Percentage of CPU utilized by real-time threads";
       }
       leaf cpu-background {
         type int32;
         description
           "Percentage of CPU utilized by background processes";
       }
       leaf cpu-system {
         type int32;
         description
           "Percentage of CPU utilized by the kernel";
       }
       leaf cpu-interrupt {
         type int32;
         description
           "Percentage of CPU utilized by interrupt processing";
       }
       leaf cpu-idle {
         type int32;
         description
           "Percentage of CPU idle time";
       }
       leaf cpu-user1 {
         type int32;
         description
           "Percentage of CPU utilized by user processes";
       }
       leaf cpu-background1 {
         type int32;
         description
           "Percentage of CPU utilized by background processes";
       }
       leaf cpu-system1 {
         type int32;
         description
           "Percentage of CPU utilized by the kernel";
       }
       leaf cpu-interrupt1 {
         type int32;
         description
           "Percentage of CPU utilized by the Interrupt";
       }
       leaf cpu-idle1 {
         type int32;
         description
           "Percentage of CPU idle time";
       }
       leaf cpu-user2 {
         type int32;
         description
           "Percentage of CPU utilized by user processes";
       }
       leaf cpu-background2 {
         type int32;
         description
           "Percentage of CPU utilized by background processes";
       }
       leaf cpu-system2 {
         type int32;
         description
           "Percentage of CPU utilized by the kernel";
       }
       leaf cpu-interrupt2 {
         type int32;
         description
           "Percentage of CPU utilized by the Interrupt";
       }
       leaf cpu-idle2 {
         type int32;
         description
           "Percentage of CPU idle time";
       }
       leaf cpu-user3 {
         type int32;
         description
           "Percentage of CPU utilized by user processes";
       }
       leaf cpu-background3 {
         type int32;
         description
           "Percentage of CPU utilized by background processes";
       }
       leaf cpu-system3 {
         type int32;
         description
           "Percentage of CPU utilized by the kernel";
       }
       leaf cpu-interrupt3 {
         type int32;
         description
           "Percentage of CPU utilized by the Interrupt";
       }
       leaf cpu-idle3 {
         type int32;
         description
           "Percentage of CPU idle time";
       }
       leaf model {
         type string;
       }
       leaf serial-number {
         type string;
         description
           "Serial number of this component";
       }
       leaf start-time {
         type string;
         description
           "Time this component was started";
       }
       leaf up-time {
         type string;
         description
           "Length of time this component has been operational";
       }
       leaf last-reboot-reason {
         type string;
         description
           "Last reboot reason of routinge engine";
       }
       leaf load-average-one {
         type string;
       }
       leaf load-average-five {
         type string;
       }
       leaf load-average-fifteen {
         type string;
       }
       leaf bios-version {
         type string;
         description
           "Routing engine BIOS version";
       }
       leaf bios-date {
         type string;
         description
           "Routing engine BIOS date";
       }
       leaf bios-id {
         type string;
         description
           "Routing engine BIOS ID";
       }
       leaf description {
         type string;
         description
           "Description of this component";
       }
       leaf status {
         type string;
         description
           "Status of clock synchronization source";
       }
       leaf loader-name {
         type string;
         description
           "Routing engine Loader name";
       }
       leaf loader-version {
         type string;
         description
           "Routing engine Loader version";
       }
       leaf icrt-version {
         type string;
         description
           "Routing engine iCRT version";
       }
     }
   }
   grouping route-engine-resiliency-information-block {
     list route-engine-resiliency-entry {
       leaf reerror-module-name {
         type string;
         description
           "Module_name";
       }
       leaf reerror-error-id {
         type uint64;
         description
           "Error_id";
       }
       leaf reerror-threshold {
         type int32;
         description
           "Threshold";
       }
       leaf reerror-count {
         type int32;
         description
           "Count";
       }
       leaf reerror-occured {
         type int32;
         description
           "Occured";
       }
       leaf reerror-cleared {
         type int32;
         description
           "Cleared";
       }
       leaf reerror-errdesc {
         type string;
         description
           "Desc";
       }
       leaf reerror-timestamp {
         type int32;
         description
           "Timestamp";
       }
       leaf reerror-module-id {
         type int32;
         description
           "Module_id";
       }
     }
   }
   grouping emmc-health-information-block {
     list emmc-information {
       leaf node-name {
         type string;
       }
       leaf dev-lifetime-a {
         type int32;
         description
           "Life time estimation for SLC eraseblocks, provided in steps of 
           10%";
       }
       leaf dev-lifetime-b {
         type int32;
         description
           "Life time estimation for MLC eraseblocks, provided in steps of 
           10%";
       }
       leaf dev-pre-eol-info {
         type int32;
         description
           "Pre EOL information: overall status for reserved blocks";
       }
     }
   }
   grouping service-node-information-block {
     list service-node {
       leaf slot {
         type int32;
       }
       leaf status {
         type string;
         description
           "Status of clock synchronization source";
       }
       leaf cpu-total {
         type int32;
         description
           "Percentage of CPU utilized";
       }
       leaf memory-dram-size {
         type string;
         description
           "DRAM";
       }
       leaf memory-heap-utilization {
         type int32;
         description
           "Percentage of heap memory utilized";
       }
       leaf start-time {
         type string;
         description
           "Time this component was started";
       }
       leaf up-time {
         type string;
         description
           "Length of time this component has been operational";
       }
       list psu-module {
         leaf psu-slot {
           type int32;
           description
             "PSU slot";
         }
         leaf model {
           type string;
         }
         leaf serial-number {
           type string;
           description
             "Serial number of this component";
         }
         leaf psu-rev {
           type string;
         }
         leaf-list psu-type {
           type string;
           description
             "PSU type";
         }
         leaf status {
           type string;
           description
             "Status of clock synchronization source";
         }
       }
       list service-node-version {
         leaf slot {
           type int32;
         }
         leaf version {
           type string;
           description
             "Version of this component";
         }
       }
     }
   }
   grouping scb-information-block {
     leaf cross-connect {
       type string;
     }
     leaf packet-scheduling {
       type string;
       description
         "Packet scheduling knob status";
     }
     list scb {
       leaf slot {
         type int32;
       }
       leaf state {
         type string;
         description
           "Status of the component";
       }
       leaf comment {
         type string;
       }
       leaf temperature {
         type string;
         description
           "Temperature of the item";
       }
       leaf cpu-total {
         type int32;
         description
           "Percentage of CPU utilized";
       }
       leaf cpu-interrupt {
         type int32;
         description
           "Percentage of CPU utilized by interrupt processing";
       }
       leaf memory-dram-size {
         type string;
         description
           "DRAM";
       }
       leaf memory-heap-utilization {
         type int32;
         description
           "Percentage of heap memory utilized";
       }
       leaf memory-buffer-utilization {
         type int32;
         description
           "Percentage of buffer memory utilized";
       }
       leaf failover-count {
         type int32;
       }
       leaf intake-temperature {
         type string;
       }
       leaf exhaust-temperature {
         type string;
       }
       leaf exhaust-a-temperature {
         type string;
         description
           "Exhaust A temperature";
       }
       leaf exhaust-b-temperature {
         type string;
         description
           "Exhaust B temperature";
       }
       leaf spp-temperature {
         type string;
       }
       leaf spr-temperature {
         type string;
       }
       leaf cpu-total-ukern {
         type int32;
       }
       leaf cpu-total-rt {
         type int32;
       }
       leaf memory-sram-size {
         type int32;
         description
           "SRAM";
       }
       leaf memory-rldram-size {
         type int32;
         description
           "RLDRAM";
       }
       leaf memory-xr2-size {
         type int32;
         description
           "XR2";
       }
       leaf memory-ddr-dram-size {
         type int32;
         description
           "DDR DRAM";
       }
       leaf asic-name {
         type string;
       }
       leaf asic-information {
         type string;
       }
       leaf start-time {
         type string;
         description
           "Time this component was started";
       }
       leaf up-time {
         type string;
         description
           "Length of time this component has been operational";
       }
       leaf activate-count {
         type int32;
       }
       leaf reset-count {
         type int32;
       }
       leaf max-power-consumption {
         type int32;
       }
       leaf max-mpc-base-power-consumption {
         type int32;
       }
       leaf max-mic0-power-consumption {
         type int32;
       }
       leaf max-mic1-power-consumption {
         type int32;
       }
       leaf max-mpc-total-power-consumption {
         type int32;
       }
       leaf memory-hbm-size {
         type int32;
         description
           "HBM";
       }
       leaf configured-bandwidth {
         type int32;
       }
       leaf operating-bandwidth {
         type int32;
       }
     }
     leaf scb-type {
       type string;
     }
   }
   grouping fan-information-block {
     leaf name {
       type string;
       description
         "Name of this component";
     }
     leaf status {
       type string;
       description
         "Status of clock synchronization source";
     }
     leaf rpm {
       type string;
       description
         "Fan speed in RPM";
     }
     leaf rpm-percent {
       type string;
       description
         "Fan speed in % RPM";
     }
     leaf comment {
       type string;
     }
     container fan-information-rpm-item {
       leaf name {
         type string;
         description
           "Name of this component";
       }
       leaf status {
         type string;
         description
           "Status of clock synchronization source";
       }
       leaf rpm {
         type string;
         description
           "Fan speed in RPM";
       }
       leaf comment {
         type string;
       }
     }
     container fan-information-percent-rpm-item {
       leaf name {
         type string;
         description
           "Name of this component";
       }
       leaf status {
         type string;
         description
           "Status of clock synchronization source";
       }
       leaf rpm-percent {
         type string;
         description
           "Fan speed in % RPM";
       }
       leaf comment {
         type string;
       }
     }
     list fan-speed-change-history-item {
       key "timestamp";
       leaf timestamp {
         type string;
       }
       leaf fru-name {
         type string;
       }
       leaf temp-sensor-name {
         type string;
       }
       leaf speed-percent {
         type string;
       }
     }
   }
   grouping chassis-location-block {
     list chassis-location-information {
       leaf country-code {
         type string;
         description
           "Country code";
       }
       leaf postal-code {
         type string;
         description
           "Postal code";
       }
       leaf npa-nxx {
         type string;
         description
           "Six digits of the phone number";
       }
       leaf altitude {
         type int32;
         description
           "Feet above (or below) sea level";
       }
       leaf lata {
         type string;
         description
           "Long distance service area";
       }
       leaf latitude {
         type string;
         description
           "Latitude";
       }
       leaf longitude {
         type string;
         description
           "Longitude";
       }
       leaf vcoord {
         type string;
         description
           "Bellcore vertical coordinate";
       }
       leaf hcoord {
         type string;
         description
           "Bellcore horizontal coordinate";
       }
       leaf building {
         type string;
         description
           "Building information";
       }
       leaf floor {
         type uint32;
         description
           "Floor in building";
       }
       leaf rack {
         type uint32;
         description
           "Rack";
       }
     }
   }
   grouping interface-location-name-information-block {
     list location-name-information {
       leaf interface-name {
         type string;
         description
           "Interface name";
       }
       leaf lcc-number {
         type int32;
         description
           "LCC Chassis number";
       }
       leaf fpc-number {
         type int32;
         description
           "FPC number";
       }
     }
   }
   grouping interface-location-slot-information-block {
     list location-slot-information {
       leaf global-fpc-number {
         type int32;
         description
           "Global FPC number";
       }
     }
   }
   grouping temperature-threshold-information-block {
     list temperature-threshold {
       key "name";
       description
         "Temperature threshold information for a component on the routing 
         platform.";
       leaf name {
         type string;
         description
           "Name of this component";
       }
       leaf fan-normal-speed {
         type string;
         description
           "Temperature above which fans are set to normal speed";
       }
       leaf fan-high-speed {
         type string;
         description
           "Temperature above which fans are set to high speed";
       }
       leaf yellow-alarm {
         type string;
         description
           "Temperature above which yellow alarm is raised";
       }
       leaf bad-fan-yellow-alarm {
         type string;
         description
           "Temperature above which yellow alarm is raised if one or more 
           fans are bad";
       }
       leaf red-alarm {
         type string;
         description
           "Temperature above which red alarm is raised";
       }
       leaf bad-fan-red-alarm {
         type string;
         description
           "Temperature above which red alarm is raised if one or more fans 
           are bad";
       }
       leaf fire-shutdown {
         type string;
         description
           "Temperature above which fire-shutdown occurs";
       }
     }
   }
   grouping enh-temperature-threshold-information-block {
     list enh-temperature-threshold {
       key "name";
       description
         "Temperature threshold information for a component on the routing 
         platform.";
       leaf name {
         type string;
         description
           "Name of this component";
       }
       leaf enh-fan-normal-speed {
         type string;
         description
           "Temperature above which fans are set to normal speed";
       }
       leaf enh-fan-high-speed {
         type string;
         description
           "Temperature above which fans are set to high speed";
       }
       leaf enh-fan-full-speed {
         type string;
         description
           "Temperature above which fans are set to full speed";
       }
       leaf enh-bad-fan-full-speed {
         type string;
         description
           "Temperature above which fans are set to high speed";
       }
       leaf enh-yellow-alarm {
         type string;
         description
           "Temperature above which yellow alarm is raised";
       }
       leaf enh-bad-fan-yellow-alarm {
         type string;
         description
           "Temperature above which yellow alarm is raised if one or more 
           fans are bad";
       }
       leaf enh-red-alarm {
         type string;
         description
           "Temperature above which red alarm is raised";
       }
       leaf enh-bad-fan-red-alarm {
         type string;
         description
           "Temperature above which red alarm is raised if one or more fans 
           are bad";
       }
       leaf enh-fire-shutdown {
         type string;
         description
           "Temperature above which fire-shutdown occurs";
       }
       leaf enh-state {
         type string;
         description
           "Temperature sensor EM policy state";
       }
     }
   }
   grouping power-management-information-block {
     list power-management {
       description
         "Information about JSeries Power Management";
       leaf power-mgmt-device {
         type string;
         description
           "Type of device";
       }
       leaf power-mgmt-low-power {
         type int32;
         description
           "Low power Rating tokens";
       }
       leaf power-mgmt-high-power {
         type int32;
         description
           "High power Rating tokens";
       }
       leaf power-mgmt-heat {
         type int32;
         description
           "Heat Rating tokens";
       }
       leaf power-mgmt-state {
         type string;
         description
           "Ratings exceed Chassis limits or not";
       }
     }
   }
   grouping in-service-upgrade-status-block {
     list in-service-upgrade-fru-status {
       description
         "In-Service Software Upgrade status for chassis";
       leaf fru-name {
         type string;
       }
       leaf fru-status {
         type string;
       }
       leaf fru-reason {
         type string;
       }
       list in-service-upgrade-pic-status {
         leaf fru-name {
           type string;
         }
         leaf fru-status {
           type string;
         }
         leaf fru-reason {
           type string;
         }
       }
     }
   }
   grouping chassis-mode-status-block {
     leaf-list fru-type {
       type string;
     }
     leaf-list fru-slt {
       type string;
     }
     leaf-list fru-mode {
       type string;
     }
   }
   grouping dedicated-ukern-cpu-block {
     leaf dedicated-ukern-cpu-enabled {
       type string;
     }
   }
   grouping chassis-oss-map-block {
     leaf chassis-model {
       type string;
       description
         "Actual chassis model";
     }
     leaf oss-map {
       type string;
       description
         "Configured OSS chassis model";
     }
   }
   grouping craft-lcd-led-information-block {
     leaf display-row-1 {
       type string;
     }
     leaf display-row-2 {
       type string;
     }
     leaf name {
       type string;
       description
         "Name of this component";
     }
     list front-panel-lcd {
       description
         "Information from the LCD-LED interfaces";
       container front-panel-title {
         leaf name {
           type string;
           description
             "Name of this component";
         }
         leaf delimiter {
           type string;
         }
       }
       container display-panel-lcd {
         description
           "Text currently appearing on the LCD interface display";
         leaf display-row-1 {
           type string;
         }
         leaf display-row-2 {
           type string;
         }
       }
       container system-led {
         description
           "State of system LEDs on the front panel";
         list system-led-display {
           key "name";
           leaf name {
             type string;
             description
               "Name of this component";
           }
           leaf led-status {
             type string;
           }
         }
       }
       container pic-status-led {
         description
           "State of QIC STATUS LEDs";
         list pic-status-led-display {
           leaf pic-name {
             type string;
           }
           leaf led-status {
             type string;
           }
         }
       }
       container interface-led {
         description
           "State of the Interface LEDs on the front panel";
         leaf interface-display-title {
           type string;
         }
         list interface-led-display {
           leaf interface-name {
             type string;
           }
           leaf led-status {
             type string;
           }
           leaf activity-led {
             type string;
             description
               "State of the Port Activity LED";
           }
         }
       }
     }
   }
   grouping chassis-cluster-interface-statistics-block {
     leaf control-interface-status {
       type string;
       description
         "Chassis cluster control interface status";
     }
     leaf dataplane-interface-status {
       type string;
       description
         "Chassis cluster fabric interface status";
     }
     container control-link-interfaces {
       list control-information {
         leaf control-link-interface-index {
           type uint32;
           description
             "Chassis cluster control interface index";
         }
         leaf control-link-interface-name {
           type string;
           description
             "Chassis cluster control interface name";
         }
         leaf control-link-interface-status {
           type string;
           description
             "Chassis cluster control interface status";
         }
         leaf control-link-interface-internal-sa-status {
           type string;
           description
             "Chassis cluster control interface internal SA status";
         }
         leaf control-link-interface-security-status {
           type string;
           description
             "Chassis cluster control interface security status";
         }
       }
     }
     container dataplane-interfaces {
       container fabric-information {
         leaf fabric-interface-index {
           type string;
           description
             "Chassis cluster fabric interface index";
         }
         leaf fabric-child-interface-name {
           type string;
           description
             "Child interface name";
         }
         leaf fabric-child-interface-status {
           type string;
           description
             "Connection status of child interface";
         }
         leaf fabric-link-interface-security-status {
           type string;
           description
             "Security status of child interface";
         }
       }
     }
     container reth {
       leaf reth-name {
         type string;
         description
           "Redundant ethernet interface name";
       }
       leaf reth-status {
         type string;
         description
           "Redundant ethernet interface status";
       }
       leaf redundancy-group-id-for-reth {
         type string;
         description
           "Redundancy-group ID of redundant ethernet interface";
       }
     }
     container interface-monitoring {
       leaf interface-name-for-monitoring {
         type string;
         description
           "Interface name for monitoring";
       }
       leaf weight {
         type int32;
         description
           "Weight assigned to this interface";
       }
       leaf status {
         type string;
         description
           "Interface administrative status";
       }
       leaf redundancy-group-for-interface {
         type int32;
         description
           "Redundancy-group for interface";
       }
     }
     container pseudo-if {
       leaf name {
         type string;
         description
           "Pseudo interface name";
       }
       leaf status {
         type string;
         description
           "Interface administrative status";
       }
       leaf redundancy-group-id {
         type int32;
         description
           "Redundancy-group id";
       }
     }
   }
   grouping chassis-cluster-control-port-status-block {
     list chassis-cluster-ctrl-intf-link-status {
       description
         "Information about Chassis Cluster control interface link status";
       leaf port-number {
         type int32;
         description
           "Control port number";
       }
       leaf line-side {
         type string;
         description
           "Control port line-side link status";
       }
     }
     list chassis-cluster-ctrl-port-eeprom {
       description
         "Information about Chassis Cluster control port ideeprom data";
       leaf port-number {
         type int32;
         description
           "Control port number";
       }
       leaf cable-type {
         type string;
         description
           "Port cable type";
       }
       leaf fiber-mode {
         type string;
         description
           "Single or multi-mode";
       }
       leaf sfp-vendor-name {
         type string;
         description
           "SFP vendor name";
       }
       leaf sfp-vendor-pno {
         type string;
         description
           "SFP vendor part number";
       }
       leaf wavelength {
         type string;
         description
           "Wavelength of the optical transceiver";
       }
       leaf sfp-vendor-fw-ver {
         type string;
         description
           "Vendor firmware version";
       }
       leaf sfp-jnpr-ver {
         type string;
         description
           "Juniper revision";
       }
       leaf sfp-msa-version {
         type string;
         description
           "Multi-Source Agreement version";
       }
     }
     list chassis-cluster-ctrl-port-diag {
       description
         "Information about Chassis Cluster control port diagnostics data";
       leaf port-index {
         type int32;
       }
       leaf current {
         type string;
       }
       leaf output-powers {
         type string;
       }
       leaf temp {
         type string;
       }
       leaf voltage {
         type string;
       }
       leaf receiver-power {
         type string;
       }
       leaf alarm-warning-flags {
         type string;
       }
       leaf current-high-alarm {
         type string;
       }
       leaf current-low-alarm {
         type string;
       }
       leaf current-high-warning {
         type string;
       }
       leaf current-low-warning {
         type string;
       }
       leaf output-power-high-alarm {
         type string;
       }
       leaf output-power-low-alarm {
         type string;
       }
       leaf output-power-high-warning {
         type string;
       }
       leaf output-power-low-warning {
         type string;
       }
       leaf temperature-high-alarm {
         type string;
       }
       leaf temperature-low-alarm {
         type string;
       }
       leaf temperature-high-warning {
         type string;
       }
       leaf temperature-low-warning {
         type string;
       }
       leaf voltage-high-alarm {
         type string;
       }
       leaf voltage-low-alarm {
         type string;
       }
       leaf voltage-high-warning {
         type string;
       }
       leaf voltage-low-warning {
         type string;
       }
       leaf rx-power-high-alarm {
         type string;
       }
       leaf rx-power-low-alarm {
         type string;
       }
       leaf rx-power-high-warning {
         type string;
       }
       leaf rx-power-low-warning {
         type string;
       }
       leaf current-high-alarm-threshold {
         type string;
       }
       leaf current-low-alarm-threshold {
         type string;
       }
       leaf current-high-warning-threshold {
         type string;
       }
       leaf current-low-warning-threshold {
         type string;
       }
       leaf output-power-high-alarm-threshold {
         type string;
       }
       leaf output-power-low-alarm-threshold {
         type string;
       }
       leaf output-power-high-warning-threshold {
         type string;
       }
       leaf output-power-low-warning-threshold {
         type string;
       }
       leaf temperature-high-alarm-threshold {
         type string;
       }
       leaf temperature-low-alarm-threshold {
         type string;
       }
       leaf temperature-high-warning-threshold {
         type string;
       }
       leaf temperature-low-warning-threshold {
         type string;
       }
       leaf voltage-high-alarm-threshold {
         type string;
       }
       leaf voltage-low-alarm-threshold {
         type string;
       }
       leaf voltage-high-warning-threshold {
         type string;
       }
       leaf voltage-low-warning-threshold {
         type string;
       }
       leaf rx-power-high-alarm-threshold {
         type string;
       }
       leaf rx-power-low-alarm-threshold {
         type string;
       }
       leaf rx-power-high-warning-threshold {
         type string;
       }
       leaf rx-power-low-warning-threshold {
         type string;
       }
     }
   }
   grouping chassis-cluster-statistics-block {
     container chassis-cluster-interfaces {
       container chassis-cluster-control {
         leaf control-interface-index {
           type uint32;
           description
             "Chassis cluster control interface index";
         }
         leaf heartbeat-sent {
           type string;
           description
             "Heartbeat packets sent on control link";
         }
         leaf heartbeat-received {
           type string;
           description
             "Heartbeat packets received on control link";
         }
         leaf heartbeat-errors {
           type string;
           description
             "Heartbeat packets dropped due to errors";
         }
       }
       list offload-heartbeat-statistics {
         description
           "Offloaded HA heartbeat statistics";
         leaf control-interface-index {
           type uint32;
           description
             "Chassis cluster control interface index";
         }
         leaf offload-heartbeat-connection {
           type string;
           description
             "HA offload mode connection status";
         }
         leaf offload-heartbeat-sent {
           type string;
           description
             "HA offload heartbeat sent";
         }
         leaf offload-heartbeat-received {
           type string;
           description
             "HA offload heartbeat received";
         }
         leaf offload-heartbeat-sent-jitter {
           type string;
           description
             "HA offload heartbeat sent jitter";
         }
         leaf offload-heartbeat-received-jitter {
           type string;
           description
             "HA offload heartbeat received jitter";
         }
       }
       container chassis-cluster-fabric {
         leaf rto-packets {
           type uint32;
           description
             "RTO packets";
         }
         leaf forwarded-packets {
           type uint32;
           description
             "Forwarded packets";
         }
         container fabric-child {
           leaf fabric-child-index {
             type uint32;
             description
               "Fabric child index";
           }
           leaf fabric-hello-sent {
             type uint32;
             description
               "Fabric hello packets sent";
           }
           leaf fabric-hello-received {
             type uint32;
             description
               "Fabric hello packets received";
           }
           leaf fabric-hello-error {
             type uint32;
             description
               "Fabric hello packets with error";
           }
         }
       }
     }
   }
   grouping services-synchronized-block {
     leaf service-name {
       type string;
       description
         "Name of the service";
     }
     leaf rtos-sent {
       type uint32;
       description
         "RTOs sent";
     }
     leaf rtos-received {
       type uint32;
       description
         "RTOs received";
     }
   }
   grouping chassis-cluster-dataplane-interfaces-block {
     leaf fabric-interface-index {
       type string;
       description
         "Chassis cluster fabric interface index";
     }
     container fabric-information {
       leaf fabric-child-interface-name {
         type string;
         description
           "Child interface name";
       }
       leaf fabric-child-interface-status {
         type string;
         description
           "Connection status of child interface";
       }
     }
   }
   grouping chassis-cluster-status-block {
     leaf cluster-id {
       type int32;
       description
         "Cluster id";
     }
     container redundancy-group {
       description
         "Redundancy group for IP monitoring";
       leaf redundancy-group-id {
         type int32;
         description
           "Redundancy-group id";
       }
       leaf redundancy-group-failover-count {
         type int32;
         description
           "No of transitions between primary and secondary states";
       }
       list device-stats {
         leaf device-name {
           type string;
           description
             "Node name";
         }
         leaf device-priority {
           type int32;
           description
             "Configured priority of the device";
         }
         leaf redundancy-group-status {
           type string;
           description
             "Status of the redundancy group";
         }
         leaf preempt {
           type string;
           description
             "Preempt configuration for the redundancy group";
         }
         leaf failover-mode {
           type string;
           description
             "Manual failover mode for the redundancy group";
         }
         leaf monitor-failures {
           type string;
           description
             "Monitoring failures for the redundancy group";
         }
       }
     }
   }
   grouping chassis-cluster-information-block {
     container chassis-cluster-redundancy-mode {
       description
         "Chassis cluster configured and operational redundancy modes";
       leaf configured {
         type string;
         description
           "Configured";
       }
       leaf operational {
         type string;
         description
           "Operational";
       }
       leaf mode-mismatch-warning {
         type string;
         description
           "Chassis cluster redundancy mode mismatch warning";
       }
     }
     container chassis-cluster-redundancy-group-information {
       description
         "Display redundancy group information";
       container redundancy-group-list {
         description
           "Display each redundancy group information";
         leaf redundancy-group-id {
           type int32;
           description
             "Redundancy-group id";
         }
         leaf redundancy-group-status {
           type string;
           description
             "Status of the redundancy group";
         }
         leaf redundancy-group-weight {
           type int32;
           description
             "Weight of redundancy group to indicate health status";
         }
         container redundancy-group-state-transition-record {
           description
             "Display each state transition";
           leaf transition-time {
             type string;
             description
               "Time of the transistion";
           }
           leaf from-state {
             type string;
             description
               "Previous state";
           }
           leaf to-state {
             type string;
             description
               "Current state";
           }
           leaf transition-reason {
             type string;
             description
               "Reason of the transition";
           }
         }
       }
     }
     container chassis-cluster-led-information {
       description
         "Chassis cluster LED related information";
       leaf current-led-color {
         type string;
         description
           "Current color of the chassis cluster LED";
       }
       leaf last-change-reason {
         type string;
         description
           "Reason for last change of state/color of the chassis cluster LED";
       }
     }
     container chassis-cluster-heartbeat-offload-information {
       description
         "Chassis cluster HA heartbeat offload mode information";
       leaf chassis-cluster-heartbeat-offload-status {
         type string;
         description
           "Chassis cluster HA heartbeat offload mode status";
       }
     }
     container chassis-cluster-hld-information {
       description
         "Chassis cluster HA HLD connection information";
       leaf chassis-cluster-hld-status {
         type string;
         description
           "Chassis cluster HA HLD connection details";
       }
     }
     container control-link-vlan-information {
       description
         "Control port traffic tagging with vlan(4094) enabled or disabled";
       leaf control-link-vlan-status {
         type string;
         description
           "Control port tagging enabled or disabled";
       }
     }
     container chassis-cluster-monitoring-failure-information {
       description
         "Display monitoring failure information";
       leaf monitoring-failure-title {
         type string;
         description
           "Display the title";
       }
       container spu-monitoring-failure-information {
         description
           "Display spu monitoring failure information";
         container spu-monitoring-failure-statistics {
           leaf spu-total-number {
             type int32;
             description
               "Statistics of total spus";
           }
           leaf npc-total-number {
             type int32;
             description
               "Statistics of total npcs";
           }
           leaf spu-up-number {
             type int32;
             description
               "Statistics of up spus";
           }
           leaf npc-up-number {
             type int32;
             description
               "Statistics of up npcs";
           }
           leaf spu-down-number {
             type int32;
             description
               "Statistics of down spus";
           }
           leaf npc-down-number {
             type int32;
             description
               "Statistics of down npcs";
           }
         }
         container spu-monitoring-failure-pic-state {
           description
             "Display monitoring pic state";
           leaf pfe-name {
             type string;
             description
               "Name of the PFE";
           }
           leaf pic-state {
             type string;
             description
               "State of each PIC";
           }
           leaf report-time {
             type string;
             description
               "Time of receiving report";
           }
         }
       }
       container ip-monitoring-failure-information {
         description
           "Display ip monitoring failure information";
         leaf redundancy-group-id {
           type int32;
           description
             "Redundancy-group id";
         }
         leaf redundancy-group-ip-monitoring-status {
           type string;
           description
             "IP monitoring status of each redundancy group";
         }
         leaf ip-address {
           type jt:ipaddr;
           description
             "IPv4 address that is being monitored";
         }
         leaf ip-reachability-status {
           type string;
           description
             "IP address reachability status";
         }
         leaf ip-unreachable-reason {
           type string;
           description
             "Reason for IP reachability failure";
         }
       }
       container interface-monitoring-failure-information {
         description
           "Display interface monitoring failure information";
         leaf redundancy-group-id {
           type int32;
           description
             "Redundancy-group id";
         }
         leaf interface-monitoring-status {
           type string;
           description
             "Monitoring status of each redundancy group";
         }
         leaf monitoring-interface-name {
           type string;
           description
             "Name of monitored interface";
         }
         leaf monitoring-interface-status {
           type string;
           description
             "Status of monitored interface";
         }
         leaf monitoring-child-interface-name {
           type string;
           description
             "Name of child interface belong to monitored interface";
         }
         leaf monitoring-child-interface-status {
           type string;
           description
             "Status of child interface belong to monitored interface";
         }
       }
       container coldsync-monitoring-failure-information {
         description
           "Display coldsync monitoring failure information";
         container coldsync-monitoring-statistics {
           description
             "Display statistics information of coldsync";
           leaf coldsync-total-spu {
             type int32;
             description
               "The number of spu that need to do coldsync";
           }
           leaf coldsync-completed-spu {
             type int32;
             description
               "The number of spu that coldsync completed";
           }
           leaf coldsync-not-complete-spu {
             type int32;
             description
               "The number of spu that coldsync not complete";
           }
         }
         container coldsync-monitoring-spu-list {
           description
             "List each spu coldsync state";
           leaf pfe-name {
             type string;
             description
               "Name of the PFE";
           }
           leaf coldsync-state {
             type string;
             description
               "Spu coldsync state";
           }
           leaf report-time {
             type string;
             description
               "Time of receiving report";
           }
         }
       }
       container hardware-monitoring-failure-information {
         description
           "Display hardware monitoring failure information";
         leaf hardware-monitoring-failure-redundancy-group {
           type string;
           description
             "Redundancy group of hardware monitoring failure";
         }
         leaf report-time {
           type string;
           description
             "Time of receiving report";
         }
       }
       container loopback-monitoring-failure-information {
         description
           "Display loopback, mbuf and nexthop monitoring information";
         leaf pfe-name {
           type string;
           description
             "Name of the PFE";
         }
         leaf loopback-monitoring-status {
           type string;
           description
             "Result of loopback monitoring";
         }
         leaf nexthop-monitoring-status {
           type string;
           description
             "Result of nexthop monitoring";
         }
         leaf mbuf-monitoring-status {
           type string;
           description
             "Result of mbuf monitoring";
         }
       }
       container fabric-link-failure-information {
         description
           "Display fabric link failure information";
         container fabric-link-interface-status {
           description
             "Status of fabric link interfaces";
           leaf fabric-link-interface-index {
             type int32;
             description
               "Index of fabric link interface";
           }
           container fabric-link-child-interface-status {
             description
               "Status of fabric link child interfaces";
             leaf fabric-link-child-interface-name {
               type string;
               description
                 "Child interface name of fabric link";
             }
             leaf fabric-link-child-interface-physical-status {
               type string;
               description
                 "Child interface ifd status of fabric link";
             }
             leaf fabric-link-child-interface-monitored-status {
               type string;
               description
                 "Child interface monitored status of fabric link";
             }
           }
         }
       }
       container control-link-failure-information {
         description
           "Display control link failure information";
         leaf control-link-status {
           type string;
           description
             "Status of control link";
         }
         leaf dual-control-link-status {
           type string;
           description
             "Enable or disabled dual control link";
         }
         container control-link-interface-state {
           leaf control-link-interface-name {
             type string;
             description
               "Chassis cluster control interface name";
           }
           leaf control-link-interface-physical-status {
             type string;
             description
               "Ifd status of control link interface";
           }
           leaf control-link-interface-monitored-status {
             type string;
             description
               "Monitored status of control link interface";
           }
         }
       }
       container schedule-monitoring-failure-information {
         description
           "Display schedule monitoring failure information";
         leaf schedule-monitoring-failure-status {
           type string;
           description
             "Status of schedule monitoring failure";
         }
         leaf schedule-monitoring-failure-clear-time {
           type uint32;
           description
             "Time to clear the failure";
         }
       }
     }
   }
   grouping configuration-synchronization-information-block {
     leaf configuration-synchronization-information-header {
       type string;
       description
         "Configuration synchronization header";
     }
     container configuration-synchronization-status {
       leaf configuration-synchronization-activation-status {
         type string;
         description
           "Configuration synchronization is enabled/disabled";
       }
       leaf configuration-synchronization-last-operation {
         type string;
         description
           "Last configuration synchronization operation";
       }
       leaf configuration-synchronization-last-result {
         type string;
         description
           "Configuration synchronization result";
       }
       container configuration-synchronization-mgd-messages {
         description
           "Configuration synchronization messages from mgd daemon";
         leaf configuration-synchronization-mgd-messages-header {
           type string;
           description
             "Configuration synchronization mgd messages header";
         }
         leaf configuration-synchronization-mgd-messages-item {
           type string;
           description
             "Configuration synchronization message from mgd daemon";
         }
       }
     }
     container configuration-synchronization-events {
       description
         "List of configuration synchronization events";
       leaf-list configuration-synchronization-event {
         type string;
         description
           "Recorded configuration synchronization events";
       }
     }
   }
   grouping issu-information-block {
     leaf-list cold-synchronization-progress {
       type string;
       description
         "Cold synchronization progress";
     }
     leaf-list chassis-cluster-issu-event {
       type string;
       description
         "ISSU events";
     }
   }
   grouping chassis-cluster-detail-information-block {
     container chassis-cluster-redundancy-mode {
       description
         "Chassis cluster configured and operational redundancy modes";
       leaf configured {
         type string;
         description
           "Configured";
       }
       leaf operational {
         type string;
         description
           "Operational";
       }
       leaf mode-mismatch-warning {
         type string;
         description
           "Chassis cluster redundancy mode mismatch warning";
       }
     }
     container chassis-cluster-configuration-information {
       description
         "Cluster configured information";
       leaf heartbeat-interval {
         type uint32;
         description
           "Heartbeat interval in ms";
       }
       leaf heartbeat-threshold {
         type uint32;
         description
           "Heartbeat threshold";
       }
       leaf control-link-recovery {
         type string;
         description
           "Control link recovery";
       }
       leaf fabric-link-timeout {
         type uint32;
         description
           "Fabric link down timeout value";
       }
       leaf ha-heartbeat-offload-disable {
         type string;
         description
           "HA heartbeat offload disable";
       }
     }
     container chassis-cluster-node-health {
       leaf local-node-health {
         type string;
         description
           "Health of current node";
       }
       leaf remote-node-health {
         type string;
         description
           "Health of remote node";
       }
     }
     container chassis-cluster-internal-statistics {
       container chassis-cluster-control-statistics {
         leaf control-interface-index {
           type uint32;
           description
             "Chassis cluster control interface index";
         }
         leaf heartbeat-sent {
           type string;
           description
             "Heartbeat packets sent on control link";
         }
         leaf heartbeat-received {
           type string;
           description
             "Heartbeat packets received on control link";
         }
         leaf heartbeat-errors {
           type string;
           description
             "Heartbeat packets dropped due to errors";
         }
         leaf heartbeat-duplicates {
           type string;
           description
             "Duplicate heartbeat packets received on control link";
         }
         leaf control-link-recovery-packet-count {
           type string;
           description
             "Hearbeat packet count to identify control link recovery";
         }
         leaf last-heartbeat-id-sent {
           type string;
           description
             "Sequence number of last heartbeat packet sent on control link";
         }
         leaf last-heartbeat-id-received {
           type string;
           description
             "Sequence number of last heartbeat packet received on control 
             link";
         }
       }
       list offload-heartbeat-statistics {
         description
           "Offloaded HA heartbeat statistics";
         leaf control-interface-index {
           type uint32;
           description
             "Chassis cluster control interface index";
         }
         leaf offload-heartbeat-connection {
           type string;
           description
             "HA offload mode connection status";
         }
         leaf offload-heartbeat-sent {
           type string;
           description
             "HA offload heartbeat sent";
         }
         leaf offload-heartbeat-received {
           type string;
           description
             "HA offload heartbeat received";
         }
         leaf offload-heartbeat-sent-jitter {
           type string;
           description
             "HA offload heartbeat sent jitter";
         }
         leaf offload-heartbeat-received-jitter {
           type string;
           description
             "HA offload heartbeat received jitter";
         }
       }
       container chassis-cluster-fabric-statistics {
         container fabric-child {
           leaf fabric-child-index {
             type uint32;
             description
               "Fabric child index";
           }
           leaf fabric-hello-sent {
             type uint32;
             description
               "Fabric hello packets sent";
           }
           leaf fabric-hello-received {
             type uint32;
             description
               "Fabric hello packets received";
           }
           leaf fabric-hello-error {
             type uint32;
             description
               "Fabric hello packets with error";
           }
         }
       }
       container chassis-cluster-swfabric-statistics {
         leaf swfabric-probe-state {
           type string;
           description
             "Swfabric probe state";
         }
         leaf swfabric-link-heartbeat-packets-sent {
           type uint64;
           description
             "Fabric probes sent";
         }
         leaf swfabric-link-heartbeat-packets-received {
           type uint64;
           description
             "Fabric probes received";
         }
         leaf swfabric-probe-recv-errors {
           type uint64;
           description
             "Fabric probes dropped due to errors";
         }
         leaf swfabric-probe-send-errors {
           type uint64;
           description
             "Fabric probes not sent due to errors";
         }
         leaf swfabric-probe-recv-dropped {
           type uint64;
           description
             "Fabric probes not processed due to errors";
         }
         leaf swfabric-last-probe-id-sent {
           type uint64;
           description
             "Sequence number of last probe sent on swfabric link";
         }
         leaf swfabric-last-probe-id-rcvd {
           type uint64;
           description
             "Sequence number of last probe received on swfabric link";
         }
       }
     }
     container chassis-cluster-led-information {
       description
         "Chassis cluster LED related information";
       leaf current-led-color {
         type string;
         description
           "Current color of the chassis cluster LED";
       }
       leaf last-change-reason {
         type string;
         description
           "Reason for last change of state/color of the chassis cluster LED";
       }
     }
     container chassis-cluster-heartbeat-offload-information {
       description
         "Chassis cluster HA heartbeat offload mode information";
       leaf chassis-cluster-heartbeat-offload-status {
         type string;
         description
           "Chassis cluster HA heartbeat offload mode status";
       }
     }
     container chassis-cluster-hld-information {
       description
         "Chassis cluster HA HLD connection information";
       leaf chassis-cluster-hld-status {
         type string;
         description
           "Chassis cluster HA HLD connection details";
       }
     }
     container control-link-vlan-information {
       description
         "Control port traffic tagging with vlan(4094) enabled or disabled";
       leaf control-link-vlan-status {
         type string;
         description
           "Control port tagging enabled or disabled";
       }
     }
     container control-link-secure-login-information {
       description
         "Control link secure login is enabled or disabled";
       leaf control-link-secure-login-status {
         type string;
         description
           "Control link secure login is enabled or disabled";
       }
     }
     container redundancy-group-information-list {
       list redundancy-group-information {
         description
           "Redundancy group related information";
         leaf redundancy-group-id {
           type int32;
           description
             "Redundancy-group id";
         }
         container redundancy-group-monitoring-information {
           leaf redundancy-group-threshold {
             type uint32;
             description
               "Current redundancy group weight";
           }
           leaf monitoring-failure-string {
             type string;
             description
               "List of current monitoring failures";
           }
         }
         container redundancy-group-state-transition-events {
           description
             "Redundancy group state transition details";
           leaf-list redundancy-group-state-transition-event {
             type string;
             description
               "State transition old state - > new state";
           }
         }
       }
     }
     container spu-monitoring-information {
       description
         "SPU monitoring related information";
       container spu-monitoring-status {
         description
           "SPU monitoring related status information";
         leaf spu-monitoring-state {
           type string;
           description
             "SPU current monitoring mode Disabled/Enabled/Active";
         }
         leaf spu-monitoring-weight {
           type uint32;
           description
             "Current SPU monitoring weight";
         }
         list spu-monitoring-spu-state {
           description
             "Each SPU current state";
           container spu-monitoring-spu-state-list {
             description
               "Each SPU current state in list";
             leaf pfe-name {
               type string;
               description
                 "Name of the PFE";
             }
             leaf pic-state {
               type string;
               description
                 "State of each PIC";
             }
           }
         }
       }
       container spu-monitoring-statistics {
         description
           "Detailed statistics of SPU monitoring";
         leaf spu-up-count {
           type uint32;
           description
             "Number of SPUs that are up";
         }
         leaf spu-down-count {
           type uint32;
           description
             "Number of SPUs that are down";
         }
         leaf npc-up-count {
           type uint32;
           description
             "Number of NPCs that are up";
         }
         leaf npc-down-count {
           type uint32;
           description
             "Number of NPCs that are down";
         }
         leaf chinfo-blob-error-count {
           type uint32;
           description
             "Error count reading chinfo blob";
         }
       }
       container spu-monitoring-events {
         description
           "List of SPU monitoring events";
         leaf-list spu-monitoring-event {
           type string;
           description
             "Recorded SPU monitoring events";
         }
       }
     }
     list loopback-information {
       description
         "Loopback information";
       container loopback-information-list {
         description
           "Display loopback information list";
         leaf pfe-name {
           type string;
           description
             "Name of the PFE";
         }
         leaf loopback-status {
           type string;
           description
             "Loopback status of each PIC";
         }
         leaf nexthop-status {
           type string;
           description
             "Nexthop status of each PIC";
         }
         leaf mbuf-status {
           type string;
           description
             "Mbuf status of each PIC";
         }
       }
     }
     container cold-synchronization-monitoring-information {
       description
         "Cold sync monitoring related information";
       leaf-list cold-synchronization-progress {
         type string;
         description
           "Cold synchronization progress";
       }
       container cold-synchronization-status-information {
         description
           "Cold synchronization related status information";
         leaf cold-synchronization-completed {
           type string;
           description
             "List of PFE's which have completed cold synchnronization";
         }
         leaf cold-synchronization-not-completed {
           type string;
           description
             "List of PFE's which have failed cold synchnronization";
         }
         leaf cold-synchronization-unknown {
           type string;
           description
             "List of PFE's for which cold synchnronization statusupdate is 
             not received";
         }
         leaf cold-synchronization-weight {
           type uint32;
           description
             "Current Cold Synchronization weight";
         }
       }
       container cold-synchronization-statistics {
         description
           "Cold synchronization statistics";
         leaf current-cold-synchronization-completed {
           type uint32;
           description
             "Cold synchronization completed for current jsrpd session";
         }
         leaf current-cold-synchronization-failed {
           type uint32;
           description
             "Cold synchronization failed for current jsrpd session";
         }
         list cold-synchronization-pfe-statistics {
           description
             "Cold synchroniizaton statistics for each PFE";
           leaf pfe-name {
             type string;
             description
               "Name of the PFE";
           }
           leaf cold-synchronization-pfe-completed {
             type uint32;
             description
               "Cold synchronization complete instances for a given PFE";
           }
           leaf cold-synchronization-pfe-failed {
             type uint32;
             description
               "Cold synchronization complete instances for a given PFE";
           }
         }
       }
       container cold-synchronization-events {
         description
           "List of cold synchronization events";
         leaf-list cold-synchronization-event {
           type string;
           description
             "Recorded cold sync complete/failure for a PFE";
         }
       }
     }
     container interface-monitoring-information {
       description
         "Interface monitoring related information";
       container interface-monitoring-statistics {
         description
           "Interface monitoring related statistics";
         leaf monitored-interface-failover-count {
           type uint32;
           description
             "Total count of monitored interface failure";
         }
       }
       container interface-monitoring-events {
         description
           "List of interface monitoring events";
         leaf-list interface-monitoring-event {
           type string;
           description
             "Recorded interface monitoring events";
         }
       }
     }
     container fabric-link-information {
       description
         "Displays complete fabric link information for debugging purposes";
       container fabric-monitoring-information {
         description
           "Fabric monitoring related information";
         container fabric-monitoring-status {
           description
             "Fabric monitoring status";
           leaf fabric-monitoring-state {
             type string;
             description
               "Fabric monitoring is enabled/disabled";
           }
           leaf fabric-monitoring-activation-status {
             type string;
             description
               "Fabric monitoring is active/suspended";
           }
           leaf fabric-monitoring-data-plane-notified-status {
             type string;
             description
               "Fabric monitoring status from data plane";
           }
           leaf fabric-monitoring-internal-status {
             type string;
             description
               "JSRPD internal fabric monitoring status";
           }
         }
       }
       container fabric-link-events {
         description
           "List of fabric link events";
         leaf-list fabric-link-event {
           type string;
           description
             "Recorded fabric link events";
         }
       }
       container fabric-link-hb-events {
         description
           "List of fabric link heartbeat and jitter events";
         leaf-list fabric-link-hb-event {
           type string;
           description
             "Recorded fabric link heartbeat events";
         }
       }
     }
     container control-link-information {
       description
         "Displays complete control link information for debugging purposes";
       leaf control-interface-status {
         type string;
         description
           "Chassis cluster control interface status";
       }
       container control-link-server-information {
         description
           "Control link server information";
         leaf server-status {
           type string;
           description
             "Control link server status";
         }
         leaf-list server-connections {
           type string;
           description
             "Information of clients connected to the server";
         }
       }
       container control-link-client-information {
         description
           "Control link client information";
         leaf client-status {
           type string;
           description
             "Control link client status";
         }
         leaf client-connections {
           type string;
           description
             "Information of server to which the connection is established";
         }
       }
       container control-link-events {
         description
           "List of control link events";
         leaf-list control-link-event {
           type string;
           description
             "Recorded control link events";
         }
       }
       container control-link-hb-events {
         description
           "List of control link monitoring heartbeat and jitter events";
         leaf-list control-link-hb-event {
           type string;
           description
             "Recorded control link monitoring heartbeat events";
         }
       }
     }
     container hardware-monitoring-information {
       description
         "Displays complete hardware monitoring information for debugging 
         purposes";
       container hardware-monitoring-status-information {
         leaf hardware-monitoring-activation-status {
           type string;
           description
             "Hardware monitoring is enabled/disabled";
         }
         leaf hardware-monitoring-rg0-failover {
           type int32;
           description
             "Hardware monitoring redundancy group 0 failover";
         }
         leaf hardware-monitoring-rg0-errors {
           type int32;
           description
             "Hardware monitoring redundancy group 0 errors";
         }
         leaf hardware-monitoring-rg1-errors {
           type int32;
           description
             "Hardware monitoring redundancy group 1 errors";
         }
       }
       container hardware-monitoring-events {
         description
           "List of hardware monitoring events";
         leaf-list hardware-monitoring-event {
           type string;
           description
             "Recorded hardware monitoring events";
         }
       }
     }
     container issu-information {
       description
         "Displays complete ISSU information for debugging purposes";
       leaf-list cold-synchronization-progress {
         type string;
         description
           "Cold synchronization progress";
       }
       leaf-list chassis-cluster-issu-event {
         type string;
         description
           "ISSU events";
       }
     }
     container command-history-information {
       description
         "Displays command history information for debugging purposes";
       leaf-list chassis-cluster-command-history-event {
         type string;
         description
           "Command history ";
       }
     }
   }
   grouping cold-synchronization-monitoring-information-block {
     leaf-list cold-synchronization-progress {
       type string;
       description
         "Cold synchronization progress";
     }
     container cold-synchronization-status-information {
       description
         "Cold synchronization related status information";
       leaf cold-synchronization-completed {
         type string;
         description
           "List of PFE's which have completed cold synchnronization";
       }
       leaf cold-synchronization-not-completed {
         type string;
         description
           "List of PFE's which have failed cold synchnronization";
       }
       leaf cold-synchronization-unknown {
         type string;
         description
           "List of PFE's for which cold synchnronization statusupdate is 
           not received";
       }
       leaf cold-synchronization-weight {
         type uint32;
         description
           "Current Cold Synchronization weight";
       }
     }
     container cold-synchronization-statistics {
       description
         "Cold synchronization statistics";
       leaf current-cold-synchronization-completed {
         type uint32;
         description
           "Cold synchronization completed for current jsrpd session";
       }
       leaf current-cold-synchronization-failed {
         type uint32;
         description
           "Cold synchronization failed for current jsrpd session";
       }
       list cold-synchronization-pfe-statistics {
         description
           "Cold synchroniizaton statistics for each PFE";
         leaf pfe-name {
           type string;
           description
             "Name of the PFE";
         }
         leaf cold-synchronization-pfe-completed {
           type uint32;
           description
             "Cold synchronization complete instances for a given PFE";
         }
         leaf cold-synchronization-pfe-failed {
           type uint32;
           description
             "Cold synchronization complete instances for a given PFE";
         }
       }
     }
     container cold-synchronization-events {
       description
         "List of cold synchronization events";
       leaf-list cold-synchronization-event {
         type string;
         description
           "Recorded cold sync complete/failure for a PFE";
       }
     }
   }
   grouping spu-monitoring-information-block {
     list spu-utilization-statistics {
       container fpc {
         description
           "FPC";
         leaf fpc-number {
           type uint32;
           description
             "FPC number";
         }
         leaf session-cps {
           type uint32;
           description
             "Session creation per second (for last 96 seconds on average)";
         }
         leaf session-cps-ipv4 {
           type uint32;
           description
             "IPv4 Session creation per second (for last 96 seconds on 
             average)";
         }
         leaf session-cps-ipv6 {
           type uint32;
           description
             "IPv6 Session creation per second (for last 96 seconds on 
             average)";
         }
         leaf session-cps2 {
           type uint32;
           description
             "Session creation per second (for last 96 seconds on average)";
         }
         leaf session-cps2-ipv4 {
           type uint32;
           description
             "IPv4 Session creation per second (for last 96 seconds on 
             average)";
         }
         leaf session-cps2-ipv6 {
           type uint32;
           description
             "IPv6 Session creation per second (for last 96 seconds on 
             average)";
         }
         container pic {
           description
             "PIC stats";
           leaf pic-number {
             type uint32;
             description
               "PIC number";
           }
           leaf spu-cpu-utilization {
             type uint32;
             description
               "SPU CPU utilization in percentage";
           }
           leaf spu-memory-utilization {
             type uint32;
             description
               "SPU memory utilization in percentage";
           }
           leaf spu-current-flow-session {
             type uint32;
             description
               "SPU current flow session";
           }
           leaf spu-current-flow-session-ipv4 {
             type uint32;
             description
               "SPU current IPv4 flow session";
           }
           leaf spu-current-flow-session-ipv6 {
             type uint32;
             description
               "SPU current IPv6 flow session";
           }
           leaf spu-max-flow-session {
             type uint32;
             description
               "SPU max flow session";
           }
           leaf spu-current-cp-session {
             type uint32;
             description
               "SPU current cp session";
           }
           leaf spu-current-cp-session-ipv4 {
             type uint32;
             description
               "SPU current IPv4 cp session";
           }
           leaf spu-current-cp-session-ipv6 {
             type uint32;
             description
               "SPU current IPv6 cp session";
           }
           leaf spu-max-cp-session {
             type uint32;
             description
               "SPU max cp session";
           }
         }
       }
     }
     container spu-monitoring-status {
       description
         "SPU monitoring related status information";
       leaf spu-monitoring-state {
         type string;
         description
           "SPU current monitoring mode Disabled/Enabled/Active";
       }
       leaf spu-monitoring-weight {
         type uint32;
         description
           "Current SPU monitoring weight";
       }
       list spu-monitoring-spu-state {
         description
           "Each SPU current state";
         container spu-monitoring-spu-state-list {
           description
             "Each SPU current state in list";
           leaf pfe-name {
             type string;
             description
               "Name of the PFE";
           }
           leaf pic-state {
             type string;
             description
               "State of each PIC";
           }
         }
       }
     }
     container spu-monitoring-statistics {
       description
         "Detailed statistics of SPU monitoring";
       leaf spu-up-count {
         type uint32;
         description
           "Number of SPUs that are up";
       }
       leaf spu-down-count {
         type uint32;
         description
           "Number of SPUs that are down";
       }
       leaf npc-up-count {
         type uint32;
         description
           "Number of NPCs that are up";
       }
       leaf npc-down-count {
         type uint32;
         description
           "Number of NPCs that are down";
       }
       leaf chinfo-blob-error-count {
         type uint32;
         description
           "Error count reading chinfo blob";
       }
     }
     container spu-monitoring-events {
       description
         "List of SPU monitoring events";
       leaf-list spu-monitoring-event {
         type string;
         description
           "Recorded SPU monitoring events";
       }
     }
   }
   grouping loopback-information-block {
     container loopback-information-list {
       description
         "Display loopback information list";
       leaf pfe-name {
         type string;
         description
           "Name of the PFE";
       }
       leaf loopback-status {
         type string;
         description
           "Loopback status of each PIC";
       }
       leaf nexthop-status {
         type string;
         description
           "Nexthop status of each PIC";
       }
       leaf mbuf-status {
         type string;
         description
           "Mbuf status of each PIC";
       }
     }
   }
   grouping hardware-monitoring-information-block {
     container hardware-monitoring-status-information {
       leaf hardware-monitoring-activation-status {
         type string;
         description
           "Hardware monitoring is enabled/disabled";
       }
       leaf hardware-monitoring-rg0-failover {
         type int32;
         description
           "Hardware monitoring redundancy group 0 failover";
       }
       leaf hardware-monitoring-rg0-errors {
         type int32;
         description
           "Hardware monitoring redundancy group 0 errors";
       }
       leaf hardware-monitoring-rg1-errors {
         type int32;
         description
           "Hardware monitoring redundancy group 1 errors";
       }
     }
     container hardware-monitoring-events {
       description
         "List of hardware monitoring events";
       leaf-list hardware-monitoring-event {
         type string;
         description
           "Recorded hardware monitoring events";
       }
     }
   }
   grouping schedule-monitoring-information-block {
     leaf schedule-monitoring-information-header {
       type string;
       description
         "Schedule monitoring header";
     }
     container schedule-monitoring-status {
       leaf schedule-monitoring-activation-status {
         type string;
         description
           "Schedule monitoring is enabled/disabled";
       }
       leaf schedule-monitoring-slip-detected {
         type string;
         description
           "Schedule slip detection status";
       }
       leaf schedule-monitoring-timers-ignored {
         type string;
         description
           "Ignore timer flag status";
       }
     }
     container schedule-monitoring-statistics {
       description
         "Statistics of slip duration and count";
       leaf schedule-monitoring-total-slip-count {
         type uint32;
         description
           "Total count of slip detected";
       }
       leaf schedule-monitoring-max-slip-duration {
         type uint32;
         description
           "The longest slip duration";
       }
     }
     container schedule-monitoring-events {
       description
         "List of schedule monitoring events";
       leaf-list schedule-monitoring-event {
         type string;
         description
           "Recorded schedule monitoring events";
       }
     }
   }
   grouping interface-monitoring-information-block {
     container interface-monitoring-statistics {
       description
         "Interface monitoring related statistics";
       leaf monitored-interface-failover-count {
         type uint32;
         description
           "Total count of monitored interface failure";
       }
     }
     container interface-monitoring-events {
       description
         "List of interface monitoring events";
       leaf-list interface-monitoring-event {
         type string;
         description
           "Recorded interface monitoring events";
       }
     }
   }
   grouping control-link-information-block {
     leaf control-interface-status {
       type string;
       description
         "Chassis cluster control interface status";
     }
     container control-link-server-information {
       description
         "Control link server information";
       leaf server-status {
         type string;
         description
           "Control link server status";
       }
       leaf-list server-connections {
         type string;
         description
           "Information of clients connected to the server";
       }
     }
     container control-link-client-information {
       description
         "Control link client information";
       leaf client-status {
         type string;
         description
           "Control link client status";
       }
       leaf client-connections {
         type string;
         description
           "Information of server to which the connection is established";
       }
     }
     container control-link-events {
       description
         "List of control link events";
       leaf-list control-link-event {
         type string;
         description
           "Recorded control link events";
       }
     }
     container control-link-hb-events {
       description
         "List of control link monitoring heartbeat and jitter events";
       leaf-list control-link-hb-event {
         type string;
         description
           "Recorded control link monitoring heartbeat events";
       }
     }
   }
   grouping fabric-link-information-block {
     container fabric-monitoring-information {
       description
         "Fabric monitoring related information";
       container fabric-monitoring-status {
         description
           "Fabric monitoring status";
         leaf fabric-monitoring-state {
           type string;
           description
             "Fabric monitoring is enabled/disabled";
         }
         leaf fabric-monitoring-activation-status {
           type string;
           description
             "Fabric monitoring is active/suspended";
         }
         leaf fabric-monitoring-data-plane-notified-status {
           type string;
           description
             "Fabric monitoring status from data plane";
         }
         leaf fabric-monitoring-internal-status {
           type string;
           description
             "JSRPD internal fabric monitoring status";
         }
       }
     }
     container fabric-link-events {
       description
         "List of fabric link events";
       leaf-list fabric-link-event {
         type string;
         description
           "Recorded fabric link events";
       }
     }
     container fabric-link-hb-events {
       description
         "List of fabric link heartbeat and jitter events";
       leaf-list fabric-link-hb-event {
         type string;
         description
           "Recorded fabric link heartbeat events";
       }
     }
   }
   grouping command-history-information-block {
     leaf-list chassis-cluster-command-history-event {
       type string;
       description
         "Command history ";
     }
   }
   grouping chassis-cluster-ip-monitoring-block {
     leaf redundancy-group {
       type int32;
       description
         "Redundancy group for IP monitoring";
     }
     leaf ip-monitoring-global-weight {
       type int32;
       description
         "Global weight for the IP monitoring";
     }
     leaf ip-monitoring-global-threshold {
       type int32;
       description
         "Global threshold of IP-monitoring";
     }
     leaf ip-monitoring-current-threshold {
       type int32;
       description
         "Current threshold of IP-monitoring";
     }
     leaf ip-address {
       type jt:ipaddr;
       description
         "IPv4 address that is being monitored";
     }
     leaf ip-reachability-status {
       type string;
       description
         "IP address reachability status";
     }
     leaf failure-count {
       type uint32;
       description
         "Indicates the number of times an IP became unreachable";
     }
     leaf ip-monitoring-weight {
       type int32;
       description
         "Weight associated with this IP";
     }
     leaf ip-unreachable-reason {
       type string;
       description
         "Reason for IP reachability failure";
     }
   }
   grouping chassis-cluster-ethernet-switching-status-block {
     leaf ethernet-switching-status {
       type string;
       description
         "Ethernet switching status";
     }
     list chassis-cluster-status {
       leaf cluster-id {
         type int32;
         description
           "Cluster id";
       }
       container redundancy-group {
         description
           "Redundancy group for IP monitoring";
         leaf redundancy-group-id {
           type int32;
           description
             "Redundancy-group id";
         }
         leaf redundancy-group-failover-count {
           type int32;
           description
             "No of transitions between primary and secondary states";
         }
         list device-stats {
           leaf device-name {
             type string;
             description
               "Node name";
           }
           leaf device-priority {
             type int32;
             description
               "Configured priority of the device";
           }
           leaf redundancy-group-status {
             type string;
             description
               "Status of the redundancy group";
           }
           leaf preempt {
             type string;
             description
               "Preempt configuration for the redundancy group";
           }
           leaf failover-mode {
             type string;
             description
               "Manual failover mode for the redundancy group";
           }
           leaf monitor-failures {
             type string;
             description
               "Monitoring failures for the redundancy group";
           }
         }
       }
     }
   }
   grouping chassis-cluster-ethernet-switching-statistics-block {
     list chassis-cluster-swfabric {
       leaf swfabric-probe-state {
         type string;
         description
           "Swfabric probe state";
       }
       leaf swfabric-link-heartbeat-packets-sent {
         type uint64;
         description
           "Fabric probes sent";
       }
       leaf swfabric-link-heartbeat-packets-received {
         type uint64;
         description
           "Fabric probes received";
       }
       leaf swfabric-probe-recv-errors {
         type uint64;
         description
           "Fabric probes dropped due to errors";
       }
       leaf swfabric-probe-send-errors {
         type uint64;
         description
           "Fabric probes not sent due to errors";
       }
     }
   }
   grouping chassis-cluster-ethernet-switching-interfaces-block {
     leaf swfabric-interface-index {
       type uint32;
       description
         "Chassis cluster switch fabric interface index";
     }
     container swfabric-information {
       leaf swfab-child-interface-name {
         type string;
         description
           "Child interface name";
       }
       leaf swfab-child-interface-status {
         type string;
         description
           "Connection status of child interface";
       }
     }
   }
   grouping chassis-cluster-port-peering-status-block {
     container port-peering-interfaces {
       list port-peering-information {
         leaf redundant-backend-interface-name {
           type string;
           description
             "Backend L3 interface name";
         }
         leaf redundant-backend-interface-status {
           type string;
           description
             "L3 interface status";
         }
         leaf mapped-interface-name {
           type string;
           description
             "Mapping L2 interface name";
         }
         leaf mapped-interface-status {
           type string;
           description
             "L2 interface status";
         }
       }
     }
   }
   grouping chassis-high-availability-info-block {
     leaf node-status {
       type string;
       description
         "Status of the current node";
     }
     leaf grid-id {
       type int32;
       description
         "Grid identifier";
     }
     leaf local-id {
       type int32;
       description
         "Local node identifier";
     }
     leaf local-ip {
       type jt:ipaddr;
       description
         "Local node IPv4 address";
     }
     leaf local-fwd-ip {
       type jt:ipaddr;
       description
         "Local Forwarding IP address";
     }
     container chassis-high-availability-info-mnha {
       description
         "Displays 4 node mnha info";
       container chassis-mnha-local-domain-info {
         description
           "Displays high-availability peer related info";
         leaf node-status {
           type string;
           description
             "Status of the current node";
         }
         leaf local-domain-id {
           type int32;
           description
             "Local-domain-id";
         }
         leaf local-id {
           type int32;
           description
             "Local node identifier";
         }
         leaf local-ip {
           type jt:ipaddr;
           description
             "Local node IPv4 address";
         }
         leaf high-availability-peer-desc {
           type string;
           description
             "Peer description";
         }
         leaf high-availability-peer-id {
           type int32;
           description
             "Peer identifier that is configured";
         }
         leaf high-availability-peer-ip-address {
           type jt:ipaddr;
           description
             "Peer remote IPv4 address that is configured";
         }
         leaf-list high-availability-local-interface {
           type string;
           description
             "Local interface";
         }
         leaf high-availability-peer-rt-instance {
           type string;
           description
             "Routing Instance name for HA peer";
         }
         leaf high-availability-peer-encryption-status {
           type string;
           description
             "Encryption status of the current node";
         }
         leaf high-availability-peer-icl-bfd-status {
           type string;
           description
             "ICL BFD Status of the current node";
         }
         leaf high-availability-peer-detect-time {
           type string;
           description
             "Configured Peer BFD detection time";
         }
         leaf cold-sync-status {
           type string;
           description
             "Cold synchronization status";
         }
         leaf rtt-result {
           type string;
           description
             "RTT result";
         }
         leaf srg0-cold-sync-status {
           type string;
           description
             "SRG0 cold sync status";
         }
         leaf local-fwd-ip {
           type jt:ipaddr;
           description
             "Local Forwarding IP address";
         }
         leaf peer-hw-incompatible {
           type string;
           description
             "Peer hardware compatible status";
         }
         leaf high-availability-peer-fwd-ip-address {
           type jt:ipaddr;
           description
             "Peer forwarding remote IP address";
         }
         leaf high-availability-local-fwd-interface {
           type string;
           description
             "Local forwarding interface";
         }
         leaf high-availability-peer-fwd-bfd-status {
           type string;
           description
             "BFD forwarding status of the current node";
         }
       }
       container chassis-mnha-peer-domain-info {
         description
           "Displays mnha peer domain info";
         leaf peer-domain-info {
           type string;
           description
             "Peer-domain-info";
         }
         leaf peer-domain-id {
           type int32;
           description
             "Peer-domain-id";
         }
         leaf-list peer-local-ip {
           type jt:ipaddr;
           description
             "Peer node IPv4 address";
         }
         container chassis-high-availability-default-srg-info {
           description
             "Displays high-availability services redundancy group 0 info";
           leaf current-state {
             type string;
             description
               "SRG 0 current state";
           }
           leaf peer-id {
             type int32;
             description
               "Peer identifier";
           }
           leaf node-priority {
             type int32;
             description
               "Node-priority";
           }
           leaf peer-domain-id {
             type int32;
             description
               "Peer-domain-id";
           }
           list srg-peer-domain-peer-id-info {
             description
               "Idl peer node Id";
             leaf idl-peer-id {
               type int32;
               description
                 "IDL Peer identifier";
             }
           }
           container high-availability-srg-signal-rt-info {
             description
               "  SRG Signal route Info";
             list ha-srg-signal-rt-list {
               description
                 "Display each signal route information";
               leaf ha-srg-signal-rt-type {
                 type string;
                 description
                   "  SRG  Signal route type";
               }
               leaf ha-srg-signal-rt-ipaddr {
                 type string;
                 description
                   "IP address configured as SRG active signal route";
               }
               leaf ha-srg-signal-rt-rt {
                 type string;
                 description
                   "Routing table configured for active signal route";
               }
               leaf ha-srg-signal-rt-status {
                 type string;
                 description
                   " SRG signal Route installation status";
               }
             }
           }
           list chassis-high-availability-shutdown-interface {
             description
               "Display high-availability shutdown interface list";
             leaf high-availability-shutdown-interface-name {
               type string;
               description
                 "Interface name for monitoring";
             }
           }
           container chassis-high-availability-srg-ipmon {
             description
               "SRG IP monitoring Info";
             leaf ha-srg-ipmon-status {
               type string;
               description
                 "SRG overall IP-monitoring status";
             }
             container chassis-high-availability-srg-ipmon-list {
               description
                 " Display each IP monitoring entry";
               leaf ha-srg-ipmon-dst-ipaddr {
                 type string;
                 description
                   "Destination IP address configured for HA ip-monitoring";
               }
               leaf ha-srg-ipmon-rt {
                 type string;
                 description
                   "Routing instance configured for HA ip-monitoring";
               }
               leaf ha-ipmon-status {
                 type string;
                 description
                   "HA ip-monitoring status";
               }
               leaf ha-srg-ipmon-reason {
                 type string;
                 description
                   "HA ip-monitoring failure reason";
               }
             }
           }
           container chassis-high-availability-srg-bfdmon {
             description
               " SRG BFD mon information ";
             leaf ha-srg-bfdmon-status {
               type string;
               description
                 "HA overall bfd-monitoring status";
             }
             container chassis-high-availability-srg-bfdmon-list {
               description
                 " Display each BFD mon entry Information";
               leaf ha-srg-bfdmon-src-ipaddr {
                 type string;
                 description
                   "Source IP address configured for HA bfd-monitoring";
               }
               leaf ha-srg-bfdmon-dst-ipaddr {
                 type string;
                 description
                   "Destination IP address configured for HA bfd-monitoring";
               }
               leaf ha-srg-bfdmon-rt {
                 type string;
                 description
                   "Routing instance configured for HA bfd-monitoring";
               }
               leaf ha-srg-bfdmon-type {
                 type string;
                 description
                   "HA bfd-monitoring type";
               }
               leaf ha-srg-bfdmon-ifl-name {
                 type string;
                 description
                   "HA bfd-monitoring IFL name";
               }
               leaf ha-srg-bfdmon-state {
                 type string;
                 description
                   "HA bfd-monitoring state";
               }
             }
           }
           container chassis-high-availability-srg-ifmon {
             description
               "SRG Interface monitoring Info";
             leaf ha-srg-ifmon-status {
               type string;
               description
                 "HA overall Interface-monitoring status";
             }
             container chassis-high-availability-srg-ifmon-list {
               description
                 " Display each Interface monitoring entry";
               leaf ha-srg-ifmon-if-name {
                 type string;
                 description
                   "HA Interface-monitoring IF name";
               }
               leaf ha-srg-ifmon-state {
                 type string;
                 description
                   "HA Interface-monitoring state";
               }
             }
           }
           container chassis-high-availability-srg-mon-info {
             description
               "SRG global threshold info";
             leaf ha-srg-mon-status {
               type string;
               description
                 "SRG monitor status";
             }
             leaf ha-srg-mon-threshold {
               type int32;
               description
                 "SRG monitor threshold";
             }
             leaf ha-srg-mon-weight {
               type int32;
               description
                 "SRG monitor weight";
             }
             leaf ha-srg-mon-failed-objects {
               type int32;
               description
                 "SRG monitor failed objects";
             }
           }
           container chassis-high-availability-srg-obj-info {
             description
               "SRG monitor-object info";
             leaf ha-srg-obj-name {
               type string;
               description
                 "SRG monitor object name";
             }
             leaf ha-srg-obj-status {
               type string;
               description
                 "SRG monitor object status";
             }
             leaf ha-srg-obj-entries {
               type string;
               description
                 "SRG monitor object monitored entries";
             }
             leaf ha-srg-obj-failure {
               type string;
               description
                 "SRG monitor object monitored failures";
             }
             leaf ha-srg-obj-threshold {
               type int32;
               description
                 "SRG monitor object threshold";
             }
             leaf ha-srg-obj-weight {
               type int32;
               description
                 "SRG monitor object current weight";
             }
           }
           container chassis-high-availability-srg-obj-ipmon {
             description
               "SRG monitor object IP monitoring Info";
             leaf ha-srg-obj-ipmon-threshold {
               type int32;
               description
                 "SRG monitor object IP-monitoring threshold";
             }
             leaf ha-srg-obj-ipmon-weight {
               type int32;
               description
                 "SRG monitor object IP-monitoring weight";
             }
             leaf ha-srg-obj-ipmon-status {
               type string;
               description
                 "SRG monitor object IP-monitoring global status";
             }
             container chassis-high-availability-srg-obj-ipmon-list {
               description
                 " Display each monitor object IP monitoring entry status";
               leaf ha-srg-obj-ipmon-entry-status {
                 type string;
                 description
                   "HA SRG monitor object ip-monitoring state";
               }
               leaf ha-srg-obj-ipmon-entry-weight {
                 type int32;
                 description
                   "HA SRG monitor object ip-monitoring weight";
               }
               leaf ha-srg-obj-ipmon-entry-dst-ipaddr {
                 type string;
                 description
                   "Destination IP address configured for HA ip-monitoring";
               }
             }
           }
           container chassis-high-availability-srg-obj-ipmon-detail {
             description
               "SRG monitor object IP monitoring detail Info";
             container chassis-high-availability-srg-ipmon-list {
               description
                 " Display each IP monitoring entry";
               leaf ha-srg-ipmon-dst-ipaddr {
                 type string;
                 description
                   "Destination IP address configured for HA ip-monitoring";
               }
               leaf ha-srg-ipmon-rt {
                 type string;
                 description
                   "Routing instance configured for HA ip-monitoring";
               }
               leaf ha-ipmon-status {
                 type string;
                 description
                   "HA ip-monitoring status";
               }
               leaf ha-srg-ipmon-reason {
                 type string;
                 description
                   "HA ip-monitoring failure reason";
               }
             }
           }
           container chassis-high-availability-srg-obj-bfdmon {
             description
               "SRG monitor object BFD monitoring Info";
             leaf ha-srg-obj-bfdmon-threshold {
               type int32;
               description
                 "SRG monitor object BFD-monitoring threshold";
             }
             leaf ha-srg-obj-bfdmon-weight {
               type int32;
               description
                 "SRG monitor object BFD-monitoring weight";
             }
             leaf ha-srg-obj-bfdmon-status {
               type string;
               description
                 "SRG monitor object BFD-monitoring global status";
             }
             container chassis-high-availability-srg-obj-bfdmon-list {
               description
                 "Display each monitor object BFD monitoring entry status";
               leaf ha-srg-obj-bfdmon-entry-status {
                 type string;
                 description
                   "HA SRG monitor object BFD-monitoring state";
               }
               leaf ha-srg-obj-bfdmon-entry-weight {
                 type int32;
                 description
                   "HA SRG monitor object BFD-monitoring weight";
               }
               leaf ha-srg-obj-bfdmon-entry-dst-bfdaddr {
                 type string;
                 description
                   "Destination BFD address configured for HA BFD-monitoring";
               }
             }
           }
           container chassis-high-availability-srg-obj-bfdmon-detail {
             description
               "SRG monitor object BFD mon information ";
             container chassis-high-availability-srg-bfdmon-list {
               description
                 " Display each BFD mon entry Information";
               leaf ha-srg-bfdmon-src-ipaddr {
                 type string;
                 description
                   "Source IP address configured for HA bfd-monitoring";
               }
               leaf ha-srg-bfdmon-dst-ipaddr {
                 type string;
                 description
                   "Destination IP address configured for HA bfd-monitoring";
               }
               leaf ha-srg-bfdmon-rt {
                 type string;
                 description
                   "Routing instance configured for HA bfd-monitoring";
               }
               leaf ha-srg-bfdmon-type {
                 type string;
                 description
                   "HA bfd-monitoring type";
               }
               leaf ha-srg-bfdmon-ifl-name {
                 type string;
                 description
                   "HA bfd-monitoring IFL name";
               }
               leaf ha-srg-bfdmon-state {
                 type string;
                 description
                   "HA bfd-monitoring state";
               }
             }
           }
           container chassis-high-availability-srg-obj-ifmon {
             description
               "SRG monitor object IF monitoring Info";
             leaf ha-srg-obj-ifmon-threshold {
               type int32;
               description
                 "SRG monitor object IF-monitoring threshold";
             }
             leaf ha-srg-obj-ifmon-weight {
               type int32;
               description
                 "SRG monitor object IF-monitoring current weight";
             }
             leaf ha-srg-ifmon-status {
               type string;
               description
                 "HA overall Interface-monitoring status";
             }
             container chassis-high-availability-srg-obj-ifmon-list {
               description
                 "Display each monitor object IF monitoring entry status";
               leaf ha-srg-ifmon-entry-status {
                 type string;
                 description
                   "HA SRG monitor object IF-monitoring entry status";
               }
               leaf ha-srg-obj-ifmon-entry-weight {
                 type int32;
                 description
                   "HA SRG monitor object IF-monitoring entry weight";
               }
               leaf ha-srg-ifmon-if-name {
                 type string;
                 description
                   "HA Interface-monitoring IF name";
               }
             }
           }
         }
         list chassis-mnha-peer-node-info {
           description
             "Displays mnha peer node related info";
           leaf-list peer-local-ip {
             type jt:ipaddr;
             description
               "Peer node IPv4 address";
           }
           leaf high-availability-peer-desc {
             type string;
             description
               "Peer description";
           }
           leaf high-availability-peer-id {
             type int32;
             description
               "Peer identifier that is configured";
           }
           leaf high-availability-peer-ip-address {
             type jt:ipaddr;
             description
               "Peer remote IPv4 address that is configured";
           }
           leaf-list high-availability-local-interface {
             type string;
             description
               "Local interface";
           }
           leaf high-availability-peer-rt-instance {
             type string;
             description
               "Routing Instance name for HA peer";
           }
           leaf high-availability-peer-encryption-status {
             type string;
             description
               "Encryption status of the current node";
           }
           leaf high-availability-peer-idl-bfd-status {
             type string;
             description
               "IDL BFD Status of the current node";
           }
           leaf high-availability-peer-detect-time {
             type string;
             description
               "Configured Peer BFD detection time";
           }
           leaf cold-sync-status {
             type string;
             description
               "Cold synchronization status";
           }
           leaf rtt-result {
             type string;
             description
               "RTT result";
           }
           leaf srg0-cold-sync-status {
             type string;
             description
               "SRG0 cold sync status";
           }
           leaf peer-hw-incompatible {
             type string;
             description
               "Peer hardware compatible status";
           }
           leaf high-availability-peer-fwd-ip-address {
             type jt:ipaddr;
             description
               "Peer forwarding remote IP address";
           }
           leaf high-availability-local-fwd-interface {
             type string;
             description
               "Local forwarding interface";
           }
           leaf high-availability-peer-fwd-bfd-status {
             type string;
             description
               "BFD forwarding status of the current node";
           }
           container chassis-high-availability-default-srg-info {
             description
               "Displays high-availability services redundancy group 0 info";
             leaf current-state {
               type string;
               description
                 "SRG 0 current state";
             }
             leaf peer-id {
               type int32;
               description
                 "Peer identifier";
             }
             leaf node-priority {
               type int32;
               description
                 "Node-priority";
             }
             leaf peer-domain-id {
               type int32;
               description
                 "Peer-domain-id";
             }
             list srg-peer-domain-peer-id-info {
               description
                 "Idl peer node Id";
               leaf idl-peer-id {
                 type int32;
                 description
                   "IDL Peer identifier";
               }
             }
             container high-availability-srg-signal-rt-info {
               description
                 "  SRG Signal route Info";
               list ha-srg-signal-rt-list {
                 description
                   "Display each signal route information";
                 leaf ha-srg-signal-rt-type {
                   type string;
                   description
                     "  SRG  Signal route type";
                 }
                 leaf ha-srg-signal-rt-ipaddr {
                   type string;
                   description
                     "IP address configured as SRG active signal route";
                 }
                 leaf ha-srg-signal-rt-rt {
                   type string;
                   description
                     "Routing table configured for active signal route";
                 }
                 leaf ha-srg-signal-rt-status {
                   type string;
                   description
                     " SRG signal Route installation status";
                 }
               }
             }
             list chassis-high-availability-shutdown-interface {
               description
                 "Display high-availability shutdown interface list";
               leaf high-availability-shutdown-interface-name {
                 type string;
                 description
                   "Interface name for monitoring";
               }
             }
             container chassis-high-availability-srg-ipmon {
               description
                 "SRG IP monitoring Info";
               leaf ha-srg-ipmon-status {
                 type string;
                 description
                   "SRG overall IP-monitoring status";
               }
               container chassis-high-availability-srg-ipmon-list {
                 description
                   " Display each IP monitoring entry";
                 leaf ha-srg-ipmon-dst-ipaddr {
                   type string;
                   description
                     "Destination IP address configured for HA ip-monitoring";
                 }
                 leaf ha-srg-ipmon-rt {
                   type string;
                   description
                     "Routing instance configured for HA ip-monitoring";
                 }
                 leaf ha-ipmon-status {
                   type string;
                   description
                     "HA ip-monitoring status";
                 }
                 leaf ha-srg-ipmon-reason {
                   type string;
                   description
                     "HA ip-monitoring failure reason";
                 }
               }
             }
             container chassis-high-availability-srg-bfdmon {
               description
                 " SRG BFD mon information ";
               leaf ha-srg-bfdmon-status {
                 type string;
                 description
                   "HA overall bfd-monitoring status";
               }
               container chassis-high-availability-srg-bfdmon-list {
                 description
                   " Display each BFD mon entry Information";
                 leaf ha-srg-bfdmon-src-ipaddr {
                   type string;
                   description
                     "Source IP address configured for HA bfd-monitoring";
                 }
                 leaf ha-srg-bfdmon-dst-ipaddr {
                   type string;
                   description
                     "Destination IP address configured for HA 
                     bfd-monitoring";
                 }
                 leaf ha-srg-bfdmon-rt {
                   type string;
                   description
                     "Routing instance configured for HA bfd-monitoring";
                 }
                 leaf ha-srg-bfdmon-type {
                   type string;
                   description
                     "HA bfd-monitoring type";
                 }
                 leaf ha-srg-bfdmon-ifl-name {
                   type string;
                   description
                     "HA bfd-monitoring IFL name";
                 }
                 leaf ha-srg-bfdmon-state {
                   type string;
                   description
                     "HA bfd-monitoring state";
                 }
               }
             }
             container chassis-high-availability-srg-ifmon {
               description
                 "SRG Interface monitoring Info";
               leaf ha-srg-ifmon-status {
                 type string;
                 description
                   "HA overall Interface-monitoring status";
               }
               container chassis-high-availability-srg-ifmon-list {
                 description
                   " Display each Interface monitoring entry";
                 leaf ha-srg-ifmon-if-name {
                   type string;
                   description
                     "HA Interface-monitoring IF name";
                 }
                 leaf ha-srg-ifmon-state {
                   type string;
                   description
                     "HA Interface-monitoring state";
                 }
               }
             }
             container chassis-high-availability-srg-mon-info {
               description
                 "SRG global threshold info";
               leaf ha-srg-mon-status {
                 type string;
                 description
                   "SRG monitor status";
               }
               leaf ha-srg-mon-threshold {
                 type int32;
                 description
                   "SRG monitor threshold";
               }
               leaf ha-srg-mon-weight {
                 type int32;
                 description
                   "SRG monitor weight";
               }
               leaf ha-srg-mon-failed-objects {
                 type int32;
                 description
                   "SRG monitor failed objects";
               }
             }
             container chassis-high-availability-srg-obj-info {
               description
                 "SRG monitor-object info";
               leaf ha-srg-obj-name {
                 type string;
                 description
                   "SRG monitor object name";
               }
               leaf ha-srg-obj-status {
                 type string;
                 description
                   "SRG monitor object status";
               }
               leaf ha-srg-obj-entries {
                 type string;
                 description
                   "SRG monitor object monitored entries";
               }
               leaf ha-srg-obj-failure {
                 type string;
                 description
                   "SRG monitor object monitored failures";
               }
               leaf ha-srg-obj-threshold {
                 type int32;
                 description
                   "SRG monitor object threshold";
               }
               leaf ha-srg-obj-weight {
                 type int32;
                 description
                   "SRG monitor object current weight";
               }
             }
             container chassis-high-availability-srg-obj-ipmon {
               description
                 "SRG monitor object IP monitoring Info";
               leaf ha-srg-obj-ipmon-threshold {
                 type int32;
                 description
                   "SRG monitor object IP-monitoring threshold";
               }
               leaf ha-srg-obj-ipmon-weight {
                 type int32;
                 description
                   "SRG monitor object IP-monitoring weight";
               }
               leaf ha-srg-obj-ipmon-status {
                 type string;
                 description
                   "SRG monitor object IP-monitoring global status";
               }
               container chassis-high-availability-srg-obj-ipmon-list {
                 description
                   " Display each monitor object IP monitoring entry status";
                 leaf ha-srg-obj-ipmon-entry-status {
                   type string;
                   description
                     "HA SRG monitor object ip-monitoring state";
                 }
                 leaf ha-srg-obj-ipmon-entry-weight {
                   type int32;
                   description
                     "HA SRG monitor object ip-monitoring weight";
                 }
                 leaf ha-srg-obj-ipmon-entry-dst-ipaddr {
                   type string;
                   description
                     "Destination IP address configured for HA ip-monitoring";
                 }
               }
             }
             container chassis-high-availability-srg-obj-ipmon-detail {
               description
                 "SRG monitor object IP monitoring detail Info";
               container chassis-high-availability-srg-ipmon-list {
                 description
                   " Display each IP monitoring entry";
                 leaf ha-srg-ipmon-dst-ipaddr {
                   type string;
                   description
                     "Destination IP address configured for HA ip-monitoring";
                 }
                 leaf ha-srg-ipmon-rt {
                   type string;
                   description
                     "Routing instance configured for HA ip-monitoring";
                 }
                 leaf ha-ipmon-status {
                   type string;
                   description
                     "HA ip-monitoring status";
                 }
                 leaf ha-srg-ipmon-reason {
                   type string;
                   description
                     "HA ip-monitoring failure reason";
                 }
               }
             }
             container chassis-high-availability-srg-obj-bfdmon {
               description
                 "SRG monitor object BFD monitoring Info";
               leaf ha-srg-obj-bfdmon-threshold {
                 type int32;
                 description
                   "SRG monitor object BFD-monitoring threshold";
               }
               leaf ha-srg-obj-bfdmon-weight {
                 type int32;
                 description
                   "SRG monitor object BFD-monitoring weight";
               }
               leaf ha-srg-obj-bfdmon-status {
                 type string;
                 description
                   "SRG monitor object BFD-monitoring global status";
               }
               container chassis-high-availability-srg-obj-bfdmon-list {
                 description
                   "Display each monitor object BFD monitoring entry status";
                 leaf ha-srg-obj-bfdmon-entry-status {
                   type string;
                   description
                     "HA SRG monitor object BFD-monitoring state";
                 }
                 leaf ha-srg-obj-bfdmon-entry-weight {
                   type int32;
                   description
                     "HA SRG monitor object BFD-monitoring weight";
                 }
                 leaf ha-srg-obj-bfdmon-entry-dst-bfdaddr {
                   type string;
                   description
                     "Destination BFD address configured for HA 
                     BFD-monitoring";
                 }
               }
             }
             container chassis-high-availability-srg-obj-bfdmon-detail {
               description
                 "SRG monitor object BFD mon information ";
               container chassis-high-availability-srg-bfdmon-list {
                 description
                   " Display each BFD mon entry Information";
                 leaf ha-srg-bfdmon-src-ipaddr {
                   type string;
                   description
                     "Source IP address configured for HA bfd-monitoring";
                 }
                 leaf ha-srg-bfdmon-dst-ipaddr {
                   type string;
                   description
                     "Destination IP address configured for HA 
                     bfd-monitoring";
                 }
                 leaf ha-srg-bfdmon-rt {
                   type string;
                   description
                     "Routing instance configured for HA bfd-monitoring";
                 }
                 leaf ha-srg-bfdmon-type {
                   type string;
                   description
                     "HA bfd-monitoring type";
                 }
                 leaf ha-srg-bfdmon-ifl-name {
                   type string;
                   description
                     "HA bfd-monitoring IFL name";
                 }
                 leaf ha-srg-bfdmon-state {
                   type string;
                   description
                     "HA bfd-monitoring state";
                 }
               }
             }
             container chassis-high-availability-srg-obj-ifmon {
               description
                 "SRG monitor object IF monitoring Info";
               leaf ha-srg-obj-ifmon-threshold {
                 type int32;
                 description
                   "SRG monitor object IF-monitoring threshold";
               }
               leaf ha-srg-obj-ifmon-weight {
                 type int32;
                 description
                   "SRG monitor object IF-monitoring current weight";
               }
               leaf ha-srg-ifmon-status {
                 type string;
                 description
                   "HA overall Interface-monitoring status";
               }
               container chassis-high-availability-srg-obj-ifmon-list {
                 description
                   "Display each monitor object IF monitoring entry status";
                 leaf ha-srg-ifmon-entry-status {
                   type string;
                   description
                     "HA SRG monitor object IF-monitoring entry status";
                 }
                 leaf ha-srg-obj-ifmon-entry-weight {
                   type int32;
                   description
                     "HA SRG monitor object IF-monitoring entry weight";
                 }
                 leaf ha-srg-ifmon-if-name {
                   type string;
                   description
                     "HA Interface-monitoring IF name";
                 }
               }
             }
           }
         }
       }
       container chassis-high-availability-default-srg-info {
         description
           "Displays high-availability services redundancy group 0 info";
         leaf current-state {
           type string;
           description
             "SRG 0 current state";
         }
         leaf peer-id {
           type int32;
           description
             "Peer identifier";
         }
         leaf node-priority {
           type int32;
           description
             "Node-priority";
         }
         leaf peer-domain-id {
           type int32;
           description
             "Peer-domain-id";
         }
         list srg-peer-domain-peer-id-info {
           description
             "Idl peer node Id";
           leaf idl-peer-id {
             type int32;
             description
               "IDL Peer identifier";
           }
         }
         container high-availability-srg-signal-rt-info {
           description
             "  SRG Signal route Info";
           list ha-srg-signal-rt-list {
             description
               "Display each signal route information";
             leaf ha-srg-signal-rt-type {
               type string;
               description
                 "  SRG  Signal route type";
             }
             leaf ha-srg-signal-rt-ipaddr {
               type string;
               description
                 "IP address configured as SRG active signal route";
             }
             leaf ha-srg-signal-rt-rt {
               type string;
               description
                 "Routing table configured for active signal route";
             }
             leaf ha-srg-signal-rt-status {
               type string;
               description
                 " SRG signal Route installation status";
             }
           }
         }
         list chassis-high-availability-shutdown-interface {
           description
             "Display high-availability shutdown interface list";
           leaf high-availability-shutdown-interface-name {
             type string;
             description
               "Interface name for monitoring";
           }
         }
         container chassis-high-availability-srg-ipmon {
           description
             "SRG IP monitoring Info";
           leaf ha-srg-ipmon-status {
             type string;
             description
               "SRG overall IP-monitoring status";
           }
           container chassis-high-availability-srg-ipmon-list {
             description
               " Display each IP monitoring entry";
             leaf ha-srg-ipmon-dst-ipaddr {
               type string;
               description
                 "Destination IP address configured for HA ip-monitoring";
             }
             leaf ha-srg-ipmon-rt {
               type string;
               description
                 "Routing instance configured for HA ip-monitoring";
             }
             leaf ha-ipmon-status {
               type string;
               description
                 "HA ip-monitoring status";
             }
             leaf ha-srg-ipmon-reason {
               type string;
               description
                 "HA ip-monitoring failure reason";
             }
           }
         }
         container chassis-high-availability-srg-bfdmon {
           description
             " SRG BFD mon information ";
           leaf ha-srg-bfdmon-status {
             type string;
             description
               "HA overall bfd-monitoring status";
           }
           container chassis-high-availability-srg-bfdmon-list {
             description
               " Display each BFD mon entry Information";
             leaf ha-srg-bfdmon-src-ipaddr {
               type string;
               description
                 "Source IP address configured for HA bfd-monitoring";
             }
             leaf ha-srg-bfdmon-dst-ipaddr {
               type string;
               description
                 "Destination IP address configured for HA bfd-monitoring";
             }
             leaf ha-srg-bfdmon-rt {
               type string;
               description
                 "Routing instance configured for HA bfd-monitoring";
             }
             leaf ha-srg-bfdmon-type {
               type string;
               description
                 "HA bfd-monitoring type";
             }
             leaf ha-srg-bfdmon-ifl-name {
               type string;
               description
                 "HA bfd-monitoring IFL name";
             }
             leaf ha-srg-bfdmon-state {
               type string;
               description
                 "HA bfd-monitoring state";
             }
           }
         }
         container chassis-high-availability-srg-ifmon {
           description
             "SRG Interface monitoring Info";
           leaf ha-srg-ifmon-status {
             type string;
             description
               "HA overall Interface-monitoring status";
           }
           container chassis-high-availability-srg-ifmon-list {
             description
               " Display each Interface monitoring entry";
             leaf ha-srg-ifmon-if-name {
               type string;
               description
                 "HA Interface-monitoring IF name";
             }
             leaf ha-srg-ifmon-state {
               type string;
               description
                 "HA Interface-monitoring state";
             }
           }
         }
         container chassis-high-availability-srg-mon-info {
           description
             "SRG global threshold info";
           leaf ha-srg-mon-status {
             type string;
             description
               "SRG monitor status";
           }
           leaf ha-srg-mon-threshold {
             type int32;
             description
               "SRG monitor threshold";
           }
           leaf ha-srg-mon-weight {
             type int32;
             description
               "SRG monitor weight";
           }
           leaf ha-srg-mon-failed-objects {
             type int32;
             description
               "SRG monitor failed objects";
           }
         }
         container chassis-high-availability-srg-obj-info {
           description
             "SRG monitor-object info";
           leaf ha-srg-obj-name {
             type string;
             description
               "SRG monitor object name";
           }
           leaf ha-srg-obj-status {
             type string;
             description
               "SRG monitor object status";
           }
           leaf ha-srg-obj-entries {
             type string;
             description
               "SRG monitor object monitored entries";
           }
           leaf ha-srg-obj-failure {
             type string;
             description
               "SRG monitor object monitored failures";
           }
           leaf ha-srg-obj-threshold {
             type int32;
             description
               "SRG monitor object threshold";
           }
           leaf ha-srg-obj-weight {
             type int32;
             description
               "SRG monitor object current weight";
           }
         }
         container chassis-high-availability-srg-obj-ipmon {
           description
             "SRG monitor object IP monitoring Info";
           leaf ha-srg-obj-ipmon-threshold {
             type int32;
             description
               "SRG monitor object IP-monitoring threshold";
           }
           leaf ha-srg-obj-ipmon-weight {
             type int32;
             description
               "SRG monitor object IP-monitoring weight";
           }
           leaf ha-srg-obj-ipmon-status {
             type string;
             description
               "SRG monitor object IP-monitoring global status";
           }
           container chassis-high-availability-srg-obj-ipmon-list {
             description
               " Display each monitor object IP monitoring entry status";
             leaf ha-srg-obj-ipmon-entry-status {
               type string;
               description
                 "HA SRG monitor object ip-monitoring state";
             }
             leaf ha-srg-obj-ipmon-entry-weight {
               type int32;
               description
                 "HA SRG monitor object ip-monitoring weight";
             }
             leaf ha-srg-obj-ipmon-entry-dst-ipaddr {
               type string;
               description
                 "Destination IP address configured for HA ip-monitoring";
             }
           }
         }
         container chassis-high-availability-srg-obj-ipmon-detail {
           description
             "SRG monitor object IP monitoring detail Info";
           container chassis-high-availability-srg-ipmon-list {
             description
               " Display each IP monitoring entry";
             leaf ha-srg-ipmon-dst-ipaddr {
               type string;
               description
                 "Destination IP address configured for HA ip-monitoring";
             }
             leaf ha-srg-ipmon-rt {
               type string;
               description
                 "Routing instance configured for HA ip-monitoring";
             }
             leaf ha-ipmon-status {
               type string;
               description
                 "HA ip-monitoring status";
             }
             leaf ha-srg-ipmon-reason {
               type string;
               description
                 "HA ip-monitoring failure reason";
             }
           }
         }
         container chassis-high-availability-srg-obj-bfdmon {
           description
             "SRG monitor object BFD monitoring Info";
           leaf ha-srg-obj-bfdmon-threshold {
             type int32;
             description
               "SRG monitor object BFD-monitoring threshold";
           }
           leaf ha-srg-obj-bfdmon-weight {
             type int32;
             description
               "SRG monitor object BFD-monitoring weight";
           }
           leaf ha-srg-obj-bfdmon-status {
             type string;
             description
               "SRG monitor object BFD-monitoring global status";
           }
           container chassis-high-availability-srg-obj-bfdmon-list {
             description
               "Display each monitor object BFD monitoring entry status";
             leaf ha-srg-obj-bfdmon-entry-status {
               type string;
               description
                 "HA SRG monitor object BFD-monitoring state";
             }
             leaf ha-srg-obj-bfdmon-entry-weight {
               type int32;
               description
                 "HA SRG monitor object BFD-monitoring weight";
             }
             leaf ha-srg-obj-bfdmon-entry-dst-bfdaddr {
               type string;
               description
                 "Destination BFD address configured for HA BFD-monitoring";
             }
           }
         }
         container chassis-high-availability-srg-obj-bfdmon-detail {
           description
             "SRG monitor object BFD mon information ";
           container chassis-high-availability-srg-bfdmon-list {
             description
               " Display each BFD mon entry Information";
             leaf ha-srg-bfdmon-src-ipaddr {
               type string;
               description
                 "Source IP address configured for HA bfd-monitoring";
             }
             leaf ha-srg-bfdmon-dst-ipaddr {
               type string;
               description
                 "Destination IP address configured for HA bfd-monitoring";
             }
             leaf ha-srg-bfdmon-rt {
               type string;
               description
                 "Routing instance configured for HA bfd-monitoring";
             }
             leaf ha-srg-bfdmon-type {
               type string;
               description
                 "HA bfd-monitoring type";
             }
             leaf ha-srg-bfdmon-ifl-name {
               type string;
               description
                 "HA bfd-monitoring IFL name";
             }
             leaf ha-srg-bfdmon-state {
               type string;
               description
                 "HA bfd-monitoring state";
             }
           }
         }
         container chassis-high-availability-srg-obj-ifmon {
           description
             "SRG monitor object IF monitoring Info";
           leaf ha-srg-obj-ifmon-threshold {
             type int32;
             description
               "SRG monitor object IF-monitoring threshold";
           }
           leaf ha-srg-obj-ifmon-weight {
             type int32;
             description
               "SRG monitor object IF-monitoring current weight";
           }
           leaf ha-srg-ifmon-status {
             type string;
             description
               "HA overall Interface-monitoring status";
           }
           container chassis-high-availability-srg-obj-ifmon-list {
             description
               "Display each monitor object IF monitoring entry status";
             leaf ha-srg-ifmon-entry-status {
               type string;
               description
                 "HA SRG monitor object IF-monitoring entry status";
             }
             leaf ha-srg-obj-ifmon-entry-weight {
               type int32;
               description
                 "HA SRG monitor object IF-monitoring entry weight";
             }
             leaf ha-srg-ifmon-if-name {
               type string;
               description
                 "HA Interface-monitoring IF name";
             }
           }
         }
       }
       container chassis-high-availability-srg-info {
         description
           "Displays high-availability services redundancy group info";
         container chassis-high-availability-srg-info-list {
           description
             "Displays each services redundancy group info";
           leaf srg-id {
             type int32;
             description
               "Current services redundancy group identifier";
           }
           leaf deployment-type {
             type string;
             description
               "Deployment Type";
           }
           leaf node-role {
             type string;
             description
               "Local node role";
           }
           leaf activeness-priority {
             type int32;
             description
               "SRG activeness priority";
           }
           leaf preemption {
             type string;
             description
               "Preemption enable flag Status";
           }
           leaf process-pkt-in-bkp-state {
             type string;
             description
               "SRG backup state pkt processing info";
           }
           leaf control-plane {
             type string;
             description
               "Control plane status";
           }
           leaf system-integrity-check {
             type string;
             description
               "Status of system integrity check";
           }
           leaf failure-events {
             type string;
             description
               "List of failure events";
           }
           leaf peer-id {
             type int32;
             description
               "Peer identifier";
           }
           leaf peer-node-role {
             type string;
             description
               "Peer node role";
           }
           leaf health-status {
             type string;
             description
               "Peer health status";
           }
           leaf failover-readiness {
             type string;
             description
               "SRG failover readiness";
           }
         }
       }
     }
     list chassis-high-availability-peer-info {
       description
         "Displays high-availability peer related info";
       leaf high-availability-peer-desc {
         type string;
         description
           "Peer description";
       }
       leaf high-availability-peer-id {
         type int32;
         description
           "Peer identifier that is configured";
       }
       leaf high-availability-peer-ip-address {
         type jt:ipaddr;
         description
           "Peer remote IPv4 address that is configured";
       }
       leaf-list high-availability-local-interface {
         type string;
         description
           "Local interface";
       }
       leaf high-availability-peer-rt-instance {
         type string;
         description
           "Routing Instance name for HA peer";
       }
       leaf high-availability-peer-encryption-status {
         type string;
         description
           "Encryption status of the current node";
       }
       leaf high-availability-peer-bfd-status {
         type string;
         description
           "BFD Status of the current node";
       }
       leaf high-availability-peer-detect-time {
         type string;
         description
           "Configured Peer BFD detection time";
       }
       leaf cold-sync-status {
         type string;
         description
           "Cold synchronization status";
       }
       leaf peer-hw-incompatible {
         type string;
         description
           "Peer hardware compatible status";
       }
       leaf high-availability-peer-fwd-ip-address {
         type jt:ipaddr;
         description
           "Peer forwarding remote IP address";
       }
       leaf high-availability-local-fwd-interface {
         type string;
         description
           "Local forwarding interface";
       }
       leaf high-availability-peer-fwd-bfd-status {
         type string;
         description
           "BFD forwarding status of the current node";
       }
       leaf peer-domain-id {
         type int32;
         description
           "Peer-domain-id";
       }
     }
     container chassis-high-availability-default-srg-info {
       description
         "Displays high-availability services redundancy group 0 info";
       leaf current-state {
         type string;
         description
           "SRG 0 current state";
       }
       leaf peer-id {
         type int32;
         description
           "Peer identifier";
       }
       leaf node-priority {
         type int32;
         description
           "Node-priority";
       }
       leaf peer-domain-id {
         type int32;
         description
           "Peer-domain-id";
       }
       list srg-peer-domain-peer-id-info {
         description
           "Idl peer node Id";
         leaf idl-peer-id {
           type int32;
           description
             "IDL Peer identifier";
         }
       }
       container high-availability-srg-signal-rt-info {
         description
           "  SRG Signal route Info";
         list ha-srg-signal-rt-list {
           description
             "Display each signal route information";
           leaf ha-srg-signal-rt-type {
             type string;
             description
               "  SRG  Signal route type";
           }
           leaf ha-srg-signal-rt-ipaddr {
             type string;
             description
               "IP address configured as SRG active signal route";
           }
           leaf ha-srg-signal-rt-rt {
             type string;
             description
               "Routing table configured for active signal route";
           }
           leaf ha-srg-signal-rt-status {
             type string;
             description
               " SRG signal Route installation status";
           }
         }
       }
       list chassis-high-availability-shutdown-interface {
         description
           "Display high-availability shutdown interface list";
         leaf high-availability-shutdown-interface-name {
           type string;
           description
             "Interface name for monitoring";
         }
       }
       container chassis-high-availability-srg-ipmon {
         description
           "SRG IP monitoring Info";
         leaf ha-srg-ipmon-status {
           type string;
           description
             "SRG overall IP-monitoring status";
         }
         container chassis-high-availability-srg-ipmon-list {
           description
             " Display each IP monitoring entry";
           leaf ha-srg-ipmon-dst-ipaddr {
             type string;
             description
               "Destination IP address configured for HA ip-monitoring";
           }
           leaf ha-srg-ipmon-rt {
             type string;
             description
               "Routing instance configured for HA ip-monitoring";
           }
           leaf ha-ipmon-status {
             type string;
             description
               "HA ip-monitoring status";
           }
           leaf ha-srg-ipmon-reason {
             type string;
             description
               "HA ip-monitoring failure reason";
           }
         }
       }
       container chassis-high-availability-srg-bfdmon {
         description
           " SRG BFD mon information ";
         leaf ha-srg-bfdmon-status {
           type string;
           description
             "HA overall bfd-monitoring status";
         }
         container chassis-high-availability-srg-bfdmon-list {
           description
             " Display each BFD mon entry Information";
           leaf ha-srg-bfdmon-src-ipaddr {
             type string;
             description
               "Source IP address configured for HA bfd-monitoring";
           }
           leaf ha-srg-bfdmon-dst-ipaddr {
             type string;
             description
               "Destination IP address configured for HA bfd-monitoring";
           }
           leaf ha-srg-bfdmon-rt {
             type string;
             description
               "Routing instance configured for HA bfd-monitoring";
           }
           leaf ha-srg-bfdmon-type {
             type string;
             description
               "HA bfd-monitoring type";
           }
           leaf ha-srg-bfdmon-ifl-name {
             type string;
             description
               "HA bfd-monitoring IFL name";
           }
           leaf ha-srg-bfdmon-state {
             type string;
             description
               "HA bfd-monitoring state";
           }
         }
       }
       container chassis-high-availability-srg-ifmon {
         description
           "SRG Interface monitoring Info";
         leaf ha-srg-ifmon-status {
           type string;
           description
             "HA overall Interface-monitoring status";
         }
         container chassis-high-availability-srg-ifmon-list {
           description
             " Display each Interface monitoring entry";
           leaf ha-srg-ifmon-if-name {
             type string;
             description
               "HA Interface-monitoring IF name";
           }
           leaf ha-srg-ifmon-state {
             type string;
             description
               "HA Interface-monitoring state";
           }
         }
       }
       container chassis-high-availability-srg-mon-info {
         description
           "SRG global threshold info";
         leaf ha-srg-mon-status {
           type string;
           description
             "SRG monitor status";
         }
         leaf ha-srg-mon-threshold {
           type int32;
           description
             "SRG monitor threshold";
         }
         leaf ha-srg-mon-weight {
           type int32;
           description
             "SRG monitor weight";
         }
         leaf ha-srg-mon-failed-objects {
           type int32;
           description
             "SRG monitor failed objects";
         }
       }
       container chassis-high-availability-srg-obj-info {
         description
           "SRG monitor-object info";
         leaf ha-srg-obj-name {
           type string;
           description
             "SRG monitor object name";
         }
         leaf ha-srg-obj-status {
           type string;
           description
             "SRG monitor object status";
         }
         leaf ha-srg-obj-entries {
           type string;
           description
             "SRG monitor object monitored entries";
         }
         leaf ha-srg-obj-failure {
           type string;
           description
             "SRG monitor object monitored failures";
         }
         leaf ha-srg-obj-threshold {
           type int32;
           description
             "SRG monitor object threshold";
         }
         leaf ha-srg-obj-weight {
           type int32;
           description
             "SRG monitor object current weight";
         }
       }
       container chassis-high-availability-srg-obj-ipmon {
         description
           "SRG monitor object IP monitoring Info";
         leaf ha-srg-obj-ipmon-threshold {
           type int32;
           description
             "SRG monitor object IP-monitoring threshold";
         }
         leaf ha-srg-obj-ipmon-weight {
           type int32;
           description
             "SRG monitor object IP-monitoring weight";
         }
         leaf ha-srg-obj-ipmon-status {
           type string;
           description
             "SRG monitor object IP-monitoring global status";
         }
         container chassis-high-availability-srg-obj-ipmon-list {
           description
             " Display each monitor object IP monitoring entry status";
           leaf ha-srg-obj-ipmon-entry-status {
             type string;
             description
               "HA SRG monitor object ip-monitoring state";
           }
           leaf ha-srg-obj-ipmon-entry-weight {
             type int32;
             description
               "HA SRG monitor object ip-monitoring weight";
           }
           leaf ha-srg-obj-ipmon-entry-dst-ipaddr {
             type string;
             description
               "Destination IP address configured for HA ip-monitoring";
           }
         }
       }
       container chassis-high-availability-srg-obj-ipmon-detail {
         description
           "SRG monitor object IP monitoring detail Info";
         container chassis-high-availability-srg-ipmon-list {
           description
             " Display each IP monitoring entry";
           leaf ha-srg-ipmon-dst-ipaddr {
             type string;
             description
               "Destination IP address configured for HA ip-monitoring";
           }
           leaf ha-srg-ipmon-rt {
             type string;
             description
               "Routing instance configured for HA ip-monitoring";
           }
           leaf ha-ipmon-status {
             type string;
             description
               "HA ip-monitoring status";
           }
           leaf ha-srg-ipmon-reason {
             type string;
             description
               "HA ip-monitoring failure reason";
           }
         }
       }
       container chassis-high-availability-srg-obj-bfdmon {
         description
           "SRG monitor object BFD monitoring Info";
         leaf ha-srg-obj-bfdmon-threshold {
           type int32;
           description
             "SRG monitor object BFD-monitoring threshold";
         }
         leaf ha-srg-obj-bfdmon-weight {
           type int32;
           description
             "SRG monitor object BFD-monitoring weight";
         }
         leaf ha-srg-obj-bfdmon-status {
           type string;
           description
             "SRG monitor object BFD-monitoring global status";
         }
         container chassis-high-availability-srg-obj-bfdmon-list {
           description
             "Display each monitor object BFD monitoring entry status";
           leaf ha-srg-obj-bfdmon-entry-status {
             type string;
             description
               "HA SRG monitor object BFD-monitoring state";
           }
           leaf ha-srg-obj-bfdmon-entry-weight {
             type int32;
             description
               "HA SRG monitor object BFD-monitoring weight";
           }
           leaf ha-srg-obj-bfdmon-entry-dst-bfdaddr {
             type string;
             description
               "Destination BFD address configured for HA BFD-monitoring";
           }
         }
       }
       container chassis-high-availability-srg-obj-bfdmon-detail {
         description
           "SRG monitor object BFD mon information ";
         container chassis-high-availability-srg-bfdmon-list {
           description
             " Display each BFD mon entry Information";
           leaf ha-srg-bfdmon-src-ipaddr {
             type string;
             description
               "Source IP address configured for HA bfd-monitoring";
           }
           leaf ha-srg-bfdmon-dst-ipaddr {
             type string;
             description
               "Destination IP address configured for HA bfd-monitoring";
           }
           leaf ha-srg-bfdmon-rt {
             type string;
             description
               "Routing instance configured for HA bfd-monitoring";
           }
           leaf ha-srg-bfdmon-type {
             type string;
             description
               "HA bfd-monitoring type";
           }
           leaf ha-srg-bfdmon-ifl-name {
             type string;
             description
               "HA bfd-monitoring IFL name";
           }
           leaf ha-srg-bfdmon-state {
             type string;
             description
               "HA bfd-monitoring state";
           }
         }
       }
       container chassis-high-availability-srg-obj-ifmon {
         description
           "SRG monitor object IF monitoring Info";
         leaf ha-srg-obj-ifmon-threshold {
           type int32;
           description
             "SRG monitor object IF-monitoring threshold";
         }
         leaf ha-srg-obj-ifmon-weight {
           type int32;
           description
             "SRG monitor object IF-monitoring current weight";
         }
         leaf ha-srg-ifmon-status {
           type string;
           description
             "HA overall Interface-monitoring status";
         }
         container chassis-high-availability-srg-obj-ifmon-list {
           description
             "Display each monitor object IF monitoring entry status";
           leaf ha-srg-ifmon-entry-status {
             type string;
             description
               "HA SRG monitor object IF-monitoring entry status";
           }
           leaf ha-srg-obj-ifmon-entry-weight {
             type int32;
             description
               "HA SRG monitor object IF-monitoring entry weight";
           }
           leaf ha-srg-ifmon-if-name {
             type string;
             description
               "HA Interface-monitoring IF name";
           }
         }
       }
     }
     container chassis-high-availability-srg-info {
       description
         "Displays high-availability services redundancy group info";
       container chassis-high-availability-srg-info-list {
         description
           "Displays each services redundancy group info";
         leaf srg-id {
           type int32;
           description
             "Current services redundancy group identifier";
         }
         leaf deployment-type {
           type string;
           description
             "Deployment Type";
         }
         leaf node-role {
           type string;
           description
             "Local node role";
         }
         leaf activeness-priority {
           type int32;
           description
             "SRG activeness priority";
         }
         leaf preemption {
           type string;
           description
             "Preemption enable flag Status";
         }
         leaf process-pkt-in-bkp-state {
           type string;
           description
             "SRG backup state pkt processing info";
         }
         leaf control-plane {
           type string;
           description
             "Control plane status";
         }
         leaf system-integrity-check {
           type string;
           description
             "Status of system integrity check";
         }
         leaf failure-events {
           type string;
           description
             "List of failure events";
         }
         leaf peer-id {
           type int32;
           description
             "Peer identifier";
         }
         leaf peer-node-role {
           type string;
           description
             "Peer node role";
         }
         leaf health-status {
           type string;
           description
             "Peer health status";
         }
         leaf failover-readiness {
           type string;
           description
             "SRG failover readiness";
         }
       }
     }
   }
   grouping chassis-high-availability-detail-information-block {
     list high-availability-peer-status-events {
       description
         "List of HA Peer Conn events";
       leaf-list high-availability-peer-status-event {
         type string;
         description
           "Recorded HA Peer Conn event";
       }
     }
     list high-availability-hw-upgrade-events {
       description
         "List of HA hardware upgrade events";
       leaf-list high-availability-hw-upgrade-event {
         type string;
         description
           "Recorded HA hardware upgrade event";
       }
     }
     container chassis-mnha-node-level-info {
       description
         "Display high-availability node level information";
       leaf node-status {
         type string;
         description
           "Status of the current node";
       }
       leaf local-domain-id {
         type int32;
         description
           "Local-domain-id";
       }
       leaf local-id {
         type int32;
         description
           "Local node identifier";
       }
       leaf local-ip {
         type jt:ipaddr;
         description
           "Local node IPv4 address";
       }
       leaf local-fwd-ip {
         type jt:ipaddr;
         description
           "Local Forwarding IP address";
       }
     }
     container chassis-mnha-local-domain-info-detail {
       description
         "Displays mnha local domain related info";
       leaf local-ip {
         type jt:ipaddr;
         description
           "Local node IPv4 address";
       }
       list high-availability-hw-upgrade-events {
         description
           "List of HA hardware upgrade events";
         leaf-list high-availability-hw-upgrade-event {
           type string;
           description
             "Recorded HA hardware upgrade event";
         }
       }
       list chassis-high-availability-shutdown-interface {
         description
           "Display high-availability shutdown interface list";
         leaf high-availability-shutdown-interface-name {
           type string;
           description
             "Interface name for monitoring";
         }
       }
       container chassis-mnha-icl-peer-info {
         description
           "Displays mnha icl peer related info";
         leaf high-availability-peer-desc {
           type string;
           description
             "Peer description";
         }
         leaf peer-domain-id {
           type int32;
           description
             "Peer-domain-id";
         }
         leaf high-availability-peer-id {
           type int32;
           description
             "Peer identifier that is configured";
         }
         leaf high-availability-peer-ip-address {
           type jt:ipaddr;
           description
             "Peer remote IPv4 address that is configured";
         }
         leaf-list high-availability-local-interface {
           type string;
           description
             "Local interface";
         }
         leaf high-availability-peer-rt-instance {
           type string;
           description
             "Routing Instance name for HA peer";
         }
         leaf high-availability-peer-encryption-status {
           type string;
           description
             "Encryption status of the current node";
         }
         leaf high-availability-peer-bfd-status {
           type string;
           description
             "BFD Status of the current node";
         }
         leaf cold-sync-status {
           type string;
           description
             "Cold synchronization status";
         }
         leaf peer-hw-incompatible {
           type string;
           description
             "Peer hardware compatible status";
         }
         leaf peer-internal-interface {
           type string;
           description
             "Peer internal interface";
         }
         leaf peer-internal-local-ip {
           type jt:ipaddr;
           description
             "Internal local IPv4 address";
         }
         leaf peer-internal-peer-ip {
           type jt:ipaddr;
           description
             "Internal peer IPv4 address";
         }
         leaf peer-internal-routing-instance {
           type string;
           description
             "Peer internal routing instance";
         }
         leaf high-availability-peer-detect-time {
           type string;
           description
             "Configured Peer BFD detection time";
         }
         leaf srg0-cold-sync-status {
           type string;
           description
             "SRG0 cold sync status";
         }
         container chassis-mnha-local-node-idl-info {
           description
             "Displays high-availability local node IDL BFD and CS state";
           leaf states-from-domain-id {
             type int32;
             description
               "States from domain id";
           }
           leaf states-from-node-id {
             type int32;
             description
               "States from node id";
           }
           leaf domain-id {
             type int32;
             description
               "Domain-id";
           }
           leaf peer-id {
             type int32;
             description
               "Peer identifier";
           }
           leaf conn-state {
             type string;
             description
               "Conn state";
           }
           leaf rtt-result {
             type string;
             description
               "RTT result";
           }
           leaf cold-sync-status {
             type string;
             description
               "Cold synchronization status";
           }
           leaf srg0-idl-status {
             type string;
             description
               "SRG0 idl status";
           }
         }
         container chassis-mnha-peer-node-icl-info {
           description
             "Displays high-availability icl info";
           leaf states-from-domain-id {
             type int32;
             description
               "States from domain id";
           }
           leaf states-from-node-id {
             type int32;
             description
               "States from node id";
           }
           leaf icl-conn-state {
             type string;
             description
               "ICL Conn state";
           }
           leaf cold-sync-status {
             type string;
             description
               "Cold synchronization status";
           }
         }
         container chassis-mnha-peer-node-idl-info {
           description
             "Displays high-availability peer node IDL BFD and CS state";
           leaf states-from-domain-id {
             type int32;
             description
               "States from domain id";
           }
           leaf states-from-node-id {
             type int32;
             description
               "States from node id";
           }
           leaf domain-id {
             type int32;
             description
               "Domain-id";
           }
           leaf peer-id {
             type int32;
             description
               "Peer identifier";
           }
           leaf conn-state {
             type string;
             description
               "Conn state";
           }
           leaf rtt-result {
             type string;
             description
               "RTT result";
           }
           leaf cold-sync-status {
             type string;
             description
               "Cold synchronization status";
           }
           leaf srg0-idl-status {
             type string;
             description
               "SRG0 idl status";
           }
         }
         list high-availability-peer-packet-stats {
           description
             "Peer Packet Stats";
           leaf packet-send-err-cnt {
             type int32;
             description
               "Peer packet send error cnt";
           }
           leaf packet-recv-err-cnt {
             type int32;
             description
               "Peer packet recv error cnt";
           }
           list peer-packet-send-rcv-stats {
             description
               "Peer Packet Send receive Stats";
             list peer-packet-stats-list {
               description
                 "Stats for each peer packet type";
               leaf peer-packet-type {
                 type string;
                 description
                   "Peer packet Type";
               }
               leaf peer-packet-send-cnt {
                 type int32;
                 description
                   "Peer packet sent count";
               }
               leaf peer-packet-rcv-cnt {
                 type int32;
                 description
                   "Peer packet rcv cnt";
               }
             }
           }
         }
       }
       container cold-synchronization-monitoring-information {
         description
           "Cold sync monitoring related information";
         leaf-list cold-synchronization-progress {
           type string;
           description
             "Cold synchronization progress";
         }
         container cold-synchronization-status-information {
           description
             "Cold synchronization related status information";
           leaf cold-synchronization-completed {
             type string;
             description
               "List of PFE's which have completed cold synchnronization";
           }
           leaf cold-synchronization-not-completed {
             type string;
             description
               "List of PFE's which have failed cold synchnronization";
           }
           leaf cold-synchronization-unknown {
             type string;
             description
               "List of PFE's for which cold synchnronization statusupdate 
               is not received";
           }
           leaf cold-synchronization-weight {
             type uint32;
             description
               "Current Cold Synchronization weight";
           }
         }
         container cold-synchronization-statistics {
           description
             "Cold synchronization statistics";
           leaf current-cold-synchronization-completed {
             type uint32;
             description
               "Cold synchronization completed for current jsrpd session";
           }
           leaf current-cold-synchronization-failed {
             type uint32;
             description
               "Cold synchronization failed for current jsrpd session";
           }
           list cold-synchronization-pfe-statistics {
             description
               "Cold synchroniizaton statistics for each PFE";
             leaf pfe-name {
               type string;
               description
                 "Name of the PFE";
             }
             leaf cold-synchronization-pfe-completed {
               type uint32;
               description
                 "Cold synchronization complete instances for a given PFE";
             }
             leaf cold-synchronization-pfe-failed {
               type uint32;
               description
                 "Cold synchronization complete instances for a given PFE";
             }
           }
         }
         container cold-synchronization-events {
           description
             "List of cold synchronization events";
           leaf-list cold-synchronization-event {
             type string;
             description
               "Recorded cold sync complete/failure for a PFE";
           }
         }
       }
       container spu-monitoring-information {
         description
           "SPU monitoring related information";
         container spu-monitoring-status {
           description
             "SPU monitoring related status information";
           leaf spu-monitoring-state {
             type string;
             description
               "SPU current monitoring mode Disabled/Enabled/Active";
           }
           leaf spu-monitoring-weight {
             type uint32;
             description
               "Current SPU monitoring weight";
           }
           list spu-monitoring-spu-state {
             description
               "Each SPU current state";
             container spu-monitoring-spu-state-list {
               description
                 "Each SPU current state in list";
               leaf pfe-name {
                 type string;
                 description
                   "Name of the PFE";
               }
               leaf pic-state {
                 type string;
                 description
                   "State of each PIC";
               }
             }
           }
         }
         container spu-monitoring-statistics {
           description
             "Detailed statistics of SPU monitoring";
           leaf spu-up-count {
             type uint32;
             description
               "Number of SPUs that are up";
           }
           leaf spu-down-count {
             type uint32;
             description
               "Number of SPUs that are down";
           }
           leaf npc-up-count {
             type uint32;
             description
               "Number of NPCs that are up";
           }
           leaf npc-down-count {
             type uint32;
             description
               "Number of NPCs that are down";
           }
           leaf chinfo-blob-error-count {
             type uint32;
             description
               "Error count reading chinfo blob";
           }
         }
         container spu-monitoring-events {
           description
             "List of SPU monitoring events";
           leaf-list spu-monitoring-event {
             type string;
             description
               "Recorded SPU monitoring events";
           }
         }
       }
       list loopback-information {
         description
           "Loopback information";
         container loopback-information-list {
           description
             "Display loopback information list";
           leaf pfe-name {
             type string;
             description
               "Name of the PFE";
           }
           leaf loopback-status {
             type string;
             description
               "Loopback status of each PIC";
           }
           leaf nexthop-status {
             type string;
             description
               "Nexthop status of each PIC";
           }
           leaf mbuf-status {
             type string;
             description
               "Mbuf status of each PIC";
           }
         }
       }
       container high-availability-hardware-monitoring-information {
         description
           "Displays complete high-availability hardware monitoring 
           information for debugging purposes";
         container hardware-monitoring-events {
           description
             "List of hardware monitoring events";
           leaf-list hardware-monitoring-event {
             type string;
             description
               "Recorded hardware monitoring events";
           }
         }
         container high-availability-hardware-monitoring-status-information {
           leaf high-availability-hardware-monitoring-activation-status {
             type string;
             description
               "Hardware monitoring is enabled/disabled";
           }
           leaf high-availability-hardware-monitoring-ctrl-plane-errors {
             type int32;
             description
               "Hardware monitoring Ctrl plane errors";
           }
           leaf high-availability-hardware-monitoring-data-plane-errors {
             type int32;
             description
               "Hardware monitoring Data plane errors";
           }
         }
       }
       container chassis-high-availability-default-srg-info {
         description
           "Displays high-availability services redundancy group 0 info";
         leaf current-state {
           type string;
           description
             "SRG 0 current state";
         }
         leaf peer-id {
           type int32;
           description
             "Peer identifier";
         }
         leaf node-priority {
           type int32;
           description
             "Node-priority";
         }
         leaf peer-domain-id {
           type int32;
           description
             "Peer-domain-id";
         }
         list srg-peer-domain-peer-id-info {
           description
             "Idl peer node Id";
           leaf idl-peer-id {
             type int32;
             description
               "IDL Peer identifier";
           }
         }
         container high-availability-srg-signal-rt-info {
           description
             "  SRG Signal route Info";
           list ha-srg-signal-rt-list {
             description
               "Display each signal route information";
             leaf ha-srg-signal-rt-type {
               type string;
               description
                 "  SRG  Signal route type";
             }
             leaf ha-srg-signal-rt-ipaddr {
               type string;
               description
                 "IP address configured as SRG active signal route";
             }
             leaf ha-srg-signal-rt-rt {
               type string;
               description
                 "Routing table configured for active signal route";
             }
             leaf ha-srg-signal-rt-status {
               type string;
               description
                 " SRG signal Route installation status";
             }
           }
         }
         list chassis-high-availability-shutdown-interface {
           description
             "Display high-availability shutdown interface list";
           leaf high-availability-shutdown-interface-name {
             type string;
             description
               "Interface name for monitoring";
           }
         }
         container chassis-high-availability-srg-ipmon {
           description
             "SRG IP monitoring Info";
           leaf ha-srg-ipmon-status {
             type string;
             description
               "SRG overall IP-monitoring status";
           }
           container chassis-high-availability-srg-ipmon-list {
             description
               " Display each IP monitoring entry";
             leaf ha-srg-ipmon-dst-ipaddr {
               type string;
               description
                 "Destination IP address configured for HA ip-monitoring";
             }
             leaf ha-srg-ipmon-rt {
               type string;
               description
                 "Routing instance configured for HA ip-monitoring";
             }
             leaf ha-ipmon-status {
               type string;
               description
                 "HA ip-monitoring status";
             }
             leaf ha-srg-ipmon-reason {
               type string;
               description
                 "HA ip-monitoring failure reason";
             }
           }
         }
         container chassis-high-availability-srg-bfdmon {
           description
             " SRG BFD mon information ";
           leaf ha-srg-bfdmon-status {
             type string;
             description
               "HA overall bfd-monitoring status";
           }
           container chassis-high-availability-srg-bfdmon-list {
             description
               " Display each BFD mon entry Information";
             leaf ha-srg-bfdmon-src-ipaddr {
               type string;
               description
                 "Source IP address configured for HA bfd-monitoring";
             }
             leaf ha-srg-bfdmon-dst-ipaddr {
               type string;
               description
                 "Destination IP address configured for HA bfd-monitoring";
             }
             leaf ha-srg-bfdmon-rt {
               type string;
               description
                 "Routing instance configured for HA bfd-monitoring";
             }
             leaf ha-srg-bfdmon-type {
               type string;
               description
                 "HA bfd-monitoring type";
             }
             leaf ha-srg-bfdmon-ifl-name {
               type string;
               description
                 "HA bfd-monitoring IFL name";
             }
             leaf ha-srg-bfdmon-state {
               type string;
               description
                 "HA bfd-monitoring state";
             }
           }
         }
         container chassis-high-availability-srg-ifmon {
           description
             "SRG Interface monitoring Info";
           leaf ha-srg-ifmon-status {
             type string;
             description
               "HA overall Interface-monitoring status";
           }
           container chassis-high-availability-srg-ifmon-list {
             description
               " Display each Interface monitoring entry";
             leaf ha-srg-ifmon-if-name {
               type string;
               description
                 "HA Interface-monitoring IF name";
             }
             leaf ha-srg-ifmon-state {
               type string;
               description
                 "HA Interface-monitoring state";
             }
           }
         }
         container chassis-high-availability-srg-mon-info {
           description
             "SRG global threshold info";
           leaf ha-srg-mon-status {
             type string;
             description
               "SRG monitor status";
           }
           leaf ha-srg-mon-threshold {
             type int32;
             description
               "SRG monitor threshold";
           }
           leaf ha-srg-mon-weight {
             type int32;
             description
               "SRG monitor weight";
           }
           leaf ha-srg-mon-failed-objects {
             type int32;
             description
               "SRG monitor failed objects";
           }
         }
         container chassis-high-availability-srg-obj-info {
           description
             "SRG monitor-object info";
           leaf ha-srg-obj-name {
             type string;
             description
               "SRG monitor object name";
           }
           leaf ha-srg-obj-status {
             type string;
             description
               "SRG monitor object status";
           }
           leaf ha-srg-obj-entries {
             type string;
             description
               "SRG monitor object monitored entries";
           }
           leaf ha-srg-obj-failure {
             type string;
             description
               "SRG monitor object monitored failures";
           }
           leaf ha-srg-obj-threshold {
             type int32;
             description
               "SRG monitor object threshold";
           }
           leaf ha-srg-obj-weight {
             type int32;
             description
               "SRG monitor object current weight";
           }
         }
         container chassis-high-availability-srg-obj-ipmon {
           description
             "SRG monitor object IP monitoring Info";
           leaf ha-srg-obj-ipmon-threshold {
             type int32;
             description
               "SRG monitor object IP-monitoring threshold";
           }
           leaf ha-srg-obj-ipmon-weight {
             type int32;
             description
               "SRG monitor object IP-monitoring weight";
           }
           leaf ha-srg-obj-ipmon-status {
             type string;
             description
               "SRG monitor object IP-monitoring global status";
           }
           container chassis-high-availability-srg-obj-ipmon-list {
             description
               " Display each monitor object IP monitoring entry status";
             leaf ha-srg-obj-ipmon-entry-status {
               type string;
               description
                 "HA SRG monitor object ip-monitoring state";
             }
             leaf ha-srg-obj-ipmon-entry-weight {
               type int32;
               description
                 "HA SRG monitor object ip-monitoring weight";
             }
             leaf ha-srg-obj-ipmon-entry-dst-ipaddr {
               type string;
               description
                 "Destination IP address configured for HA ip-monitoring";
             }
           }
         }
         container chassis-high-availability-srg-obj-ipmon-detail {
           description
             "SRG monitor object IP monitoring detail Info";
           container chassis-high-availability-srg-ipmon-list {
             description
               " Display each IP monitoring entry";
             leaf ha-srg-ipmon-dst-ipaddr {
               type string;
               description
                 "Destination IP address configured for HA ip-monitoring";
             }
             leaf ha-srg-ipmon-rt {
               type string;
               description
                 "Routing instance configured for HA ip-monitoring";
             }
             leaf ha-ipmon-status {
               type string;
               description
                 "HA ip-monitoring status";
             }
             leaf ha-srg-ipmon-reason {
               type string;
               description
                 "HA ip-monitoring failure reason";
             }
           }
         }
         container chassis-high-availability-srg-obj-bfdmon {
           description
             "SRG monitor object BFD monitoring Info";
           leaf ha-srg-obj-bfdmon-threshold {
             type int32;
             description
               "SRG monitor object BFD-monitoring threshold";
           }
           leaf ha-srg-obj-bfdmon-weight {
             type int32;
             description
               "SRG monitor object BFD-monitoring weight";
           }
           leaf ha-srg-obj-bfdmon-status {
             type string;
             description
               "SRG monitor object BFD-monitoring global status";
           }
           container chassis-high-availability-srg-obj-bfdmon-list {
             description
               "Display each monitor object BFD monitoring entry status";
             leaf ha-srg-obj-bfdmon-entry-status {
               type string;
               description
                 "HA SRG monitor object BFD-monitoring state";
             }
             leaf ha-srg-obj-bfdmon-entry-weight {
               type int32;
               description
                 "HA SRG monitor object BFD-monitoring weight";
             }
             leaf ha-srg-obj-bfdmon-entry-dst-bfdaddr {
               type string;
               description
                 "Destination BFD address configured for HA BFD-monitoring";
             }
           }
         }
         container chassis-high-availability-srg-obj-bfdmon-detail {
           description
             "SRG monitor object BFD mon information ";
           container chassis-high-availability-srg-bfdmon-list {
             description
               " Display each BFD mon entry Information";
             leaf ha-srg-bfdmon-src-ipaddr {
               type string;
               description
                 "Source IP address configured for HA bfd-monitoring";
             }
             leaf ha-srg-bfdmon-dst-ipaddr {
               type string;
               description
                 "Destination IP address configured for HA bfd-monitoring";
             }
             leaf ha-srg-bfdmon-rt {
               type string;
               description
                 "Routing instance configured for HA bfd-monitoring";
             }
             leaf ha-srg-bfdmon-type {
               type string;
               description
                 "HA bfd-monitoring type";
             }
             leaf ha-srg-bfdmon-ifl-name {
               type string;
               description
                 "HA bfd-monitoring IFL name";
             }
             leaf ha-srg-bfdmon-state {
               type string;
               description
                 "HA bfd-monitoring state";
             }
           }
         }
         container chassis-high-availability-srg-obj-ifmon {
           description
             "SRG monitor object IF monitoring Info";
           leaf ha-srg-obj-ifmon-threshold {
             type int32;
             description
               "SRG monitor object IF-monitoring threshold";
           }
           leaf ha-srg-obj-ifmon-weight {
             type int32;
             description
               "SRG monitor object IF-monitoring current weight";
           }
           leaf ha-srg-ifmon-status {
             type string;
             description
               "HA overall Interface-monitoring status";
           }
           container chassis-high-availability-srg-obj-ifmon-list {
             description
               "Display each monitor object IF monitoring entry status";
             leaf ha-srg-ifmon-entry-status {
               type string;
               description
                 "HA SRG monitor object IF-monitoring entry status";
             }
             leaf ha-srg-obj-ifmon-entry-weight {
               type int32;
               description
                 "HA SRG monitor object IF-monitoring entry weight";
             }
             leaf ha-srg-ifmon-if-name {
               type string;
               description
                 "HA Interface-monitoring IF name";
             }
           }
         }
       }
       list chassis-high-availability-srg-info-detail {
         description
           "Displays high-availability services redundancy group detail info";
         container chassis-high-availability-srg-info-list {
           description
             "Displays each services redundancy group info";
           leaf srg-id {
             type int32;
             description
               "Current services redundancy group identifier";
           }
           leaf deployment-type {
             type string;
             description
               "Deployment Type";
           }
           leaf node-role {
             type string;
             description
               "Local node role";
           }
           leaf activeness-priority {
             type int32;
             description
               "SRG activeness priority";
           }
           leaf preemption {
             type string;
             description
               "Preemption enable flag Status";
           }
           leaf hold-timer {
             type int32;
             description
               "SRG hold down timer";
           }
           leaf process-pkt-in-bkp-state {
             type string;
             description
               "SRG backup state pkt processing info";
           }
           leaf service-names {
             type string;
             description
               "SRG service names";
           }
           leaf control-plane {
             type string;
             description
               "Control plane status";
           }
           leaf system-integrity-check {
             type string;
             description
               "Status of system integrity check";
           }
           leaf peer-id {
             type int32;
             description
               "Peer identifier";
           }
           leaf peer-node-role {
             type string;
             description
               "Peer node role";
           }
           leaf health-status {
             type string;
             description
               "Peer health status";
           }
           leaf failover-readiness {
             type string;
             description
               "SRG failover readiness";
           }
           leaf failure-events {
             type string;
             description
               "List of failure events";
           }
           leaf preempt {
             type string;
             description
               "Preempt configuration for the redundancy group";
           }
           container chassis-high-availability-srg-info-list {
             description
               "Displays each services redundancy group info";
             leaf srg-id {
               type int32;
               description
                 "Current services redundancy group identifier";
             }
             leaf deployment-type {
               type string;
               description
                 "Deployment Type";
             }
             leaf node-role {
               type string;
               description
                 "Local node role";
             }
             leaf activeness-priority {
               type int32;
               description
                 "SRG activeness priority";
             }
             leaf preemption {
               type string;
               description
                 "Preemption enable flag Status";
             }
             leaf hold-timer {
               type int32;
               description
                 "SRG hold down timer";
             }
             leaf process-pkt-in-bkp-state {
               type string;
               description
                 "SRG backup state pkt processing info";
             }
             leaf service-names {
               type string;
               description
                 "SRG service names";
             }
             leaf control-plane {
               type string;
               description
                 "Control plane status";
             }
             leaf system-integrity-check {
               type string;
               description
                 "Status of system integrity check";
             }
             leaf peer-id {
               type int32;
               description
                 "Peer identifier";
             }
             leaf peer-node-role {
               type string;
               description
                 "Peer node role";
             }
             leaf health-status {
               type string;
               description
                 "Peer health status";
             }
             leaf failover-readiness {
               type string;
               description
                 "SRG failover readiness";
             }
             leaf failure-events {
               type string;
               description
                 "List of failure events";
             }
             leaf preempt {
               type string;
               description
                 "Preempt configuration for the redundancy group";
             }
           }
           container high-availability-srg-signal-rt-info {
             description
               "  SRG Signal route Info";
             list ha-srg-signal-rt-list {
               description
                 "Display each signal route information";
               leaf ha-srg-signal-rt-type {
                 type string;
                 description
                   "  SRG  Signal route type";
               }
               leaf ha-srg-signal-rt-ipaddr {
                 type string;
                 description
                   "IP address configured as SRG active signal route";
               }
               leaf ha-srg-signal-rt-rt {
                 type string;
                 description
                   "Routing table configured for active signal route";
               }
               leaf ha-srg-signal-rt-status {
                 type string;
                 description
                   " SRG signal Route installation status";
               }
             }
           }
           container high-availability-srg-vip-info {
             description
               "  SRG Virtual IP Info";
             list ha-srg-vip-list {
               key "ha-srg-vip-index";
               description
                 "Display each Virtual IP information";
               leaf ha-srg-vip-index {
                 type string;
                 description
                   "  SRG  Signal Virtual IP Index";
               }
               leaf ha-srg-virtual-ipaddr {
                 type string;
                 description
                   "IP address configured as SRG virtual IP";
               }
               leaf ha-srg-virtual-ipaddr2 {
                 type string;
                 description
                   "IP address configured as SRG virtual IP";
               }
               leaf ha-srg-virtual-mac-address {
                 type string;
                 description
                   "MAC address for the virtual IP.";
               }
               leaf ha-srg-vip-if-name {
                 type string;
                 description
                   "Interface for the virtual IP assignment";
               }
               leaf ha-srg-vip-status {
                 type string;
                 description
                   " SRG Virtual IP assignmentstatus";
               }
             }
           }
           list high-availability-srg-state-events {
             description
               "List of service redundancy group state change events";
             leaf-list high-availability-srg-state-event {
               type string;
               description
                 "Recorded service redundancy group state change event";
             }
           }
           list high-availability-peer-status-events {
             description
               "List of HA Peer Conn events";
             leaf-list high-availability-peer-status-event {
               type string;
               description
                 "Recorded HA Peer Conn event";
             }
           }
           list high-availability-hw-upgrade-events {
             description
               "List of HA hardware upgrade events";
             leaf-list high-availability-hw-upgrade-event {
               type string;
               description
                 "Recorded HA hardware upgrade event";
             }
           }
           container chassis-high-availability-srg-probe {
             description
               "SRG split brain prevention probe info";
             list chassis-high-availability-srg-probe-list {
               key "ha-srg-probe-dst-ipaddr";
               description
                 "Display each probe information";
               leaf ha-srg-probe-dst-ipaddr {
                 type string;
                 description
                   "Destination IP address used for probing";
               }
               leaf ha-srg-probe-src-ipaddr {
                 type string;
                 description
                   "Source IP address used for probing";
               }
               leaf ha-srg-vip-if-name {
                 type string;
                 description
                   "Interface for the virtual IP assignment";
               }
               leaf ha-srg-probe-rt {
                 type string;
                 description
                   "Routing instance used for probing";
               }
               leaf ha-srg-probe-type {
                 type string;
                 description
                   "Probing type";
               }
               leaf ha-probe-interval {
                 type int32;
                 description
                   "HA probe interval in ms";
               }
               leaf ha-probe-multiplier {
                 type int32;
                 description
                   "HA probe multiplier";
               }
               leaf ha-probe-status {
                 type string;
                 description
                   "Probing status";
               }
               leaf ha-probe-result {
                 type string;
                 description
                   "Probing result";
               }
               leaf ha-srg-probe-fail-reason {
                 type string;
                 description
                   "Probing failure reason";
               }
             }
           }
           container chassis-high-availability-srg-mon-info {
             description
               "SRG global threshold info";
             leaf ha-srg-mon-status {
               type string;
               description
                 "SRG monitor status";
             }
             leaf ha-srg-mon-threshold {
               type int32;
               description
                 "SRG monitor threshold";
             }
             leaf ha-srg-mon-weight {
               type int32;
               description
                 "SRG monitor weight";
             }
             leaf ha-srg-mon-failed-objects {
               type int32;
               description
                 "SRG monitor failed objects";
             }
           }
           container chassis-high-availability-srg-obj-info {
             description
               "SRG monitor-object info";
             leaf ha-srg-obj-name {
               type string;
               description
                 "SRG monitor object name";
             }
             leaf ha-srg-obj-status {
               type string;
               description
                 "SRG monitor object status";
             }
             leaf ha-srg-obj-entries {
               type string;
               description
                 "SRG monitor object monitored entries";
             }
             leaf ha-srg-obj-failure {
               type string;
               description
                 "SRG monitor object monitored failures";
             }
             leaf ha-srg-obj-threshold {
               type int32;
               description
                 "SRG monitor object threshold";
             }
             leaf ha-srg-obj-weight {
               type int32;
               description
                 "SRG monitor object current weight";
             }
           }
           container chassis-high-availability-srg-bfdmon {
             description
               " SRG BFD mon information ";
             leaf ha-srg-bfdmon-status {
               type string;
               description
                 "HA overall bfd-monitoring status";
             }
             container chassis-high-availability-srg-bfdmon-list {
               description
                 " Display each BFD mon entry Information";
               leaf ha-srg-bfdmon-src-ipaddr {
                 type string;
                 description
                   "Source IP address configured for HA bfd-monitoring";
               }
               leaf ha-srg-bfdmon-dst-ipaddr {
                 type string;
                 description
                   "Destination IP address configured for HA bfd-monitoring";
               }
               leaf ha-srg-bfdmon-rt {
                 type string;
                 description
                   "Routing instance configured for HA bfd-monitoring";
               }
               leaf ha-srg-bfdmon-type {
                 type string;
                 description
                   "HA bfd-monitoring type";
               }
               leaf ha-srg-bfdmon-ifl-name {
                 type string;
                 description
                   "HA bfd-monitoring IFL name";
               }
               leaf ha-srg-bfdmon-state {
                 type string;
                 description
                   "HA bfd-monitoring state";
               }
             }
           }
           list high-availability-bfdmon-status-events {
             description
               "List of BFD-monitoring status events";
             leaf-list high-availability-bfdmon-status-event {
               type string;
               description
                 "Recorded BFD-monitoring status event";
             }
           }
           container chassis-high-availability-srg-ipmon {
             description
               "SRG IP monitoring Info";
             leaf ha-srg-ipmon-status {
               type string;
               description
                 "SRG overall IP-monitoring status";
             }
             container chassis-high-availability-srg-ipmon-list {
               description
                 " Display each IP monitoring entry";
               leaf ha-srg-ipmon-dst-ipaddr {
                 type string;
                 description
                   "Destination IP address configured for HA ip-monitoring";
               }
               leaf ha-srg-ipmon-rt {
                 type string;
                 description
                   "Routing instance configured for HA ip-monitoring";
               }
               leaf ha-ipmon-status {
                 type string;
                 description
                   "HA ip-monitoring status";
               }
               leaf ha-srg-ipmon-reason {
                 type string;
                 description
                   "HA ip-monitoring failure reason";
               }
             }
           }
           container chassis-high-availability-srg-obj-ipmon {
             description
               "SRG monitor object IP monitoring Info";
             leaf ha-srg-obj-ipmon-threshold {
               type int32;
               description
                 "SRG monitor object IP-monitoring threshold";
             }
             leaf ha-srg-obj-ipmon-weight {
               type int32;
               description
                 "SRG monitor object IP-monitoring weight";
             }
             leaf ha-srg-obj-ipmon-status {
               type string;
               description
                 "SRG monitor object IP-monitoring global status";
             }
             container chassis-high-availability-srg-obj-ipmon-list {
               description
                 " Display each monitor object IP monitoring entry status";
               leaf ha-srg-obj-ipmon-entry-status {
                 type string;
                 description
                   "HA SRG monitor object ip-monitoring state";
               }
               leaf ha-srg-obj-ipmon-entry-weight {
                 type int32;
                 description
                   "HA SRG monitor object ip-monitoring weight";
               }
               leaf ha-srg-obj-ipmon-entry-dst-ipaddr {
                 type string;
                 description
                   "Destination IP address configured for HA ip-monitoring";
               }
             }
           }
           container chassis-high-availability-srg-obj-ipmon-detail {
             description
               "SRG monitor object IP monitoring detail Info";
             container chassis-high-availability-srg-ipmon-list {
               description
                 " Display each IP monitoring entry";
               leaf ha-srg-ipmon-dst-ipaddr {
                 type string;
                 description
                   "Destination IP address configured for HA ip-monitoring";
               }
               leaf ha-srg-ipmon-rt {
                 type string;
                 description
                   "Routing instance configured for HA ip-monitoring";
               }
               leaf ha-ipmon-status {
                 type string;
                 description
                   "HA ip-monitoring status";
               }
               leaf ha-srg-ipmon-reason {
                 type string;
                 description
                   "HA ip-monitoring failure reason";
               }
             }
           }
           list high-availability-ipmon-status-events {
             description
               "List of ip-monitoring status events";
             leaf-list high-availability-ipmon-status-event {
               type string;
               description
                 "Recorded ip-monitoring status event";
             }
           }
           list high-availability-probe-status-events {
             description
               "List of activeness probe status events";
             leaf-list high-availability-probe-status-event {
               type string;
               description
                 "Recorded activeness probe status event";
             }
           }
           container chassis-high-availability-srg-ifmon {
             description
               "SRG Interface monitoring Info";
             leaf ha-srg-ifmon-status {
               type string;
               description
                 "HA overall Interface-monitoring status";
             }
             container chassis-high-availability-srg-ifmon-list {
               description
                 " Display each Interface monitoring entry";
               leaf ha-srg-ifmon-if-name {
                 type string;
                 description
                   "HA Interface-monitoring IF name";
               }
               leaf ha-srg-ifmon-state {
                 type string;
                 description
                   "HA Interface-monitoring state";
               }
             }
           }
         }
         list srg-info-detail {
           leaf srg-id {
             type int32;
             description
               "Current services redundancy group identifier";
           }
           leaf deployment-type {
             type string;
             description
               "Deployment Type";
           }
           leaf node-role {
             type string;
             description
               "Local node role";
           }
           leaf activeness-priority {
             type int32;
             description
               "SRG activeness priority";
           }
           leaf preemption {
             type string;
             description
               "Preemption enable flag Status";
           }
           leaf hold-timer {
             type int32;
             description
               "SRG hold down timer";
           }
           leaf process-pkt-in-bkp-state {
             type string;
             description
               "SRG backup state pkt processing info";
           }
           leaf service-names {
             type string;
             description
               "SRG service names";
           }
           leaf control-plane {
             type string;
             description
               "Control plane status";
           }
           leaf system-integrity-check {
             type string;
             description
               "Status of system integrity check";
           }
           leaf peer-id {
             type int32;
             description
               "Peer identifier";
           }
           leaf peer-node-role {
             type string;
             description
               "Peer node role";
           }
           leaf health-status {
             type string;
             description
               "Peer health status";
           }
           leaf failover-readiness {
             type string;
             description
               "SRG failover readiness";
           }
           leaf failure-events {
             type string;
             description
               "List of failure events";
           }
           leaf preempt {
             type string;
             description
               "Preempt configuration for the redundancy group";
           }
           container chassis-high-availability-srg-info-list {
             description
               "Displays each services redundancy group info";
             leaf srg-id {
               type int32;
               description
                 "Current services redundancy group identifier";
             }
             leaf deployment-type {
               type string;
               description
                 "Deployment Type";
             }
             leaf node-role {
               type string;
               description
                 "Local node role";
             }
             leaf activeness-priority {
               type int32;
               description
                 "SRG activeness priority";
             }
             leaf preemption {
               type string;
               description
                 "Preemption enable flag Status";
             }
             leaf hold-timer {
               type int32;
               description
                 "SRG hold down timer";
             }
             leaf process-pkt-in-bkp-state {
               type string;
               description
                 "SRG backup state pkt processing info";
             }
             leaf service-names {
               type string;
               description
                 "SRG service names";
             }
             leaf control-plane {
               type string;
               description
                 "Control plane status";
             }
             leaf system-integrity-check {
               type string;
               description
                 "Status of system integrity check";
             }
             leaf peer-id {
               type int32;
               description
                 "Peer identifier";
             }
             leaf peer-node-role {
               type string;
               description
                 "Peer node role";
             }
             leaf health-status {
               type string;
               description
                 "Peer health status";
             }
             leaf failover-readiness {
               type string;
               description
                 "SRG failover readiness";
             }
             leaf failure-events {
               type string;
               description
                 "List of failure events";
             }
             leaf preempt {
               type string;
               description
                 "Preempt configuration for the redundancy group";
             }
           }
           container high-availability-srg-signal-rt-info {
             description
               "  SRG Signal route Info";
             list ha-srg-signal-rt-list {
               description
                 "Display each signal route information";
               leaf ha-srg-signal-rt-type {
                 type string;
                 description
                   "  SRG  Signal route type";
               }
               leaf ha-srg-signal-rt-ipaddr {
                 type string;
                 description
                   "IP address configured as SRG active signal route";
               }
               leaf ha-srg-signal-rt-rt {
                 type string;
                 description
                   "Routing table configured for active signal route";
               }
               leaf ha-srg-signal-rt-status {
                 type string;
                 description
                   " SRG signal Route installation status";
               }
             }
           }
           container high-availability-srg-vip-info {
             description
               "  SRG Virtual IP Info";
             list ha-srg-vip-list {
               key "ha-srg-vip-index";
               description
                 "Display each Virtual IP information";
               leaf ha-srg-vip-index {
                 type string;
                 description
                   "  SRG  Signal Virtual IP Index";
               }
               leaf ha-srg-virtual-ipaddr {
                 type string;
                 description
                   "IP address configured as SRG virtual IP";
               }
               leaf ha-srg-virtual-ipaddr2 {
                 type string;
                 description
                   "IP address configured as SRG virtual IP";
               }
               leaf ha-srg-virtual-mac-address {
                 type string;
                 description
                   "MAC address for the virtual IP.";
               }
               leaf ha-srg-vip-if-name {
                 type string;
                 description
                   "Interface for the virtual IP assignment";
               }
               leaf ha-srg-vip-status {
                 type string;
                 description
                   " SRG Virtual IP assignmentstatus";
               }
             }
           }
           list high-availability-srg-state-events {
             description
               "List of service redundancy group state change events";
             leaf-list high-availability-srg-state-event {
               type string;
               description
                 "Recorded service redundancy group state change event";
             }
           }
           list high-availability-peer-status-events {
             description
               "List of HA Peer Conn events";
             leaf-list high-availability-peer-status-event {
               type string;
               description
                 "Recorded HA Peer Conn event";
             }
           }
           list high-availability-hw-upgrade-events {
             description
               "List of HA hardware upgrade events";
             leaf-list high-availability-hw-upgrade-event {
               type string;
               description
                 "Recorded HA hardware upgrade event";
             }
           }
           container chassis-high-availability-srg-probe {
             description
               "SRG split brain prevention probe info";
             list chassis-high-availability-srg-probe-list {
               key "ha-srg-probe-dst-ipaddr";
               description
                 "Display each probe information";
               leaf ha-srg-probe-dst-ipaddr {
                 type string;
                 description
                   "Destination IP address used for probing";
               }
               leaf ha-srg-probe-src-ipaddr {
                 type string;
                 description
                   "Source IP address used for probing";
               }
               leaf ha-srg-vip-if-name {
                 type string;
                 description
                   "Interface for the virtual IP assignment";
               }
               leaf ha-srg-probe-rt {
                 type string;
                 description
                   "Routing instance used for probing";
               }
               leaf ha-srg-probe-type {
                 type string;
                 description
                   "Probing type";
               }
               leaf ha-probe-interval {
                 type int32;
                 description
                   "HA probe interval in ms";
               }
               leaf ha-probe-multiplier {
                 type int32;
                 description
                   "HA probe multiplier";
               }
               leaf ha-probe-status {
                 type string;
                 description
                   "Probing status";
               }
               leaf ha-probe-result {
                 type string;
                 description
                   "Probing result";
               }
               leaf ha-srg-probe-fail-reason {
                 type string;
                 description
                   "Probing failure reason";
               }
             }
           }
           container chassis-high-availability-srg-mon-info {
             description
               "SRG global threshold info";
             leaf ha-srg-mon-status {
               type string;
               description
                 "SRG monitor status";
             }
             leaf ha-srg-mon-threshold {
               type int32;
               description
                 "SRG monitor threshold";
             }
             leaf ha-srg-mon-weight {
               type int32;
               description
                 "SRG monitor weight";
             }
             leaf ha-srg-mon-failed-objects {
               type int32;
               description
                 "SRG monitor failed objects";
             }
           }
           container chassis-high-availability-srg-obj-info {
             description
               "SRG monitor-object info";
             leaf ha-srg-obj-name {
               type string;
               description
                 "SRG monitor object name";
             }
             leaf ha-srg-obj-status {
               type string;
               description
                 "SRG monitor object status";
             }
             leaf ha-srg-obj-entries {
               type string;
               description
                 "SRG monitor object monitored entries";
             }
             leaf ha-srg-obj-failure {
               type string;
               description
                 "SRG monitor object monitored failures";
             }
             leaf ha-srg-obj-threshold {
               type int32;
               description
                 "SRG monitor object threshold";
             }
             leaf ha-srg-obj-weight {
               type int32;
               description
                 "SRG monitor object current weight";
             }
           }
           container chassis-high-availability-srg-bfdmon {
             description
               " SRG BFD mon information ";
             leaf ha-srg-bfdmon-status {
               type string;
               description
                 "HA overall bfd-monitoring status";
             }
             container chassis-high-availability-srg-bfdmon-list {
               description
                 " Display each BFD mon entry Information";
               leaf ha-srg-bfdmon-src-ipaddr {
                 type string;
                 description
                   "Source IP address configured for HA bfd-monitoring";
               }
               leaf ha-srg-bfdmon-dst-ipaddr {
                 type string;
                 description
                   "Destination IP address configured for HA bfd-monitoring";
               }
               leaf ha-srg-bfdmon-rt {
                 type string;
                 description
                   "Routing instance configured for HA bfd-monitoring";
               }
               leaf ha-srg-bfdmon-type {
                 type string;
                 description
                   "HA bfd-monitoring type";
               }
               leaf ha-srg-bfdmon-ifl-name {
                 type string;
                 description
                   "HA bfd-monitoring IFL name";
               }
               leaf ha-srg-bfdmon-state {
                 type string;
                 description
                   "HA bfd-monitoring state";
               }
             }
           }
           list high-availability-bfdmon-status-events {
             description
               "List of BFD-monitoring status events";
             leaf-list high-availability-bfdmon-status-event {
               type string;
               description
                 "Recorded BFD-monitoring status event";
             }
           }
           container chassis-high-availability-srg-ipmon {
             description
               "SRG IP monitoring Info";
             leaf ha-srg-ipmon-status {
               type string;
               description
                 "SRG overall IP-monitoring status";
             }
             container chassis-high-availability-srg-ipmon-list {
               description
                 " Display each IP monitoring entry";
               leaf ha-srg-ipmon-dst-ipaddr {
                 type string;
                 description
                   "Destination IP address configured for HA ip-monitoring";
               }
               leaf ha-srg-ipmon-rt {
                 type string;
                 description
                   "Routing instance configured for HA ip-monitoring";
               }
               leaf ha-ipmon-status {
                 type string;
                 description
                   "HA ip-monitoring status";
               }
               leaf ha-srg-ipmon-reason {
                 type string;
                 description
                   "HA ip-monitoring failure reason";
               }
             }
           }
           container chassis-high-availability-srg-obj-ipmon {
             description
               "SRG monitor object IP monitoring Info";
             leaf ha-srg-obj-ipmon-threshold {
               type int32;
               description
                 "SRG monitor object IP-monitoring threshold";
             }
             leaf ha-srg-obj-ipmon-weight {
               type int32;
               description
                 "SRG monitor object IP-monitoring weight";
             }
             leaf ha-srg-obj-ipmon-status {
               type string;
               description
                 "SRG monitor object IP-monitoring global status";
             }
             container chassis-high-availability-srg-obj-ipmon-list {
               description
                 " Display each monitor object IP monitoring entry status";
               leaf ha-srg-obj-ipmon-entry-status {
                 type string;
                 description
                   "HA SRG monitor object ip-monitoring state";
               }
               leaf ha-srg-obj-ipmon-entry-weight {
                 type int32;
                 description
                   "HA SRG monitor object ip-monitoring weight";
               }
               leaf ha-srg-obj-ipmon-entry-dst-ipaddr {
                 type string;
                 description
                   "Destination IP address configured for HA ip-monitoring";
               }
             }
           }
           container chassis-high-availability-srg-obj-ipmon-detail {
             description
               "SRG monitor object IP monitoring detail Info";
             container chassis-high-availability-srg-ipmon-list {
               description
                 " Display each IP monitoring entry";
               leaf ha-srg-ipmon-dst-ipaddr {
                 type string;
                 description
                   "Destination IP address configured for HA ip-monitoring";
               }
               leaf ha-srg-ipmon-rt {
                 type string;
                 description
                   "Routing instance configured for HA ip-monitoring";
               }
               leaf ha-ipmon-status {
                 type string;
                 description
                   "HA ip-monitoring status";
               }
               leaf ha-srg-ipmon-reason {
                 type string;
                 description
                   "HA ip-monitoring failure reason";
               }
             }
           }
           list high-availability-ipmon-status-events {
             description
               "List of ip-monitoring status events";
             leaf-list high-availability-ipmon-status-event {
               type string;
               description
                 "Recorded ip-monitoring status event";
             }
           }
           list high-availability-probe-status-events {
             description
               "List of activeness probe status events";
             leaf-list high-availability-probe-status-event {
               type string;
               description
                 "Recorded activeness probe status event";
             }
           }
           container chassis-high-availability-srg-ifmon {
             description
               "SRG Interface monitoring Info";
             leaf ha-srg-ifmon-status {
               type string;
               description
                 "HA overall Interface-monitoring status";
             }
             container chassis-high-availability-srg-ifmon-list {
               description
                 " Display each Interface monitoring entry";
               leaf ha-srg-ifmon-if-name {
                 type string;
                 description
                   "HA Interface-monitoring IF name";
               }
               leaf ha-srg-ifmon-state {
                 type string;
                 description
                   "HA Interface-monitoring state";
               }
             }
           }
         }
       }
     }
     container chassis-mnha-peer-domain-info-detail {
       description
         "Displays high-availability peer related info";
       leaf peer-domain-info {
         type string;
         description
           "Peer-domain-info";
       }
       leaf peer-domain-id {
         type int32;
         description
           "Peer-domain-id";
       }
       leaf-list peer-local-ip {
         type jt:ipaddr;
         description
           "Peer node IPv4 address";
       }
       list high-availability-hw-upgrade-events {
         description
           "List of HA hardware upgrade events";
         leaf-list high-availability-hw-upgrade-event {
           type string;
           description
             "Recorded HA hardware upgrade event";
         }
       }
       list chassis-mnha-idl-peer-info {
         description
           "Displays mnha idl peer related info";
         leaf high-availability-peer-desc {
           type string;
           description
             "Peer description";
         }
         leaf peer-domain-id {
           type int32;
           description
             "Peer-domain-id";
         }
         leaf high-availability-peer-id {
           type int32;
           description
             "Peer identifier that is configured";
         }
         leaf high-availability-peer-ip-address {
           type jt:ipaddr;
           description
             "Peer remote IPv4 address that is configured";
         }
         leaf-list high-availability-local-interface {
           type string;
           description
             "Local interface";
         }
         leaf high-availability-peer-rt-instance {
           type string;
           description
             "Routing Instance name for HA peer";
         }
         leaf high-availability-peer-encryption-status {
           type string;
           description
             "Encryption status of the current node";
         }
         leaf high-availability-peer-idl-bfd-status {
           type string;
           description
             "IDL BFD Status of the current node";
         }
         leaf cold-sync-status {
           type string;
           description
             "Cold synchronization status";
         }
         leaf peer-hw-incompatible {
           type string;
           description
             "Peer hardware compatible status";
         }
         leaf peer-internal-interface {
           type string;
           description
             "Peer internal interface";
         }
         leaf peer-internal-local-ip {
           type jt:ipaddr;
           description
             "Internal local IPv4 address";
         }
         leaf peer-internal-peer-ip {
           type jt:ipaddr;
           description
             "Internal peer IPv4 address";
         }
         leaf peer-internal-routing-instance {
           type string;
           description
             "Peer internal routing instance";
         }
         leaf high-availability-peer-detect-time {
           type string;
           description
             "Configured Peer BFD detection time";
         }
         container chassis-mnha-peer-node-icl-info {
           description
             "Displays high-availability icl info";
           leaf states-from-domain-id {
             type int32;
             description
               "States from domain id";
           }
           leaf states-from-node-id {
             type int32;
             description
               "States from node id";
           }
           leaf icl-conn-state {
             type string;
             description
               "ICL Conn state";
           }
           leaf cold-sync-status {
             type string;
             description
               "Cold synchronization status";
           }
         }
         container chassis-mnha-peer-domain-idl-info {
           description
             "Displays high-availability peer domain IDL BFD and CS state";
           leaf states-from-domain-id {
             type int32;
             description
               "States from domain id";
           }
           leaf states-from-node-id {
             type int32;
             description
               "States from node id";
           }
           leaf domain-id {
             type int32;
             description
               "Domain-id";
           }
           leaf peer-id {
             type int32;
             description
               "Peer identifier";
           }
           leaf conn-state {
             type string;
             description
               "Conn state";
           }
           leaf rtt-result {
             type string;
             description
               "RTT result";
           }
           leaf cold-sync-status {
             type string;
             description
               "Cold synchronization status";
           }
           leaf srg0-idl-status {
             type string;
             description
               "SRG0 idl status";
           }
         }
         list high-availability-peer-packet-stats {
           description
             "Peer Packet Stats";
           leaf packet-send-err-cnt {
             type int32;
             description
               "Peer packet send error cnt";
           }
           leaf packet-recv-err-cnt {
             type int32;
             description
               "Peer packet recv error cnt";
           }
           list peer-packet-send-rcv-stats {
             description
               "Peer Packet Send receive Stats";
             list peer-packet-stats-list {
               description
                 "Stats for each peer packet type";
               leaf peer-packet-type {
                 type string;
                 description
                   "Peer packet Type";
               }
               leaf peer-packet-send-cnt {
                 type int32;
                 description
                   "Peer packet sent count";
               }
               leaf peer-packet-rcv-cnt {
                 type int32;
                 description
                   "Peer packet rcv cnt";
               }
             }
           }
         }
       }
       container cold-synchronization-monitoring-information {
         description
           "Cold sync monitoring related information";
         leaf-list cold-synchronization-progress {
           type string;
           description
             "Cold synchronization progress";
         }
         container cold-synchronization-status-information {
           description
             "Cold synchronization related status information";
           leaf cold-synchronization-completed {
             type string;
             description
               "List of PFE's which have completed cold synchnronization";
           }
           leaf cold-synchronization-not-completed {
             type string;
             description
               "List of PFE's which have failed cold synchnronization";
           }
           leaf cold-synchronization-unknown {
             type string;
             description
               "List of PFE's for which cold synchnronization statusupdate 
               is not received";
           }
           leaf cold-synchronization-weight {
             type uint32;
             description
               "Current Cold Synchronization weight";
           }
         }
         container cold-synchronization-statistics {
           description
             "Cold synchronization statistics";
           leaf current-cold-synchronization-completed {
             type uint32;
             description
               "Cold synchronization completed for current jsrpd session";
           }
           leaf current-cold-synchronization-failed {
             type uint32;
             description
               "Cold synchronization failed for current jsrpd session";
           }
           list cold-synchronization-pfe-statistics {
             description
               "Cold synchroniizaton statistics for each PFE";
             leaf pfe-name {
               type string;
               description
                 "Name of the PFE";
             }
             leaf cold-synchronization-pfe-completed {
               type uint32;
               description
                 "Cold synchronization complete instances for a given PFE";
             }
             leaf cold-synchronization-pfe-failed {
               type uint32;
               description
                 "Cold synchronization complete instances for a given PFE";
             }
           }
         }
         container cold-synchronization-events {
           description
             "List of cold synchronization events";
           leaf-list cold-synchronization-event {
             type string;
             description
               "Recorded cold sync complete/failure for a PFE";
           }
         }
       }
       container spu-monitoring-information {
         description
           "SPU monitoring related information";
         container spu-monitoring-status {
           description
             "SPU monitoring related status information";
           leaf spu-monitoring-state {
             type string;
             description
               "SPU current monitoring mode Disabled/Enabled/Active";
           }
           leaf spu-monitoring-weight {
             type uint32;
             description
               "Current SPU monitoring weight";
           }
           list spu-monitoring-spu-state {
             description
               "Each SPU current state";
             container spu-monitoring-spu-state-list {
               description
                 "Each SPU current state in list";
               leaf pfe-name {
                 type string;
                 description
                   "Name of the PFE";
               }
               leaf pic-state {
                 type string;
                 description
                   "State of each PIC";
               }
             }
           }
         }
         container spu-monitoring-statistics {
           description
             "Detailed statistics of SPU monitoring";
           leaf spu-up-count {
             type uint32;
             description
               "Number of SPUs that are up";
           }
           leaf spu-down-count {
             type uint32;
             description
               "Number of SPUs that are down";
           }
           leaf npc-up-count {
             type uint32;
             description
               "Number of NPCs that are up";
           }
           leaf npc-down-count {
             type uint32;
             description
               "Number of NPCs that are down";
           }
           leaf chinfo-blob-error-count {
             type uint32;
             description
               "Error count reading chinfo blob";
           }
         }
         container spu-monitoring-events {
           description
             "List of SPU monitoring events";
           leaf-list spu-monitoring-event {
             type string;
             description
               "Recorded SPU monitoring events";
           }
         }
       }
       list loopback-information {
         description
           "Loopback information";
         container loopback-information-list {
           description
             "Display loopback information list";
           leaf pfe-name {
             type string;
             description
               "Name of the PFE";
           }
           leaf loopback-status {
             type string;
             description
               "Loopback status of each PIC";
           }
           leaf nexthop-status {
             type string;
             description
               "Nexthop status of each PIC";
           }
           leaf mbuf-status {
             type string;
             description
               "Mbuf status of each PIC";
           }
         }
       }
       container high-availability-hardware-monitoring-information {
         description
           "Displays complete high-availability hardware monitoring 
           information for debugging purposes";
         container hardware-monitoring-events {
           description
             "List of hardware monitoring events";
           leaf-list hardware-monitoring-event {
             type string;
             description
               "Recorded hardware monitoring events";
           }
         }
         container high-availability-hardware-monitoring-status-information {
           leaf high-availability-hardware-monitoring-activation-status {
             type string;
             description
               "Hardware monitoring is enabled/disabled";
           }
           leaf high-availability-hardware-monitoring-ctrl-plane-errors {
             type int32;
             description
               "Hardware monitoring Ctrl plane errors";
           }
           leaf high-availability-hardware-monitoring-data-plane-errors {
             type int32;
             description
               "Hardware monitoring Data plane errors";
           }
         }
       }
       container chassis-high-availability-default-srg-info {
         description
           "Displays high-availability services redundancy group 0 info";
         leaf current-state {
           type string;
           description
             "SRG 0 current state";
         }
         leaf peer-id {
           type int32;
           description
             "Peer identifier";
         }
         leaf node-priority {
           type int32;
           description
             "Node-priority";
         }
         leaf peer-domain-id {
           type int32;
           description
             "Peer-domain-id";
         }
         list srg-peer-domain-peer-id-info {
           description
             "Idl peer node Id";
           leaf idl-peer-id {
             type int32;
             description
               "IDL Peer identifier";
           }
         }
         container high-availability-srg-signal-rt-info {
           description
             "  SRG Signal route Info";
           list ha-srg-signal-rt-list {
             description
               "Display each signal route information";
             leaf ha-srg-signal-rt-type {
               type string;
               description
                 "  SRG  Signal route type";
             }
             leaf ha-srg-signal-rt-ipaddr {
               type string;
               description
                 "IP address configured as SRG active signal route";
             }
             leaf ha-srg-signal-rt-rt {
               type string;
               description
                 "Routing table configured for active signal route";
             }
             leaf ha-srg-signal-rt-status {
               type string;
               description
                 " SRG signal Route installation status";
             }
           }
         }
         list chassis-high-availability-shutdown-interface {
           description
             "Display high-availability shutdown interface list";
           leaf high-availability-shutdown-interface-name {
             type string;
             description
               "Interface name for monitoring";
           }
         }
         container chassis-high-availability-srg-ipmon {
           description
             "SRG IP monitoring Info";
           leaf ha-srg-ipmon-status {
             type string;
             description
               "SRG overall IP-monitoring status";
           }
           container chassis-high-availability-srg-ipmon-list {
             description
               " Display each IP monitoring entry";
             leaf ha-srg-ipmon-dst-ipaddr {
               type string;
               description
                 "Destination IP address configured for HA ip-monitoring";
             }
             leaf ha-srg-ipmon-rt {
               type string;
               description
                 "Routing instance configured for HA ip-monitoring";
             }
             leaf ha-ipmon-status {
               type string;
               description
                 "HA ip-monitoring status";
             }
             leaf ha-srg-ipmon-reason {
               type string;
               description
                 "HA ip-monitoring failure reason";
             }
           }
         }
         container chassis-high-availability-srg-bfdmon {
           description
             " SRG BFD mon information ";
           leaf ha-srg-bfdmon-status {
             type string;
             description
               "HA overall bfd-monitoring status";
           }
           container chassis-high-availability-srg-bfdmon-list {
             description
               " Display each BFD mon entry Information";
             leaf ha-srg-bfdmon-src-ipaddr {
               type string;
               description
                 "Source IP address configured for HA bfd-monitoring";
             }
             leaf ha-srg-bfdmon-dst-ipaddr {
               type string;
               description
                 "Destination IP address configured for HA bfd-monitoring";
             }
             leaf ha-srg-bfdmon-rt {
               type string;
               description
                 "Routing instance configured for HA bfd-monitoring";
             }
             leaf ha-srg-bfdmon-type {
               type string;
               description
                 "HA bfd-monitoring type";
             }
             leaf ha-srg-bfdmon-ifl-name {
               type string;
               description
                 "HA bfd-monitoring IFL name";
             }
             leaf ha-srg-bfdmon-state {
               type string;
               description
                 "HA bfd-monitoring state";
             }
           }
         }
         container chassis-high-availability-srg-ifmon {
           description
             "SRG Interface monitoring Info";
           leaf ha-srg-ifmon-status {
             type string;
             description
               "HA overall Interface-monitoring status";
           }
           container chassis-high-availability-srg-ifmon-list {
             description
               " Display each Interface monitoring entry";
             leaf ha-srg-ifmon-if-name {
               type string;
               description
                 "HA Interface-monitoring IF name";
             }
             leaf ha-srg-ifmon-state {
               type string;
               description
                 "HA Interface-monitoring state";
             }
           }
         }
         container chassis-high-availability-srg-mon-info {
           description
             "SRG global threshold info";
           leaf ha-srg-mon-status {
             type string;
             description
               "SRG monitor status";
           }
           leaf ha-srg-mon-threshold {
             type int32;
             description
               "SRG monitor threshold";
           }
           leaf ha-srg-mon-weight {
             type int32;
             description
               "SRG monitor weight";
           }
           leaf ha-srg-mon-failed-objects {
             type int32;
             description
               "SRG monitor failed objects";
           }
         }
         container chassis-high-availability-srg-obj-info {
           description
             "SRG monitor-object info";
           leaf ha-srg-obj-name {
             type string;
             description
               "SRG monitor object name";
           }
           leaf ha-srg-obj-status {
             type string;
             description
               "SRG monitor object status";
           }
           leaf ha-srg-obj-entries {
             type string;
             description
               "SRG monitor object monitored entries";
           }
           leaf ha-srg-obj-failure {
             type string;
             description
               "SRG monitor object monitored failures";
           }
           leaf ha-srg-obj-threshold {
             type int32;
             description
               "SRG monitor object threshold";
           }
           leaf ha-srg-obj-weight {
             type int32;
             description
               "SRG monitor object current weight";
           }
         }
         container chassis-high-availability-srg-obj-ipmon {
           description
             "SRG monitor object IP monitoring Info";
           leaf ha-srg-obj-ipmon-threshold {
             type int32;
             description
               "SRG monitor object IP-monitoring threshold";
           }
           leaf ha-srg-obj-ipmon-weight {
             type int32;
             description
               "SRG monitor object IP-monitoring weight";
           }
           leaf ha-srg-obj-ipmon-status {
             type string;
             description
               "SRG monitor object IP-monitoring global status";
           }
           container chassis-high-availability-srg-obj-ipmon-list {
             description
               " Display each monitor object IP monitoring entry status";
             leaf ha-srg-obj-ipmon-entry-status {
               type string;
               description
                 "HA SRG monitor object ip-monitoring state";
             }
             leaf ha-srg-obj-ipmon-entry-weight {
               type int32;
               description
                 "HA SRG monitor object ip-monitoring weight";
             }
             leaf ha-srg-obj-ipmon-entry-dst-ipaddr {
               type string;
               description
                 "Destination IP address configured for HA ip-monitoring";
             }
           }
         }
         container chassis-high-availability-srg-obj-ipmon-detail {
           description
             "SRG monitor object IP monitoring detail Info";
           container chassis-high-availability-srg-ipmon-list {
             description
               " Display each IP monitoring entry";
             leaf ha-srg-ipmon-dst-ipaddr {
               type string;
               description
                 "Destination IP address configured for HA ip-monitoring";
             }
             leaf ha-srg-ipmon-rt {
               type string;
               description
                 "Routing instance configured for HA ip-monitoring";
             }
             leaf ha-ipmon-status {
               type string;
               description
                 "HA ip-monitoring status";
             }
             leaf ha-srg-ipmon-reason {
               type string;
               description
                 "HA ip-monitoring failure reason";
             }
           }
         }
         container chassis-high-availability-srg-obj-bfdmon {
           description
             "SRG monitor object BFD monitoring Info";
           leaf ha-srg-obj-bfdmon-threshold {
             type int32;
             description
               "SRG monitor object BFD-monitoring threshold";
           }
           leaf ha-srg-obj-bfdmon-weight {
             type int32;
             description
               "SRG monitor object BFD-monitoring weight";
           }
           leaf ha-srg-obj-bfdmon-status {
             type string;
             description
               "SRG monitor object BFD-monitoring global status";
           }
           container chassis-high-availability-srg-obj-bfdmon-list {
             description
               "Display each monitor object BFD monitoring entry status";
             leaf ha-srg-obj-bfdmon-entry-status {
               type string;
               description
                 "HA SRG monitor object BFD-monitoring state";
             }
             leaf ha-srg-obj-bfdmon-entry-weight {
               type int32;
               description
                 "HA SRG monitor object BFD-monitoring weight";
             }
             leaf ha-srg-obj-bfdmon-entry-dst-bfdaddr {
               type string;
               description
                 "Destination BFD address configured for HA BFD-monitoring";
             }
           }
         }
         container chassis-high-availability-srg-obj-bfdmon-detail {
           description
             "SRG monitor object BFD mon information ";
           container chassis-high-availability-srg-bfdmon-list {
             description
               " Display each BFD mon entry Information";
             leaf ha-srg-bfdmon-src-ipaddr {
               type string;
               description
                 "Source IP address configured for HA bfd-monitoring";
             }
             leaf ha-srg-bfdmon-dst-ipaddr {
               type string;
               description
                 "Destination IP address configured for HA bfd-monitoring";
             }
             leaf ha-srg-bfdmon-rt {
               type string;
               description
                 "Routing instance configured for HA bfd-monitoring";
             }
             leaf ha-srg-bfdmon-type {
               type string;
               description
                 "HA bfd-monitoring type";
             }
             leaf ha-srg-bfdmon-ifl-name {
               type string;
               description
                 "HA bfd-monitoring IFL name";
             }
             leaf ha-srg-bfdmon-state {
               type string;
               description
                 "HA bfd-monitoring state";
             }
           }
         }
         container chassis-high-availability-srg-obj-ifmon {
           description
             "SRG monitor object IF monitoring Info";
           leaf ha-srg-obj-ifmon-threshold {
             type int32;
             description
               "SRG monitor object IF-monitoring threshold";
           }
           leaf ha-srg-obj-ifmon-weight {
             type int32;
             description
               "SRG monitor object IF-monitoring current weight";
           }
           leaf ha-srg-ifmon-status {
             type string;
             description
               "HA overall Interface-monitoring status";
           }
           container chassis-high-availability-srg-obj-ifmon-list {
             description
               "Display each monitor object IF monitoring entry status";
             leaf ha-srg-ifmon-entry-status {
               type string;
               description
                 "HA SRG monitor object IF-monitoring entry status";
             }
             leaf ha-srg-obj-ifmon-entry-weight {
               type int32;
               description
                 "HA SRG monitor object IF-monitoring entry weight";
             }
             leaf ha-srg-ifmon-if-name {
               type string;
               description
                 "HA Interface-monitoring IF name";
             }
           }
         }
       }
       list chassis-high-availability-srg-info-detail {
         description
           "Displays high-availability services redundancy group detail info";
         container chassis-high-availability-srg-info-list {
           description
             "Displays each services redundancy group info";
           leaf srg-id {
             type int32;
             description
               "Current services redundancy group identifier";
           }
           leaf deployment-type {
             type string;
             description
               "Deployment Type";
           }
           leaf node-role {
             type string;
             description
               "Local node role";
           }
           leaf activeness-priority {
             type int32;
             description
               "SRG activeness priority";
           }
           leaf preemption {
             type string;
             description
               "Preemption enable flag Status";
           }
           leaf hold-timer {
             type int32;
             description
               "SRG hold down timer";
           }
           leaf process-pkt-in-bkp-state {
             type string;
             description
               "SRG backup state pkt processing info";
           }
           leaf service-names {
             type string;
             description
               "SRG service names";
           }
           leaf control-plane {
             type string;
             description
               "Control plane status";
           }
           leaf system-integrity-check {
             type string;
             description
               "Status of system integrity check";
           }
           leaf peer-id {
             type int32;
             description
               "Peer identifier";
           }
           leaf peer-node-role {
             type string;
             description
               "Peer node role";
           }
           leaf health-status {
             type string;
             description
               "Peer health status";
           }
           leaf failover-readiness {
             type string;
             description
               "SRG failover readiness";
           }
           leaf failure-events {
             type string;
             description
               "List of failure events";
           }
           leaf preempt {
             type string;
             description
               "Preempt configuration for the redundancy group";
           }
           container chassis-high-availability-srg-info-list {
             description
               "Displays each services redundancy group info";
             leaf srg-id {
               type int32;
               description
                 "Current services redundancy group identifier";
             }
             leaf deployment-type {
               type string;
               description
                 "Deployment Type";
             }
             leaf node-role {
               type string;
               description
                 "Local node role";
             }
             leaf activeness-priority {
               type int32;
               description
                 "SRG activeness priority";
             }
             leaf preemption {
               type string;
               description
                 "Preemption enable flag Status";
             }
             leaf hold-timer {
               type int32;
               description
                 "SRG hold down timer";
             }
             leaf process-pkt-in-bkp-state {
               type string;
               description
                 "SRG backup state pkt processing info";
             }
             leaf service-names {
               type string;
               description
                 "SRG service names";
             }
             leaf control-plane {
               type string;
               description
                 "Control plane status";
             }
             leaf system-integrity-check {
               type string;
               description
                 "Status of system integrity check";
             }
             leaf peer-id {
               type int32;
               description
                 "Peer identifier";
             }
             leaf peer-node-role {
               type string;
               description
                 "Peer node role";
             }
             leaf health-status {
               type string;
               description
                 "Peer health status";
             }
             leaf failover-readiness {
               type string;
               description
                 "SRG failover readiness";
             }
             leaf failure-events {
               type string;
               description
                 "List of failure events";
             }
             leaf preempt {
               type string;
               description
                 "Preempt configuration for the redundancy group";
             }
           }
           container high-availability-srg-signal-rt-info {
             description
               "  SRG Signal route Info";
             list ha-srg-signal-rt-list {
               description
                 "Display each signal route information";
               leaf ha-srg-signal-rt-type {
                 type string;
                 description
                   "  SRG  Signal route type";
               }
               leaf ha-srg-signal-rt-ipaddr {
                 type string;
                 description
                   "IP address configured as SRG active signal route";
               }
               leaf ha-srg-signal-rt-rt {
                 type string;
                 description
                   "Routing table configured for active signal route";
               }
               leaf ha-srg-signal-rt-status {
                 type string;
                 description
                   " SRG signal Route installation status";
               }
             }
           }
           container high-availability-srg-vip-info {
             description
               "  SRG Virtual IP Info";
             list ha-srg-vip-list {
               key "ha-srg-vip-index";
               description
                 "Display each Virtual IP information";
               leaf ha-srg-vip-index {
                 type string;
                 description
                   "  SRG  Signal Virtual IP Index";
               }
               leaf ha-srg-virtual-ipaddr {
                 type string;
                 description
                   "IP address configured as SRG virtual IP";
               }
               leaf ha-srg-virtual-ipaddr2 {
                 type string;
                 description
                   "IP address configured as SRG virtual IP";
               }
               leaf ha-srg-virtual-mac-address {
                 type string;
                 description
                   "MAC address for the virtual IP.";
               }
               leaf ha-srg-vip-if-name {
                 type string;
                 description
                   "Interface for the virtual IP assignment";
               }
               leaf ha-srg-vip-status {
                 type string;
                 description
                   " SRG Virtual IP assignmentstatus";
               }
             }
           }
           list high-availability-srg-state-events {
             description
               "List of service redundancy group state change events";
             leaf-list high-availability-srg-state-event {
               type string;
               description
                 "Recorded service redundancy group state change event";
             }
           }
           list high-availability-peer-status-events {
             description
               "List of HA Peer Conn events";
             leaf-list high-availability-peer-status-event {
               type string;
               description
                 "Recorded HA Peer Conn event";
             }
           }
           list high-availability-hw-upgrade-events {
             description
               "List of HA hardware upgrade events";
             leaf-list high-availability-hw-upgrade-event {
               type string;
               description
                 "Recorded HA hardware upgrade event";
             }
           }
           container chassis-high-availability-srg-probe {
             description
               "SRG split brain prevention probe info";
             list chassis-high-availability-srg-probe-list {
               key "ha-srg-probe-dst-ipaddr";
               description
                 "Display each probe information";
               leaf ha-srg-probe-dst-ipaddr {
                 type string;
                 description
                   "Destination IP address used for probing";
               }
               leaf ha-srg-probe-src-ipaddr {
                 type string;
                 description
                   "Source IP address used for probing";
               }
               leaf ha-srg-vip-if-name {
                 type string;
                 description
                   "Interface for the virtual IP assignment";
               }
               leaf ha-srg-probe-rt {
                 type string;
                 description
                   "Routing instance used for probing";
               }
               leaf ha-srg-probe-type {
                 type string;
                 description
                   "Probing type";
               }
               leaf ha-probe-interval {
                 type int32;
                 description
                   "HA probe interval in ms";
               }
               leaf ha-probe-multiplier {
                 type int32;
                 description
                   "HA probe multiplier";
               }
               leaf ha-probe-status {
                 type string;
                 description
                   "Probing status";
               }
               leaf ha-probe-result {
                 type string;
                 description
                   "Probing result";
               }
               leaf ha-srg-probe-fail-reason {
                 type string;
                 description
                   "Probing failure reason";
               }
             }
           }
           container chassis-high-availability-srg-mon-info {
             description
               "SRG global threshold info";
             leaf ha-srg-mon-status {
               type string;
               description
                 "SRG monitor status";
             }
             leaf ha-srg-mon-threshold {
               type int32;
               description
                 "SRG monitor threshold";
             }
             leaf ha-srg-mon-weight {
               type int32;
               description
                 "SRG monitor weight";
             }
             leaf ha-srg-mon-failed-objects {
               type int32;
               description
                 "SRG monitor failed objects";
             }
           }
           container chassis-high-availability-srg-obj-info {
             description
               "SRG monitor-object info";
             leaf ha-srg-obj-name {
               type string;
               description
                 "SRG monitor object name";
             }
             leaf ha-srg-obj-status {
               type string;
               description
                 "SRG monitor object status";
             }
             leaf ha-srg-obj-entries {
               type string;
               description
                 "SRG monitor object monitored entries";
             }
             leaf ha-srg-obj-failure {
               type string;
               description
                 "SRG monitor object monitored failures";
             }
             leaf ha-srg-obj-threshold {
               type int32;
               description
                 "SRG monitor object threshold";
             }
             leaf ha-srg-obj-weight {
               type int32;
               description
                 "SRG monitor object current weight";
             }
           }
           container chassis-high-availability-srg-bfdmon {
             description
               " SRG BFD mon information ";
             leaf ha-srg-bfdmon-status {
               type string;
               description
                 "HA overall bfd-monitoring status";
             }
             container chassis-high-availability-srg-bfdmon-list {
               description
                 " Display each BFD mon entry Information";
               leaf ha-srg-bfdmon-src-ipaddr {
                 type string;
                 description
                   "Source IP address configured for HA bfd-monitoring";
               }
               leaf ha-srg-bfdmon-dst-ipaddr {
                 type string;
                 description
                   "Destination IP address configured for HA bfd-monitoring";
               }
               leaf ha-srg-bfdmon-rt {
                 type string;
                 description
                   "Routing instance configured for HA bfd-monitoring";
               }
               leaf ha-srg-bfdmon-type {
                 type string;
                 description
                   "HA bfd-monitoring type";
               }
               leaf ha-srg-bfdmon-ifl-name {
                 type string;
                 description
                   "HA bfd-monitoring IFL name";
               }
               leaf ha-srg-bfdmon-state {
                 type string;
                 description
                   "HA bfd-monitoring state";
               }
             }
           }
           list high-availability-bfdmon-status-events {
             description
               "List of BFD-monitoring status events";
             leaf-list high-availability-bfdmon-status-event {
               type string;
               description
                 "Recorded BFD-monitoring status event";
             }
           }
           container chassis-high-availability-srg-ipmon {
             description
               "SRG IP monitoring Info";
             leaf ha-srg-ipmon-status {
               type string;
               description
                 "SRG overall IP-monitoring status";
             }
             container chassis-high-availability-srg-ipmon-list {
               description
                 " Display each IP monitoring entry";
               leaf ha-srg-ipmon-dst-ipaddr {
                 type string;
                 description
                   "Destination IP address configured for HA ip-monitoring";
               }
               leaf ha-srg-ipmon-rt {
                 type string;
                 description
                   "Routing instance configured for HA ip-monitoring";
               }
               leaf ha-ipmon-status {
                 type string;
                 description
                   "HA ip-monitoring status";
               }
               leaf ha-srg-ipmon-reason {
                 type string;
                 description
                   "HA ip-monitoring failure reason";
               }
             }
           }
           container chassis-high-availability-srg-obj-ipmon {
             description
               "SRG monitor object IP monitoring Info";
             leaf ha-srg-obj-ipmon-threshold {
               type int32;
               description
                 "SRG monitor object IP-monitoring threshold";
             }
             leaf ha-srg-obj-ipmon-weight {
               type int32;
               description
                 "SRG monitor object IP-monitoring weight";
             }
             leaf ha-srg-obj-ipmon-status {
               type string;
               description
                 "SRG monitor object IP-monitoring global status";
             }
             container chassis-high-availability-srg-obj-ipmon-list {
               description
                 " Display each monitor object IP monitoring entry status";
               leaf ha-srg-obj-ipmon-entry-status {
                 type string;
                 description
                   "HA SRG monitor object ip-monitoring state";
               }
               leaf ha-srg-obj-ipmon-entry-weight {
                 type int32;
                 description
                   "HA SRG monitor object ip-monitoring weight";
               }
               leaf ha-srg-obj-ipmon-entry-dst-ipaddr {
                 type string;
                 description
                   "Destination IP address configured for HA ip-monitoring";
               }
             }
           }
           container chassis-high-availability-srg-obj-ipmon-detail {
             description
               "SRG monitor object IP monitoring detail Info";
             container chassis-high-availability-srg-ipmon-list {
               description
                 " Display each IP monitoring entry";
               leaf ha-srg-ipmon-dst-ipaddr {
                 type string;
                 description
                   "Destination IP address configured for HA ip-monitoring";
               }
               leaf ha-srg-ipmon-rt {
                 type string;
                 description
                   "Routing instance configured for HA ip-monitoring";
               }
               leaf ha-ipmon-status {
                 type string;
                 description
                   "HA ip-monitoring status";
               }
               leaf ha-srg-ipmon-reason {
                 type string;
                 description
                   "HA ip-monitoring failure reason";
               }
             }
           }
           list high-availability-ipmon-status-events {
             description
               "List of ip-monitoring status events";
             leaf-list high-availability-ipmon-status-event {
               type string;
               description
                 "Recorded ip-monitoring status event";
             }
           }
           list high-availability-probe-status-events {
             description
               "List of activeness probe status events";
             leaf-list high-availability-probe-status-event {
               type string;
               description
                 "Recorded activeness probe status event";
             }
           }
           container chassis-high-availability-srg-ifmon {
             description
               "SRG Interface monitoring Info";
             leaf ha-srg-ifmon-status {
               type string;
               description
                 "HA overall Interface-monitoring status";
             }
             container chassis-high-availability-srg-ifmon-list {
               description
                 " Display each Interface monitoring entry";
               leaf ha-srg-ifmon-if-name {
                 type string;
                 description
                   "HA Interface-monitoring IF name";
               }
               leaf ha-srg-ifmon-state {
                 type string;
                 description
                   "HA Interface-monitoring state";
               }
             }
           }
         }
         list srg-info-detail {
           leaf srg-id {
             type int32;
             description
               "Current services redundancy group identifier";
           }
           leaf deployment-type {
             type string;
             description
               "Deployment Type";
           }
           leaf node-role {
             type string;
             description
               "Local node role";
           }
           leaf activeness-priority {
             type int32;
             description
               "SRG activeness priority";
           }
           leaf preemption {
             type string;
             description
               "Preemption enable flag Status";
           }
           leaf hold-timer {
             type int32;
             description
               "SRG hold down timer";
           }
           leaf process-pkt-in-bkp-state {
             type string;
             description
               "SRG backup state pkt processing info";
           }
           leaf service-names {
             type string;
             description
               "SRG service names";
           }
           leaf control-plane {
             type string;
             description
               "Control plane status";
           }
           leaf system-integrity-check {
             type string;
             description
               "Status of system integrity check";
           }
           leaf peer-id {
             type int32;
             description
               "Peer identifier";
           }
           leaf peer-node-role {
             type string;
             description
               "Peer node role";
           }
           leaf health-status {
             type string;
             description
               "Peer health status";
           }
           leaf failover-readiness {
             type string;
             description
               "SRG failover readiness";
           }
           leaf failure-events {
             type string;
             description
               "List of failure events";
           }
           leaf preempt {
             type string;
             description
               "Preempt configuration for the redundancy group";
           }
           container chassis-high-availability-srg-info-list {
             description
               "Displays each services redundancy group info";
             leaf srg-id {
               type int32;
               description
                 "Current services redundancy group identifier";
             }
             leaf deployment-type {
               type string;
               description
                 "Deployment Type";
             }
             leaf node-role {
               type string;
               description
                 "Local node role";
             }
             leaf activeness-priority {
               type int32;
               description
                 "SRG activeness priority";
             }
             leaf preemption {
               type string;
               description
                 "Preemption enable flag Status";
             }
             leaf hold-timer {
               type int32;
               description
                 "SRG hold down timer";
             }
             leaf process-pkt-in-bkp-state {
               type string;
               description
                 "SRG backup state pkt processing info";
             }
             leaf service-names {
               type string;
               description
                 "SRG service names";
             }
             leaf control-plane {
               type string;
               description
                 "Control plane status";
             }
             leaf system-integrity-check {
               type string;
               description
                 "Status of system integrity check";
             }
             leaf peer-id {
               type int32;
               description
                 "Peer identifier";
             }
             leaf peer-node-role {
               type string;
               description
                 "Peer node role";
             }
             leaf health-status {
               type string;
               description
                 "Peer health status";
             }
             leaf failover-readiness {
               type string;
               description
                 "SRG failover readiness";
             }
             leaf failure-events {
               type string;
               description
                 "List of failure events";
             }
             leaf preempt {
               type string;
               description
                 "Preempt configuration for the redundancy group";
             }
           }
           container high-availability-srg-signal-rt-info {
             description
               "  SRG Signal route Info";
             list ha-srg-signal-rt-list {
               description
                 "Display each signal route information";
               leaf ha-srg-signal-rt-type {
                 type string;
                 description
                   "  SRG  Signal route type";
               }
               leaf ha-srg-signal-rt-ipaddr {
                 type string;
                 description
                   "IP address configured as SRG active signal route";
               }
               leaf ha-srg-signal-rt-rt {
                 type string;
                 description
                   "Routing table configured for active signal route";
               }
               leaf ha-srg-signal-rt-status {
                 type string;
                 description
                   " SRG signal Route installation status";
               }
             }
           }
           container high-availability-srg-vip-info {
             description
               "  SRG Virtual IP Info";
             list ha-srg-vip-list {
               key "ha-srg-vip-index";
               description
                 "Display each Virtual IP information";
               leaf ha-srg-vip-index {
                 type string;
                 description
                   "  SRG  Signal Virtual IP Index";
               }
               leaf ha-srg-virtual-ipaddr {
                 type string;
                 description
                   "IP address configured as SRG virtual IP";
               }
               leaf ha-srg-virtual-ipaddr2 {
                 type string;
                 description
                   "IP address configured as SRG virtual IP";
               }
               leaf ha-srg-virtual-mac-address {
                 type string;
                 description
                   "MAC address for the virtual IP.";
               }
               leaf ha-srg-vip-if-name {
                 type string;
                 description
                   "Interface for the virtual IP assignment";
               }
               leaf ha-srg-vip-status {
                 type string;
                 description
                   " SRG Virtual IP assignmentstatus";
               }
             }
           }
           list high-availability-srg-state-events {
             description
               "List of service redundancy group state change events";
             leaf-list high-availability-srg-state-event {
               type string;
               description
                 "Recorded service redundancy group state change event";
             }
           }
           list high-availability-peer-status-events {
             description
               "List of HA Peer Conn events";
             leaf-list high-availability-peer-status-event {
               type string;
               description
                 "Recorded HA Peer Conn event";
             }
           }
           list high-availability-hw-upgrade-events {
             description
               "List of HA hardware upgrade events";
             leaf-list high-availability-hw-upgrade-event {
               type string;
               description
                 "Recorded HA hardware upgrade event";
             }
           }
           container chassis-high-availability-srg-probe {
             description
               "SRG split brain prevention probe info";
             list chassis-high-availability-srg-probe-list {
               key "ha-srg-probe-dst-ipaddr";
               description
                 "Display each probe information";
               leaf ha-srg-probe-dst-ipaddr {
                 type string;
                 description
                   "Destination IP address used for probing";
               }
               leaf ha-srg-probe-src-ipaddr {
                 type string;
                 description
                   "Source IP address used for probing";
               }
               leaf ha-srg-vip-if-name {
                 type string;
                 description
                   "Interface for the virtual IP assignment";
               }
               leaf ha-srg-probe-rt {
                 type string;
                 description
                   "Routing instance used for probing";
               }
               leaf ha-srg-probe-type {
                 type string;
                 description
                   "Probing type";
               }
               leaf ha-probe-interval {
                 type int32;
                 description
                   "HA probe interval in ms";
               }
               leaf ha-probe-multiplier {
                 type int32;
                 description
                   "HA probe multiplier";
               }
               leaf ha-probe-status {
                 type string;
                 description
                   "Probing status";
               }
               leaf ha-probe-result {
                 type string;
                 description
                   "Probing result";
               }
               leaf ha-srg-probe-fail-reason {
                 type string;
                 description
                   "Probing failure reason";
               }
             }
           }
           container chassis-high-availability-srg-mon-info {
             description
               "SRG global threshold info";
             leaf ha-srg-mon-status {
               type string;
               description
                 "SRG monitor status";
             }
             leaf ha-srg-mon-threshold {
               type int32;
               description
                 "SRG monitor threshold";
             }
             leaf ha-srg-mon-weight {
               type int32;
               description
                 "SRG monitor weight";
             }
             leaf ha-srg-mon-failed-objects {
               type int32;
               description
                 "SRG monitor failed objects";
             }
           }
           container chassis-high-availability-srg-obj-info {
             description
               "SRG monitor-object info";
             leaf ha-srg-obj-name {
               type string;
               description
                 "SRG monitor object name";
             }
             leaf ha-srg-obj-status {
               type string;
               description
                 "SRG monitor object status";
             }
             leaf ha-srg-obj-entries {
               type string;
               description
                 "SRG monitor object monitored entries";
             }
             leaf ha-srg-obj-failure {
               type string;
               description
                 "SRG monitor object monitored failures";
             }
             leaf ha-srg-obj-threshold {
               type int32;
               description
                 "SRG monitor object threshold";
             }
             leaf ha-srg-obj-weight {
               type int32;
               description
                 "SRG monitor object current weight";
             }
           }
           container chassis-high-availability-srg-bfdmon {
             description
               " SRG BFD mon information ";
             leaf ha-srg-bfdmon-status {
               type string;
               description
                 "HA overall bfd-monitoring status";
             }
             container chassis-high-availability-srg-bfdmon-list {
               description
                 " Display each BFD mon entry Information";
               leaf ha-srg-bfdmon-src-ipaddr {
                 type string;
                 description
                   "Source IP address configured for HA bfd-monitoring";
               }
               leaf ha-srg-bfdmon-dst-ipaddr {
                 type string;
                 description
                   "Destination IP address configured for HA bfd-monitoring";
               }
               leaf ha-srg-bfdmon-rt {
                 type string;
                 description
                   "Routing instance configured for HA bfd-monitoring";
               }
               leaf ha-srg-bfdmon-type {
                 type string;
                 description
                   "HA bfd-monitoring type";
               }
               leaf ha-srg-bfdmon-ifl-name {
                 type string;
                 description
                   "HA bfd-monitoring IFL name";
               }
               leaf ha-srg-bfdmon-state {
                 type string;
                 description
                   "HA bfd-monitoring state";
               }
             }
           }
           list high-availability-bfdmon-status-events {
             description
               "List of BFD-monitoring status events";
             leaf-list high-availability-bfdmon-status-event {
               type string;
               description
                 "Recorded BFD-monitoring status event";
             }
           }
           container chassis-high-availability-srg-ipmon {
             description
               "SRG IP monitoring Info";
             leaf ha-srg-ipmon-status {
               type string;
               description
                 "SRG overall IP-monitoring status";
             }
             container chassis-high-availability-srg-ipmon-list {
               description
                 " Display each IP monitoring entry";
               leaf ha-srg-ipmon-dst-ipaddr {
                 type string;
                 description
                   "Destination IP address configured for HA ip-monitoring";
               }
               leaf ha-srg-ipmon-rt {
                 type string;
                 description
                   "Routing instance configured for HA ip-monitoring";
               }
               leaf ha-ipmon-status {
                 type string;
                 description
                   "HA ip-monitoring status";
               }
               leaf ha-srg-ipmon-reason {
                 type string;
                 description
                   "HA ip-monitoring failure reason";
               }
             }
           }
           container chassis-high-availability-srg-obj-ipmon {
             description
               "SRG monitor object IP monitoring Info";
             leaf ha-srg-obj-ipmon-threshold {
               type int32;
               description
                 "SRG monitor object IP-monitoring threshold";
             }
             leaf ha-srg-obj-ipmon-weight {
               type int32;
               description
                 "SRG monitor object IP-monitoring weight";
             }
             leaf ha-srg-obj-ipmon-status {
               type string;
               description
                 "SRG monitor object IP-monitoring global status";
             }
             container chassis-high-availability-srg-obj-ipmon-list {
               description
                 " Display each monitor object IP monitoring entry status";
               leaf ha-srg-obj-ipmon-entry-status {
                 type string;
                 description
                   "HA SRG monitor object ip-monitoring state";
               }
               leaf ha-srg-obj-ipmon-entry-weight {
                 type int32;
                 description
                   "HA SRG monitor object ip-monitoring weight";
               }
               leaf ha-srg-obj-ipmon-entry-dst-ipaddr {
                 type string;
                 description
                   "Destination IP address configured for HA ip-monitoring";
               }
             }
           }
           container chassis-high-availability-srg-obj-ipmon-detail {
             description
               "SRG monitor object IP monitoring detail Info";
             container chassis-high-availability-srg-ipmon-list {
               description
                 " Display each IP monitoring entry";
               leaf ha-srg-ipmon-dst-ipaddr {
                 type string;
                 description
                   "Destination IP address configured for HA ip-monitoring";
               }
               leaf ha-srg-ipmon-rt {
                 type string;
                 description
                   "Routing instance configured for HA ip-monitoring";
               }
               leaf ha-ipmon-status {
                 type string;
                 description
                   "HA ip-monitoring status";
               }
               leaf ha-srg-ipmon-reason {
                 type string;
                 description
                   "HA ip-monitoring failure reason";
               }
             }
           }
           list high-availability-ipmon-status-events {
             description
               "List of ip-monitoring status events";
             leaf-list high-availability-ipmon-status-event {
               type string;
               description
                 "Recorded ip-monitoring status event";
             }
           }
           list high-availability-probe-status-events {
             description
               "List of activeness probe status events";
             leaf-list high-availability-probe-status-event {
               type string;
               description
                 "Recorded activeness probe status event";
             }
           }
           container chassis-high-availability-srg-ifmon {
             description
               "SRG Interface monitoring Info";
             leaf ha-srg-ifmon-status {
               type string;
               description
                 "HA overall Interface-monitoring status";
             }
             container chassis-high-availability-srg-ifmon-list {
               description
                 " Display each Interface monitoring entry";
               leaf ha-srg-ifmon-if-name {
                 type string;
                 description
                   "HA Interface-monitoring IF name";
               }
               leaf ha-srg-ifmon-state {
                 type string;
                 description
                   "HA Interface-monitoring state";
               }
             }
           }
         }
       }
     }
     container chassis-high-availability-node-info {
       description
         "Display high-availability node level information";
       leaf node-status {
         type string;
         description
           "Status of the current node";
       }
       leaf local-id {
         type int32;
         description
           "Local node identifier";
       }
       leaf local-ip {
         type jt:ipaddr;
         description
           "Local node IPv4 address";
       }
       leaf local-fwd-ip {
         type jt:ipaddr;
         description
           "Local Forwarding IP address";
       }
       leaf grid-id {
         type int32;
         description
           "Grid identifier";
       }
       list chassis-high-availability-shutdown-interface {
         description
           "Display high-availability shutdown interface list";
         leaf high-availability-shutdown-interface-name {
           type string;
           description
             "Interface name for monitoring";
         }
       }
       container chassis-high-availability-peer-info-detail {
         description
           "Displays high-availability peer related detail info";
         leaf high-availability-peer-desc {
           type string;
           description
             "Peer description";
         }
         leaf high-availability-peer-id {
           type int32;
           description
             "Peer identifier that is configured";
         }
         leaf high-availability-peer-ip-address {
           type jt:ipaddr;
           description
             "Peer remote IPv4 address that is configured";
         }
         leaf-list high-availability-local-interface {
           type string;
           description
             "Local interface";
         }
         leaf high-availability-peer-rt-instance {
           type string;
           description
             "Routing Instance name for HA peer";
         }
         leaf high-availability-peer-encryption-status {
           type string;
           description
             "Encryption status of the current node";
         }
         leaf high-availability-peer-bfd-status {
           type string;
           description
             "BFD Status of the current node";
         }
         leaf cold-sync-status {
           type string;
           description
             "Cold synchronization status";
         }
         leaf peer-hw-incompatible {
           type string;
           description
             "Peer hardware compatible status";
         }
         leaf peer-internal-interface {
           type string;
           description
             "Peer internal interface";
         }
         leaf peer-internal-local-ip {
           type jt:ipaddr;
           description
             "Internal local IPv4 address";
         }
         leaf peer-internal-peer-ip {
           type jt:ipaddr;
           description
             "Internal peer IPv4 address";
         }
         leaf peer-internal-routing-instance {
           type string;
           description
             "Peer internal routing instance";
         }
         leaf high-availability-peer-fwd-ip-address {
           type jt:ipaddr;
           description
             "Peer forwarding remote IP address";
         }
         leaf high-availability-local-fwd-interface {
           type string;
           description
             "Local forwarding interface";
         }
         leaf high-availability-peer-fwd-bfd-status {
           type string;
           description
             "BFD forwarding status of the current node";
         }
         leaf peer-domain-id {
           type int32;
           description
             "Peer-domain-id";
         }
         leaf high-availability-peer-detect-time {
           type string;
           description
             "Configured Peer BFD detection time";
         }
         container chassis-mnha-icl-peer-info {
           description
             "Displays mnha icl peer related info";
           leaf high-availability-peer-desc {
             type string;
             description
               "Peer description";
           }
           leaf peer-domain-id {
             type int32;
             description
               "Peer-domain-id";
           }
           leaf high-availability-peer-id {
             type int32;
             description
               "Peer identifier that is configured";
           }
           leaf high-availability-peer-ip-address {
             type jt:ipaddr;
             description
               "Peer remote IPv4 address that is configured";
           }
           leaf-list high-availability-local-interface {
             type string;
             description
               "Local interface";
           }
           leaf high-availability-peer-rt-instance {
             type string;
             description
               "Routing Instance name for HA peer";
           }
           leaf high-availability-peer-encryption-status {
             type string;
             description
               "Encryption status of the current node";
           }
           leaf high-availability-peer-bfd-status {
             type string;
             description
               "BFD Status of the current node";
           }
           leaf cold-sync-status {
             type string;
             description
               "Cold synchronization status";
           }
           leaf peer-hw-incompatible {
             type string;
             description
               "Peer hardware compatible status";
           }
           leaf peer-internal-interface {
             type string;
             description
               "Peer internal interface";
           }
           leaf peer-internal-local-ip {
             type jt:ipaddr;
             description
               "Internal local IPv4 address";
           }
           leaf peer-internal-peer-ip {
             type jt:ipaddr;
             description
               "Internal peer IPv4 address";
           }
           leaf peer-internal-routing-instance {
             type string;
             description
               "Peer internal routing instance";
           }
           leaf high-availability-peer-detect-time {
             type string;
             description
               "Configured Peer BFD detection time";
           }
           leaf srg0-cold-sync-status {
             type string;
             description
               "SRG0 cold sync status";
           }
           container chassis-mnha-local-node-idl-info {
             description
               "Displays high-availability local node IDL BFD and CS state";
             leaf states-from-domain-id {
               type int32;
               description
                 "States from domain id";
             }
             leaf states-from-node-id {
               type int32;
               description
                 "States from node id";
             }
             leaf domain-id {
               type int32;
               description
                 "Domain-id";
             }
             leaf peer-id {
               type int32;
               description
                 "Peer identifier";
             }
             leaf conn-state {
               type string;
               description
                 "Conn state";
             }
             leaf rtt-result {
               type string;
               description
                 "RTT result";
             }
             leaf cold-sync-status {
               type string;
               description
                 "Cold synchronization status";
             }
             leaf srg0-idl-status {
               type string;
               description
                 "SRG0 idl status";
             }
           }
           container chassis-mnha-peer-node-icl-info {
             description
               "Displays high-availability icl info";
             leaf states-from-domain-id {
               type int32;
               description
                 "States from domain id";
             }
             leaf states-from-node-id {
               type int32;
               description
                 "States from node id";
             }
             leaf icl-conn-state {
               type string;
               description
                 "ICL Conn state";
             }
             leaf cold-sync-status {
               type string;
               description
                 "Cold synchronization status";
             }
           }
           container chassis-mnha-peer-node-idl-info {
             description
               "Displays high-availability peer node IDL BFD and CS state";
             leaf states-from-domain-id {
               type int32;
               description
                 "States from domain id";
             }
             leaf states-from-node-id {
               type int32;
               description
                 "States from node id";
             }
             leaf domain-id {
               type int32;
               description
                 "Domain-id";
             }
             leaf peer-id {
               type int32;
               description
                 "Peer identifier";
             }
             leaf conn-state {
               type string;
               description
                 "Conn state";
             }
             leaf rtt-result {
               type string;
               description
                 "RTT result";
             }
             leaf cold-sync-status {
               type string;
               description
                 "Cold synchronization status";
             }
             leaf srg0-idl-status {
               type string;
               description
                 "SRG0 idl status";
             }
           }
           list high-availability-peer-packet-stats {
             description
               "Peer Packet Stats";
             leaf packet-send-err-cnt {
               type int32;
               description
                 "Peer packet send error cnt";
             }
             leaf packet-recv-err-cnt {
               type int32;
               description
                 "Peer packet recv error cnt";
             }
             list peer-packet-send-rcv-stats {
               description
                 "Peer Packet Send receive Stats";
               list peer-packet-stats-list {
                 description
                   "Stats for each peer packet type";
                 leaf peer-packet-type {
                   type string;
                   description
                     "Peer packet Type";
                 }
                 leaf peer-packet-send-cnt {
                   type int32;
                   description
                     "Peer packet sent count";
                 }
                 leaf peer-packet-rcv-cnt {
                   type int32;
                   description
                     "Peer packet rcv cnt";
                 }
               }
             }
           }
         }
         list chassis-mnha-idl-peer-info {
           description
             "Displays mnha idl peer related info";
           leaf high-availability-peer-desc {
             type string;
             description
               "Peer description";
           }
           leaf peer-domain-id {
             type int32;
             description
               "Peer-domain-id";
           }
           leaf high-availability-peer-id {
             type int32;
             description
               "Peer identifier that is configured";
           }
           leaf high-availability-peer-ip-address {
             type jt:ipaddr;
             description
               "Peer remote IPv4 address that is configured";
           }
           leaf-list high-availability-local-interface {
             type string;
             description
               "Local interface";
           }
           leaf high-availability-peer-rt-instance {
             type string;
             description
               "Routing Instance name for HA peer";
           }
           leaf high-availability-peer-encryption-status {
             type string;
             description
               "Encryption status of the current node";
           }
           leaf high-availability-peer-idl-bfd-status {
             type string;
             description
               "IDL BFD Status of the current node";
           }
           leaf cold-sync-status {
             type string;
             description
               "Cold synchronization status";
           }
           leaf peer-hw-incompatible {
             type string;
             description
               "Peer hardware compatible status";
           }
           leaf peer-internal-interface {
             type string;
             description
               "Peer internal interface";
           }
           leaf peer-internal-local-ip {
             type jt:ipaddr;
             description
               "Internal local IPv4 address";
           }
           leaf peer-internal-peer-ip {
             type jt:ipaddr;
             description
               "Internal peer IPv4 address";
           }
           leaf peer-internal-routing-instance {
             type string;
             description
               "Peer internal routing instance";
           }
           leaf high-availability-peer-detect-time {
             type string;
             description
               "Configured Peer BFD detection time";
           }
           container chassis-mnha-peer-node-icl-info {
             description
               "Displays high-availability icl info";
             leaf states-from-domain-id {
               type int32;
               description
                 "States from domain id";
             }
             leaf states-from-node-id {
               type int32;
               description
                 "States from node id";
             }
             leaf icl-conn-state {
               type string;
               description
                 "ICL Conn state";
             }
             leaf cold-sync-status {
               type string;
               description
                 "Cold synchronization status";
             }
           }
           container chassis-mnha-peer-domain-idl-info {
             description
               "Displays high-availability peer domain IDL BFD and CS state";
             leaf states-from-domain-id {
               type int32;
               description
                 "States from domain id";
             }
             leaf states-from-node-id {
               type int32;
               description
                 "States from node id";
             }
             leaf domain-id {
               type int32;
               description
                 "Domain-id";
             }
             leaf peer-id {
               type int32;
               description
                 "Peer identifier";
             }
             leaf conn-state {
               type string;
               description
                 "Conn state";
             }
             leaf rtt-result {
               type string;
               description
                 "RTT result";
             }
             leaf cold-sync-status {
               type string;
               description
                 "Cold synchronization status";
             }
             leaf srg0-idl-status {
               type string;
               description
                 "SRG0 idl status";
             }
           }
           list high-availability-peer-packet-stats {
             description
               "Peer Packet Stats";
             leaf packet-send-err-cnt {
               type int32;
               description
                 "Peer packet send error cnt";
             }
             leaf packet-recv-err-cnt {
               type int32;
               description
                 "Peer packet recv error cnt";
             }
             list peer-packet-send-rcv-stats {
               description
                 "Peer Packet Send receive Stats";
               list peer-packet-stats-list {
                 description
                   "Stats for each peer packet type";
                 leaf peer-packet-type {
                   type string;
                   description
                     "Peer packet Type";
                 }
                 leaf peer-packet-send-cnt {
                   type int32;
                   description
                     "Peer packet sent count";
                 }
                 leaf peer-packet-rcv-cnt {
                   type int32;
                   description
                     "Peer packet rcv cnt";
                 }
               }
             }
           }
         }
         list high-availability-peer-packet-stats {
           description
             "Peer Packet Stats";
           leaf packet-send-err-cnt {
             type int32;
             description
               "Peer packet send error cnt";
           }
           leaf packet-recv-err-cnt {
             type int32;
             description
               "Peer packet recv error cnt";
           }
           list peer-packet-send-rcv-stats {
             description
               "Peer Packet Send receive Stats";
             list peer-packet-stats-list {
               description
                 "Stats for each peer packet type";
               leaf peer-packet-type {
                 type string;
                 description
                   "Peer packet Type";
               }
               leaf peer-packet-send-cnt {
                 type int32;
                 description
                   "Peer packet sent count";
               }
               leaf peer-packet-rcv-cnt {
                 type int32;
                 description
                   "Peer packet rcv cnt";
               }
             }
           }
         }
       }
     }
     container cold-synchronization-monitoring-information {
       description
         "Cold sync monitoring related information";
       leaf-list cold-synchronization-progress {
         type string;
         description
           "Cold synchronization progress";
       }
       container cold-synchronization-status-information {
         description
           "Cold synchronization related status information";
         leaf cold-synchronization-completed {
           type string;
           description
             "List of PFE's which have completed cold synchnronization";
         }
         leaf cold-synchronization-not-completed {
           type string;
           description
             "List of PFE's which have failed cold synchnronization";
         }
         leaf cold-synchronization-unknown {
           type string;
           description
             "List of PFE's for which cold synchnronization statusupdate is 
             not received";
         }
         leaf cold-synchronization-weight {
           type uint32;
           description
             "Current Cold Synchronization weight";
         }
       }
       container cold-synchronization-statistics {
         description
           "Cold synchronization statistics";
         leaf current-cold-synchronization-completed {
           type uint32;
           description
             "Cold synchronization completed for current jsrpd session";
         }
         leaf current-cold-synchronization-failed {
           type uint32;
           description
             "Cold synchronization failed for current jsrpd session";
         }
         list cold-synchronization-pfe-statistics {
           description
             "Cold synchroniizaton statistics for each PFE";
           leaf pfe-name {
             type string;
             description
               "Name of the PFE";
           }
           leaf cold-synchronization-pfe-completed {
             type uint32;
             description
               "Cold synchronization complete instances for a given PFE";
           }
           leaf cold-synchronization-pfe-failed {
             type uint32;
             description
               "Cold synchronization complete instances for a given PFE";
           }
         }
       }
       container cold-synchronization-events {
         description
           "List of cold synchronization events";
         leaf-list cold-synchronization-event {
           type string;
           description
             "Recorded cold sync complete/failure for a PFE";
         }
       }
     }
     container spu-monitoring-information {
       description
         "SPU monitoring related information";
       container spu-monitoring-status {
         description
           "SPU monitoring related status information";
         leaf spu-monitoring-state {
           type string;
           description
             "SPU current monitoring mode Disabled/Enabled/Active";
         }
         leaf spu-monitoring-weight {
           type uint32;
           description
             "Current SPU monitoring weight";
         }
         list spu-monitoring-spu-state {
           description
             "Each SPU current state";
           container spu-monitoring-spu-state-list {
             description
               "Each SPU current state in list";
             leaf pfe-name {
               type string;
               description
                 "Name of the PFE";
             }
             leaf pic-state {
               type string;
               description
                 "State of each PIC";
             }
           }
         }
       }
       container spu-monitoring-statistics {
         description
           "Detailed statistics of SPU monitoring";
         leaf spu-up-count {
           type uint32;
           description
             "Number of SPUs that are up";
         }
         leaf spu-down-count {
           type uint32;
           description
             "Number of SPUs that are down";
         }
         leaf npc-up-count {
           type uint32;
           description
             "Number of NPCs that are up";
         }
         leaf npc-down-count {
           type uint32;
           description
             "Number of NPCs that are down";
         }
         leaf chinfo-blob-error-count {
           type uint32;
           description
             "Error count reading chinfo blob";
         }
       }
       container spu-monitoring-events {
         description
           "List of SPU monitoring events";
         leaf-list spu-monitoring-event {
           type string;
           description
             "Recorded SPU monitoring events";
         }
       }
     }
     list loopback-information {
       description
         "Loopback information";
       container loopback-information-list {
         description
           "Display loopback information list";
         leaf pfe-name {
           type string;
           description
             "Name of the PFE";
         }
         leaf loopback-status {
           type string;
           description
             "Loopback status of each PIC";
         }
         leaf nexthop-status {
           type string;
           description
             "Nexthop status of each PIC";
         }
         leaf mbuf-status {
           type string;
           description
             "Mbuf status of each PIC";
         }
       }
     }
     container high-availability-hardware-monitoring-information {
       description
         "Displays complete high-availability hardware monitoring 
         information for debugging purposes";
       container hardware-monitoring-events {
         description
           "List of hardware monitoring events";
         leaf-list hardware-monitoring-event {
           type string;
           description
             "Recorded hardware monitoring events";
         }
       }
       container high-availability-hardware-monitoring-status-information {
         leaf high-availability-hardware-monitoring-activation-status {
           type string;
           description
             "Hardware monitoring is enabled/disabled";
         }
         leaf high-availability-hardware-monitoring-ctrl-plane-errors {
           type int32;
           description
             "Hardware monitoring Ctrl plane errors";
         }
         leaf high-availability-hardware-monitoring-data-plane-errors {
           type int32;
           description
             "Hardware monitoring Data plane errors";
         }
       }
     }
     container chassis-high-availability-default-srg-info {
       description
         "Displays high-availability services redundancy group 0 info";
       leaf current-state {
         type string;
         description
           "SRG 0 current state";
       }
       leaf peer-id {
         type int32;
         description
           "Peer identifier";
       }
       leaf node-priority {
         type int32;
         description
           "Node-priority";
       }
       leaf peer-domain-id {
         type int32;
         description
           "Peer-domain-id";
       }
       list srg-peer-domain-peer-id-info {
         description
           "Idl peer node Id";
         leaf idl-peer-id {
           type int32;
           description
             "IDL Peer identifier";
         }
       }
       container high-availability-srg-signal-rt-info {
         description
           "  SRG Signal route Info";
         list ha-srg-signal-rt-list {
           description
             "Display each signal route information";
           leaf ha-srg-signal-rt-type {
             type string;
             description
               "  SRG  Signal route type";
           }
           leaf ha-srg-signal-rt-ipaddr {
             type string;
             description
               "IP address configured as SRG active signal route";
           }
           leaf ha-srg-signal-rt-rt {
             type string;
             description
               "Routing table configured for active signal route";
           }
           leaf ha-srg-signal-rt-status {
             type string;
             description
               " SRG signal Route installation status";
           }
         }
       }
       list chassis-high-availability-shutdown-interface {
         description
           "Display high-availability shutdown interface list";
         leaf high-availability-shutdown-interface-name {
           type string;
           description
             "Interface name for monitoring";
         }
       }
       container chassis-high-availability-srg-ipmon {
         description
           "SRG IP monitoring Info";
         leaf ha-srg-ipmon-status {
           type string;
           description
             "SRG overall IP-monitoring status";
         }
         container chassis-high-availability-srg-ipmon-list {
           description
             " Display each IP monitoring entry";
           leaf ha-srg-ipmon-dst-ipaddr {
             type string;
             description
               "Destination IP address configured for HA ip-monitoring";
           }
           leaf ha-srg-ipmon-rt {
             type string;
             description
               "Routing instance configured for HA ip-monitoring";
           }
           leaf ha-ipmon-status {
             type string;
             description
               "HA ip-monitoring status";
           }
           leaf ha-srg-ipmon-reason {
             type string;
             description
               "HA ip-monitoring failure reason";
           }
         }
       }
       container chassis-high-availability-srg-bfdmon {
         description
           " SRG BFD mon information ";
         leaf ha-srg-bfdmon-status {
           type string;
           description
             "HA overall bfd-monitoring status";
         }
         container chassis-high-availability-srg-bfdmon-list {
           description
             " Display each BFD mon entry Information";
           leaf ha-srg-bfdmon-src-ipaddr {
             type string;
             description
               "Source IP address configured for HA bfd-monitoring";
           }
           leaf ha-srg-bfdmon-dst-ipaddr {
             type string;
             description
               "Destination IP address configured for HA bfd-monitoring";
           }
           leaf ha-srg-bfdmon-rt {
             type string;
             description
               "Routing instance configured for HA bfd-monitoring";
           }
           leaf ha-srg-bfdmon-type {
             type string;
             description
               "HA bfd-monitoring type";
           }
           leaf ha-srg-bfdmon-ifl-name {
             type string;
             description
               "HA bfd-monitoring IFL name";
           }
           leaf ha-srg-bfdmon-state {
             type string;
             description
               "HA bfd-monitoring state";
           }
         }
       }
       container chassis-high-availability-srg-ifmon {
         description
           "SRG Interface monitoring Info";
         leaf ha-srg-ifmon-status {
           type string;
           description
             "HA overall Interface-monitoring status";
         }
         container chassis-high-availability-srg-ifmon-list {
           description
             " Display each Interface monitoring entry";
           leaf ha-srg-ifmon-if-name {
             type string;
             description
               "HA Interface-monitoring IF name";
           }
           leaf ha-srg-ifmon-state {
             type string;
             description
               "HA Interface-monitoring state";
           }
         }
       }
       container chassis-high-availability-srg-mon-info {
         description
           "SRG global threshold info";
         leaf ha-srg-mon-status {
           type string;
           description
             "SRG monitor status";
         }
         leaf ha-srg-mon-threshold {
           type int32;
           description
             "SRG monitor threshold";
         }
         leaf ha-srg-mon-weight {
           type int32;
           description
             "SRG monitor weight";
         }
         leaf ha-srg-mon-failed-objects {
           type int32;
           description
             "SRG monitor failed objects";
         }
       }
       container chassis-high-availability-srg-obj-info {
         description
           "SRG monitor-object info";
         leaf ha-srg-obj-name {
           type string;
           description
             "SRG monitor object name";
         }
         leaf ha-srg-obj-status {
           type string;
           description
             "SRG monitor object status";
         }
         leaf ha-srg-obj-entries {
           type string;
           description
             "SRG monitor object monitored entries";
         }
         leaf ha-srg-obj-failure {
           type string;
           description
             "SRG monitor object monitored failures";
         }
         leaf ha-srg-obj-threshold {
           type int32;
           description
             "SRG monitor object threshold";
         }
         leaf ha-srg-obj-weight {
           type int32;
           description
             "SRG monitor object current weight";
         }
       }
       container chassis-high-availability-srg-obj-ipmon {
         description
           "SRG monitor object IP monitoring Info";
         leaf ha-srg-obj-ipmon-threshold {
           type int32;
           description
             "SRG monitor object IP-monitoring threshold";
         }
         leaf ha-srg-obj-ipmon-weight {
           type int32;
           description
             "SRG monitor object IP-monitoring weight";
         }
         leaf ha-srg-obj-ipmon-status {
           type string;
           description
             "SRG monitor object IP-monitoring global status";
         }
         container chassis-high-availability-srg-obj-ipmon-list {
           description
             " Display each monitor object IP monitoring entry status";
           leaf ha-srg-obj-ipmon-entry-status {
             type string;
             description
               "HA SRG monitor object ip-monitoring state";
           }
           leaf ha-srg-obj-ipmon-entry-weight {
             type int32;
             description
               "HA SRG monitor object ip-monitoring weight";
           }
           leaf ha-srg-obj-ipmon-entry-dst-ipaddr {
             type string;
             description
               "Destination IP address configured for HA ip-monitoring";
           }
         }
       }
       container chassis-high-availability-srg-obj-ipmon-detail {
         description
           "SRG monitor object IP monitoring detail Info";
         container chassis-high-availability-srg-ipmon-list {
           description
             " Display each IP monitoring entry";
           leaf ha-srg-ipmon-dst-ipaddr {
             type string;
             description
               "Destination IP address configured for HA ip-monitoring";
           }
           leaf ha-srg-ipmon-rt {
             type string;
             description
               "Routing instance configured for HA ip-monitoring";
           }
           leaf ha-ipmon-status {
             type string;
             description
               "HA ip-monitoring status";
           }
           leaf ha-srg-ipmon-reason {
             type string;
             description
               "HA ip-monitoring failure reason";
           }
         }
       }
       container chassis-high-availability-srg-obj-bfdmon {
         description
           "SRG monitor object BFD monitoring Info";
         leaf ha-srg-obj-bfdmon-threshold {
           type int32;
           description
             "SRG monitor object BFD-monitoring threshold";
         }
         leaf ha-srg-obj-bfdmon-weight {
           type int32;
           description
             "SRG monitor object BFD-monitoring weight";
         }
         leaf ha-srg-obj-bfdmon-status {
           type string;
           description
             "SRG monitor object BFD-monitoring global status";
         }
         container chassis-high-availability-srg-obj-bfdmon-list {
           description
             "Display each monitor object BFD monitoring entry status";
           leaf ha-srg-obj-bfdmon-entry-status {
             type string;
             description
               "HA SRG monitor object BFD-monitoring state";
           }
           leaf ha-srg-obj-bfdmon-entry-weight {
             type int32;
             description
               "HA SRG monitor object BFD-monitoring weight";
           }
           leaf ha-srg-obj-bfdmon-entry-dst-bfdaddr {
             type string;
             description
               "Destination BFD address configured for HA BFD-monitoring";
           }
         }
       }
       container chassis-high-availability-srg-obj-bfdmon-detail {
         description
           "SRG monitor object BFD mon information ";
         container chassis-high-availability-srg-bfdmon-list {
           description
             " Display each BFD mon entry Information";
           leaf ha-srg-bfdmon-src-ipaddr {
             type string;
             description
               "Source IP address configured for HA bfd-monitoring";
           }
           leaf ha-srg-bfdmon-dst-ipaddr {
             type string;
             description
               "Destination IP address configured for HA bfd-monitoring";
           }
           leaf ha-srg-bfdmon-rt {
             type string;
             description
               "Routing instance configured for HA bfd-monitoring";
           }
           leaf ha-srg-bfdmon-type {
             type string;
             description
               "HA bfd-monitoring type";
           }
           leaf ha-srg-bfdmon-ifl-name {
             type string;
             description
               "HA bfd-monitoring IFL name";
           }
           leaf ha-srg-bfdmon-state {
             type string;
             description
               "HA bfd-monitoring state";
           }
         }
       }
       container chassis-high-availability-srg-obj-ifmon {
         description
           "SRG monitor object IF monitoring Info";
         leaf ha-srg-obj-ifmon-threshold {
           type int32;
           description
             "SRG monitor object IF-monitoring threshold";
         }
         leaf ha-srg-obj-ifmon-weight {
           type int32;
           description
             "SRG monitor object IF-monitoring current weight";
         }
         leaf ha-srg-ifmon-status {
           type string;
           description
             "HA overall Interface-monitoring status";
         }
         container chassis-high-availability-srg-obj-ifmon-list {
           description
             "Display each monitor object IF monitoring entry status";
           leaf ha-srg-ifmon-entry-status {
             type string;
             description
               "HA SRG monitor object IF-monitoring entry status";
           }
           leaf ha-srg-obj-ifmon-entry-weight {
             type int32;
             description
               "HA SRG monitor object IF-monitoring entry weight";
           }
           leaf ha-srg-ifmon-if-name {
             type string;
             description
               "HA Interface-monitoring IF name";
           }
         }
       }
     }
     list chassis-high-availability-srg-info-detail {
       description
         "Displays high-availability services redundancy group detail info";
       container chassis-high-availability-srg-info-list {
         description
           "Displays each services redundancy group info";
         leaf srg-id {
           type int32;
           description
             "Current services redundancy group identifier";
         }
         leaf deployment-type {
           type string;
           description
             "Deployment Type";
         }
         leaf node-role {
           type string;
           description
             "Local node role";
         }
         leaf activeness-priority {
           type int32;
           description
             "SRG activeness priority";
         }
         leaf preemption {
           type string;
           description
             "Preemption enable flag Status";
         }
         leaf hold-timer {
           type int32;
           description
             "SRG hold down timer";
         }
         leaf process-pkt-in-bkp-state {
           type string;
           description
             "SRG backup state pkt processing info";
         }
         leaf service-names {
           type string;
           description
             "SRG service names";
         }
         leaf control-plane {
           type string;
           description
             "Control plane status";
         }
         leaf system-integrity-check {
           type string;
           description
             "Status of system integrity check";
         }
         leaf peer-id {
           type int32;
           description
             "Peer identifier";
         }
         leaf peer-node-role {
           type string;
           description
             "Peer node role";
         }
         leaf health-status {
           type string;
           description
             "Peer health status";
         }
         leaf failover-readiness {
           type string;
           description
             "SRG failover readiness";
         }
         leaf failure-events {
           type string;
           description
             "List of failure events";
         }
         leaf preempt {
           type string;
           description
             "Preempt configuration for the redundancy group";
         }
         container chassis-high-availability-srg-info-list {
           description
             "Displays each services redundancy group info";
           leaf srg-id {
             type int32;
             description
               "Current services redundancy group identifier";
           }
           leaf deployment-type {
             type string;
             description
               "Deployment Type";
           }
           leaf node-role {
             type string;
             description
               "Local node role";
           }
           leaf activeness-priority {
             type int32;
             description
               "SRG activeness priority";
           }
           leaf preemption {
             type string;
             description
               "Preemption enable flag Status";
           }
           leaf hold-timer {
             type int32;
             description
               "SRG hold down timer";
           }
           leaf process-pkt-in-bkp-state {
             type string;
             description
               "SRG backup state pkt processing info";
           }
           leaf service-names {
             type string;
             description
               "SRG service names";
           }
           leaf control-plane {
             type string;
             description
               "Control plane status";
           }
           leaf system-integrity-check {
             type string;
             description
               "Status of system integrity check";
           }
           leaf peer-id {
             type int32;
             description
               "Peer identifier";
           }
           leaf peer-node-role {
             type string;
             description
               "Peer node role";
           }
           leaf health-status {
             type string;
             description
               "Peer health status";
           }
           leaf failover-readiness {
             type string;
             description
               "SRG failover readiness";
           }
           leaf failure-events {
             type string;
             description
               "List of failure events";
           }
           leaf preempt {
             type string;
             description
               "Preempt configuration for the redundancy group";
           }
         }
         container high-availability-srg-signal-rt-info {
           description
             "  SRG Signal route Info";
           list ha-srg-signal-rt-list {
             description
               "Display each signal route information";
             leaf ha-srg-signal-rt-type {
               type string;
               description
                 "  SRG  Signal route type";
             }
             leaf ha-srg-signal-rt-ipaddr {
               type string;
               description
                 "IP address configured as SRG active signal route";
             }
             leaf ha-srg-signal-rt-rt {
               type string;
               description
                 "Routing table configured for active signal route";
             }
             leaf ha-srg-signal-rt-status {
               type string;
               description
                 " SRG signal Route installation status";
             }
           }
         }
         container high-availability-srg-vip-info {
           description
             "  SRG Virtual IP Info";
           list ha-srg-vip-list {
             key "ha-srg-vip-index";
             description
               "Display each Virtual IP information";
             leaf ha-srg-vip-index {
               type string;
               description
                 "  SRG  Signal Virtual IP Index";
             }
             leaf ha-srg-virtual-ipaddr {
               type string;
               description
                 "IP address configured as SRG virtual IP";
             }
             leaf ha-srg-virtual-ipaddr2 {
               type string;
               description
                 "IP address configured as SRG virtual IP";
             }
             leaf ha-srg-virtual-mac-address {
               type string;
               description
                 "MAC address for the virtual IP.";
             }
             leaf ha-srg-vip-if-name {
               type string;
               description
                 "Interface for the virtual IP assignment";
             }
             leaf ha-srg-vip-status {
               type string;
               description
                 " SRG Virtual IP assignmentstatus";
             }
           }
         }
         list high-availability-srg-state-events {
           description
             "List of service redundancy group state change events";
           leaf-list high-availability-srg-state-event {
             type string;
             description
               "Recorded service redundancy group state change event";
           }
         }
         list high-availability-peer-status-events {
           description
             "List of HA Peer Conn events";
           leaf-list high-availability-peer-status-event {
             type string;
             description
               "Recorded HA Peer Conn event";
           }
         }
         list high-availability-hw-upgrade-events {
           description
             "List of HA hardware upgrade events";
           leaf-list high-availability-hw-upgrade-event {
             type string;
             description
               "Recorded HA hardware upgrade event";
           }
         }
         container chassis-high-availability-srg-probe {
           description
             "SRG split brain prevention probe info";
           list chassis-high-availability-srg-probe-list {
             key "ha-srg-probe-dst-ipaddr";
             description
               "Display each probe information";
             leaf ha-srg-probe-dst-ipaddr {
               type string;
               description
                 "Destination IP address used for probing";
             }
             leaf ha-srg-probe-src-ipaddr {
               type string;
               description
                 "Source IP address used for probing";
             }
             leaf ha-srg-vip-if-name {
               type string;
               description
                 "Interface for the virtual IP assignment";
             }
             leaf ha-srg-probe-rt {
               type string;
               description
                 "Routing instance used for probing";
             }
             leaf ha-srg-probe-type {
               type string;
               description
                 "Probing type";
             }
             leaf ha-probe-interval {
               type int32;
               description
                 "HA probe interval in ms";
             }
             leaf ha-probe-multiplier {
               type int32;
               description
                 "HA probe multiplier";
             }
             leaf ha-probe-status {
               type string;
               description
                 "Probing status";
             }
             leaf ha-probe-result {
               type string;
               description
                 "Probing result";
             }
             leaf ha-srg-probe-fail-reason {
               type string;
               description
                 "Probing failure reason";
             }
           }
         }
         container chassis-high-availability-srg-mon-info {
           description
             "SRG global threshold info";
           leaf ha-srg-mon-status {
             type string;
             description
               "SRG monitor status";
           }
           leaf ha-srg-mon-threshold {
             type int32;
             description
               "SRG monitor threshold";
           }
           leaf ha-srg-mon-weight {
             type int32;
             description
               "SRG monitor weight";
           }
           leaf ha-srg-mon-failed-objects {
             type int32;
             description
               "SRG monitor failed objects";
           }
         }
         container chassis-high-availability-srg-obj-info {
           description
             "SRG monitor-object info";
           leaf ha-srg-obj-name {
             type string;
             description
               "SRG monitor object name";
           }
           leaf ha-srg-obj-status {
             type string;
             description
               "SRG monitor object status";
           }
           leaf ha-srg-obj-entries {
             type string;
             description
               "SRG monitor object monitored entries";
           }
           leaf ha-srg-obj-failure {
             type string;
             description
               "SRG monitor object monitored failures";
           }
           leaf ha-srg-obj-threshold {
             type int32;
             description
               "SRG monitor object threshold";
           }
           leaf ha-srg-obj-weight {
             type int32;
             description
               "SRG monitor object current weight";
           }
         }
         container chassis-high-availability-srg-bfdmon {
           description
             " SRG BFD mon information ";
           leaf ha-srg-bfdmon-status {
             type string;
             description
               "HA overall bfd-monitoring status";
           }
           container chassis-high-availability-srg-bfdmon-list {
             description
               " Display each BFD mon entry Information";
             leaf ha-srg-bfdmon-src-ipaddr {
               type string;
               description
                 "Source IP address configured for HA bfd-monitoring";
             }
             leaf ha-srg-bfdmon-dst-ipaddr {
               type string;
               description
                 "Destination IP address configured for HA bfd-monitoring";
             }
             leaf ha-srg-bfdmon-rt {
               type string;
               description
                 "Routing instance configured for HA bfd-monitoring";
             }
             leaf ha-srg-bfdmon-type {
               type string;
               description
                 "HA bfd-monitoring type";
             }
             leaf ha-srg-bfdmon-ifl-name {
               type string;
               description
                 "HA bfd-monitoring IFL name";
             }
             leaf ha-srg-bfdmon-state {
               type string;
               description
                 "HA bfd-monitoring state";
             }
           }
         }
         list high-availability-bfdmon-status-events {
           description
             "List of BFD-monitoring status events";
           leaf-list high-availability-bfdmon-status-event {
             type string;
             description
               "Recorded BFD-monitoring status event";
           }
         }
         container chassis-high-availability-srg-ipmon {
           description
             "SRG IP monitoring Info";
           leaf ha-srg-ipmon-status {
             type string;
             description
               "SRG overall IP-monitoring status";
           }
           container chassis-high-availability-srg-ipmon-list {
             description
               " Display each IP monitoring entry";
             leaf ha-srg-ipmon-dst-ipaddr {
               type string;
               description
                 "Destination IP address configured for HA ip-monitoring";
             }
             leaf ha-srg-ipmon-rt {
               type string;
               description
                 "Routing instance configured for HA ip-monitoring";
             }
             leaf ha-ipmon-status {
               type string;
               description
                 "HA ip-monitoring status";
             }
             leaf ha-srg-ipmon-reason {
               type string;
               description
                 "HA ip-monitoring failure reason";
             }
           }
         }
         container chassis-high-availability-srg-obj-ipmon {
           description
             "SRG monitor object IP monitoring Info";
           leaf ha-srg-obj-ipmon-threshold {
             type int32;
             description
               "SRG monitor object IP-monitoring threshold";
           }
           leaf ha-srg-obj-ipmon-weight {
             type int32;
             description
               "SRG monitor object IP-monitoring weight";
           }
           leaf ha-srg-obj-ipmon-status {
             type string;
             description
               "SRG monitor object IP-monitoring global status";
           }
           container chassis-high-availability-srg-obj-ipmon-list {
             description
               " Display each monitor object IP monitoring entry status";
             leaf ha-srg-obj-ipmon-entry-status {
               type string;
               description
                 "HA SRG monitor object ip-monitoring state";
             }
             leaf ha-srg-obj-ipmon-entry-weight {
               type int32;
               description
                 "HA SRG monitor object ip-monitoring weight";
             }
             leaf ha-srg-obj-ipmon-entry-dst-ipaddr {
               type string;
               description
                 "Destination IP address configured for HA ip-monitoring";
             }
           }
         }
         container chassis-high-availability-srg-obj-ipmon-detail {
           description
             "SRG monitor object IP monitoring detail Info";
           container chassis-high-availability-srg-ipmon-list {
             description
               " Display each IP monitoring entry";
             leaf ha-srg-ipmon-dst-ipaddr {
               type string;
               description
                 "Destination IP address configured for HA ip-monitoring";
             }
             leaf ha-srg-ipmon-rt {
               type string;
               description
                 "Routing instance configured for HA ip-monitoring";
             }
             leaf ha-ipmon-status {
               type string;
               description
                 "HA ip-monitoring status";
             }
             leaf ha-srg-ipmon-reason {
               type string;
               description
                 "HA ip-monitoring failure reason";
             }
           }
         }
         list high-availability-ipmon-status-events {
           description
             "List of ip-monitoring status events";
           leaf-list high-availability-ipmon-status-event {
             type string;
             description
               "Recorded ip-monitoring status event";
           }
         }
         list high-availability-probe-status-events {
           description
             "List of activeness probe status events";
           leaf-list high-availability-probe-status-event {
             type string;
             description
               "Recorded activeness probe status event";
           }
         }
         container chassis-high-availability-srg-ifmon {
           description
             "SRG Interface monitoring Info";
           leaf ha-srg-ifmon-status {
             type string;
             description
               "HA overall Interface-monitoring status";
           }
           container chassis-high-availability-srg-ifmon-list {
             description
               " Display each Interface monitoring entry";
             leaf ha-srg-ifmon-if-name {
               type string;
               description
                 "HA Interface-monitoring IF name";
             }
             leaf ha-srg-ifmon-state {
               type string;
               description
                 "HA Interface-monitoring state";
             }
           }
         }
       }
       list srg-info-detail {
         leaf srg-id {
           type int32;
           description
             "Current services redundancy group identifier";
         }
         leaf deployment-type {
           type string;
           description
             "Deployment Type";
         }
         leaf node-role {
           type string;
           description
             "Local node role";
         }
         leaf activeness-priority {
           type int32;
           description
             "SRG activeness priority";
         }
         leaf preemption {
           type string;
           description
             "Preemption enable flag Status";
         }
         leaf hold-timer {
           type int32;
           description
             "SRG hold down timer";
         }
         leaf process-pkt-in-bkp-state {
           type string;
           description
             "SRG backup state pkt processing info";
         }
         leaf service-names {
           type string;
           description
             "SRG service names";
         }
         leaf control-plane {
           type string;
           description
             "Control plane status";
         }
         leaf system-integrity-check {
           type string;
           description
             "Status of system integrity check";
         }
         leaf peer-id {
           type int32;
           description
             "Peer identifier";
         }
         leaf peer-node-role {
           type string;
           description
             "Peer node role";
         }
         leaf health-status {
           type string;
           description
             "Peer health status";
         }
         leaf failover-readiness {
           type string;
           description
             "SRG failover readiness";
         }
         leaf failure-events {
           type string;
           description
             "List of failure events";
         }
         leaf preempt {
           type string;
           description
             "Preempt configuration for the redundancy group";
         }
         container chassis-high-availability-srg-info-list {
           description
             "Displays each services redundancy group info";
           leaf srg-id {
             type int32;
             description
               "Current services redundancy group identifier";
           }
           leaf deployment-type {
             type string;
             description
               "Deployment Type";
           }
           leaf node-role {
             type string;
             description
               "Local node role";
           }
           leaf activeness-priority {
             type int32;
             description
               "SRG activeness priority";
           }
           leaf preemption {
             type string;
             description
               "Preemption enable flag Status";
           }
           leaf hold-timer {
             type int32;
             description
               "SRG hold down timer";
           }
           leaf process-pkt-in-bkp-state {
             type string;
             description
               "SRG backup state pkt processing info";
           }
           leaf service-names {
             type string;
             description
               "SRG service names";
           }
           leaf control-plane {
             type string;
             description
               "Control plane status";
           }
           leaf system-integrity-check {
             type string;
             description
               "Status of system integrity check";
           }
           leaf peer-id {
             type int32;
             description
               "Peer identifier";
           }
           leaf peer-node-role {
             type string;
             description
               "Peer node role";
           }
           leaf health-status {
             type string;
             description
               "Peer health status";
           }
           leaf failover-readiness {
             type string;
             description
               "SRG failover readiness";
           }
           leaf failure-events {
             type string;
             description
               "List of failure events";
           }
           leaf preempt {
             type string;
             description
               "Preempt configuration for the redundancy group";
           }
         }
         container high-availability-srg-signal-rt-info {
           description
             "  SRG Signal route Info";
           list ha-srg-signal-rt-list {
             description
               "Display each signal route information";
             leaf ha-srg-signal-rt-type {
               type string;
               description
                 "  SRG  Signal route type";
             }
             leaf ha-srg-signal-rt-ipaddr {
               type string;
               description
                 "IP address configured as SRG active signal route";
             }
             leaf ha-srg-signal-rt-rt {
               type string;
               description
                 "Routing table configured for active signal route";
             }
             leaf ha-srg-signal-rt-status {
               type string;
               description
                 " SRG signal Route installation status";
             }
           }
         }
         container high-availability-srg-vip-info {
           description
             "  SRG Virtual IP Info";
           list ha-srg-vip-list {
             key "ha-srg-vip-index";
             description
               "Display each Virtual IP information";
             leaf ha-srg-vip-index {
               type string;
               description
                 "  SRG  Signal Virtual IP Index";
             }
             leaf ha-srg-virtual-ipaddr {
               type string;
               description
                 "IP address configured as SRG virtual IP";
             }
             leaf ha-srg-virtual-ipaddr2 {
               type string;
               description
                 "IP address configured as SRG virtual IP";
             }
             leaf ha-srg-virtual-mac-address {
               type string;
               description
                 "MAC address for the virtual IP.";
             }
             leaf ha-srg-vip-if-name {
               type string;
               description
                 "Interface for the virtual IP assignment";
             }
             leaf ha-srg-vip-status {
               type string;
               description
                 " SRG Virtual IP assignmentstatus";
             }
           }
         }
         list high-availability-srg-state-events {
           description
             "List of service redundancy group state change events";
           leaf-list high-availability-srg-state-event {
             type string;
             description
               "Recorded service redundancy group state change event";
           }
         }
         list high-availability-peer-status-events {
           description
             "List of HA Peer Conn events";
           leaf-list high-availability-peer-status-event {
             type string;
             description
               "Recorded HA Peer Conn event";
           }
         }
         list high-availability-hw-upgrade-events {
           description
             "List of HA hardware upgrade events";
           leaf-list high-availability-hw-upgrade-event {
             type string;
             description
               "Recorded HA hardware upgrade event";
           }
         }
         container chassis-high-availability-srg-probe {
           description
             "SRG split brain prevention probe info";
           list chassis-high-availability-srg-probe-list {
             key "ha-srg-probe-dst-ipaddr";
             description
               "Display each probe information";
             leaf ha-srg-probe-dst-ipaddr {
               type string;
               description
                 "Destination IP address used for probing";
             }
             leaf ha-srg-probe-src-ipaddr {
               type string;
               description
                 "Source IP address used for probing";
             }
             leaf ha-srg-vip-if-name {
               type string;
               description
                 "Interface for the virtual IP assignment";
             }
             leaf ha-srg-probe-rt {
               type string;
               description
                 "Routing instance used for probing";
             }
             leaf ha-srg-probe-type {
               type string;
               description
                 "Probing type";
             }
             leaf ha-probe-interval {
               type int32;
               description
                 "HA probe interval in ms";
             }
             leaf ha-probe-multiplier {
               type int32;
               description
                 "HA probe multiplier";
             }
             leaf ha-probe-status {
               type string;
               description
                 "Probing status";
             }
             leaf ha-probe-result {
               type string;
               description
                 "Probing result";
             }
             leaf ha-srg-probe-fail-reason {
               type string;
               description
                 "Probing failure reason";
             }
           }
         }
         container chassis-high-availability-srg-mon-info {
           description
             "SRG global threshold info";
           leaf ha-srg-mon-status {
             type string;
             description
               "SRG monitor status";
           }
           leaf ha-srg-mon-threshold {
             type int32;
             description
               "SRG monitor threshold";
           }
           leaf ha-srg-mon-weight {
             type int32;
             description
               "SRG monitor weight";
           }
           leaf ha-srg-mon-failed-objects {
             type int32;
             description
               "SRG monitor failed objects";
           }
         }
         container chassis-high-availability-srg-obj-info {
           description
             "SRG monitor-object info";
           leaf ha-srg-obj-name {
             type string;
             description
               "SRG monitor object name";
           }
           leaf ha-srg-obj-status {
             type string;
             description
               "SRG monitor object status";
           }
           leaf ha-srg-obj-entries {
             type string;
             description
               "SRG monitor object monitored entries";
           }
           leaf ha-srg-obj-failure {
             type string;
             description
               "SRG monitor object monitored failures";
           }
           leaf ha-srg-obj-threshold {
             type int32;
             description
               "SRG monitor object threshold";
           }
           leaf ha-srg-obj-weight {
             type int32;
             description
               "SRG monitor object current weight";
           }
         }
         container chassis-high-availability-srg-bfdmon {
           description
             " SRG BFD mon information ";
           leaf ha-srg-bfdmon-status {
             type string;
             description
               "HA overall bfd-monitoring status";
           }
           container chassis-high-availability-srg-bfdmon-list {
             description
               " Display each BFD mon entry Information";
             leaf ha-srg-bfdmon-src-ipaddr {
               type string;
               description
                 "Source IP address configured for HA bfd-monitoring";
             }
             leaf ha-srg-bfdmon-dst-ipaddr {
               type string;
               description
                 "Destination IP address configured for HA bfd-monitoring";
             }
             leaf ha-srg-bfdmon-rt {
               type string;
               description
                 "Routing instance configured for HA bfd-monitoring";
             }
             leaf ha-srg-bfdmon-type {
               type string;
               description
                 "HA bfd-monitoring type";
             }
             leaf ha-srg-bfdmon-ifl-name {
               type string;
               description
                 "HA bfd-monitoring IFL name";
             }
             leaf ha-srg-bfdmon-state {
               type string;
               description
                 "HA bfd-monitoring state";
             }
           }
         }
         list high-availability-bfdmon-status-events {
           description
             "List of BFD-monitoring status events";
           leaf-list high-availability-bfdmon-status-event {
             type string;
             description
               "Recorded BFD-monitoring status event";
           }
         }
         container chassis-high-availability-srg-ipmon {
           description
             "SRG IP monitoring Info";
           leaf ha-srg-ipmon-status {
             type string;
             description
               "SRG overall IP-monitoring status";
           }
           container chassis-high-availability-srg-ipmon-list {
             description
               " Display each IP monitoring entry";
             leaf ha-srg-ipmon-dst-ipaddr {
               type string;
               description
                 "Destination IP address configured for HA ip-monitoring";
             }
             leaf ha-srg-ipmon-rt {
               type string;
               description
                 "Routing instance configured for HA ip-monitoring";
             }
             leaf ha-ipmon-status {
               type string;
               description
                 "HA ip-monitoring status";
             }
             leaf ha-srg-ipmon-reason {
               type string;
               description
                 "HA ip-monitoring failure reason";
             }
           }
         }
         container chassis-high-availability-srg-obj-ipmon {
           description
             "SRG monitor object IP monitoring Info";
           leaf ha-srg-obj-ipmon-threshold {
             type int32;
             description
               "SRG monitor object IP-monitoring threshold";
           }
           leaf ha-srg-obj-ipmon-weight {
             type int32;
             description
               "SRG monitor object IP-monitoring weight";
           }
           leaf ha-srg-obj-ipmon-status {
             type string;
             description
               "SRG monitor object IP-monitoring global status";
           }
           container chassis-high-availability-srg-obj-ipmon-list {
             description
               " Display each monitor object IP monitoring entry status";
             leaf ha-srg-obj-ipmon-entry-status {
               type string;
               description
                 "HA SRG monitor object ip-monitoring state";
             }
             leaf ha-srg-obj-ipmon-entry-weight {
               type int32;
               description
                 "HA SRG monitor object ip-monitoring weight";
             }
             leaf ha-srg-obj-ipmon-entry-dst-ipaddr {
               type string;
               description
                 "Destination IP address configured for HA ip-monitoring";
             }
           }
         }
         container chassis-high-availability-srg-obj-ipmon-detail {
           description
             "SRG monitor object IP monitoring detail Info";
           container chassis-high-availability-srg-ipmon-list {
             description
               " Display each IP monitoring entry";
             leaf ha-srg-ipmon-dst-ipaddr {
               type string;
               description
                 "Destination IP address configured for HA ip-monitoring";
             }
             leaf ha-srg-ipmon-rt {
               type string;
               description
                 "Routing instance configured for HA ip-monitoring";
             }
             leaf ha-ipmon-status {
               type string;
               description
                 "HA ip-monitoring status";
             }
             leaf ha-srg-ipmon-reason {
               type string;
               description
                 "HA ip-monitoring failure reason";
             }
           }
         }
         list high-availability-ipmon-status-events {
           description
             "List of ip-monitoring status events";
           leaf-list high-availability-ipmon-status-event {
             type string;
             description
               "Recorded ip-monitoring status event";
           }
         }
         list high-availability-probe-status-events {
           description
             "List of activeness probe status events";
           leaf-list high-availability-probe-status-event {
             type string;
             description
               "Recorded activeness probe status event";
           }
         }
         container chassis-high-availability-srg-ifmon {
           description
             "SRG Interface monitoring Info";
           leaf ha-srg-ifmon-status {
             type string;
             description
               "HA overall Interface-monitoring status";
           }
           container chassis-high-availability-srg-ifmon-list {
             description
               " Display each Interface monitoring entry";
             leaf ha-srg-ifmon-if-name {
               type string;
               description
                 "HA Interface-monitoring IF name";
             }
             leaf ha-srg-ifmon-state {
               type string;
               description
                 "HA Interface-monitoring state";
             }
           }
         }
       }
     }
   }
   grouping chassis-high-availability-peer-info-detail-block {
     leaf high-availability-peer-desc {
       type string;
       description
         "Peer description";
     }
     leaf high-availability-peer-id {
       type int32;
       description
         "Peer identifier that is configured";
     }
     leaf high-availability-peer-ip-address {
       type jt:ipaddr;
       description
         "Peer remote IPv4 address that is configured";
     }
     leaf-list high-availability-local-interface {
       type string;
       description
         "Local interface";
     }
     leaf high-availability-peer-rt-instance {
       type string;
       description
         "Routing Instance name for HA peer";
     }
     leaf high-availability-peer-encryption-status {
       type string;
       description
         "Encryption status of the current node";
     }
     leaf high-availability-peer-bfd-status {
       type string;
       description
         "BFD Status of the current node";
     }
     leaf cold-sync-status {
       type string;
       description
         "Cold synchronization status";
     }
     leaf peer-hw-incompatible {
       type string;
       description
         "Peer hardware compatible status";
     }
     leaf peer-internal-interface {
       type string;
       description
         "Peer internal interface";
     }
     leaf peer-internal-local-ip {
       type jt:ipaddr;
       description
         "Internal local IPv4 address";
     }
     leaf peer-internal-peer-ip {
       type jt:ipaddr;
       description
         "Internal peer IPv4 address";
     }
     leaf peer-internal-routing-instance {
       type string;
       description
         "Peer internal routing instance";
     }
     leaf high-availability-peer-fwd-ip-address {
       type jt:ipaddr;
       description
         "Peer forwarding remote IP address";
     }
     leaf high-availability-local-fwd-interface {
       type string;
       description
         "Local forwarding interface";
     }
     leaf high-availability-peer-fwd-bfd-status {
       type string;
       description
         "BFD forwarding status of the current node";
     }
     leaf peer-domain-id {
       type int32;
       description
         "Peer-domain-id";
     }
     leaf high-availability-peer-detect-time {
       type string;
       description
         "Configured Peer BFD detection time";
     }
     container chassis-mnha-icl-peer-info {
       description
         "Displays mnha icl peer related info";
       leaf high-availability-peer-desc {
         type string;
         description
           "Peer description";
       }
       leaf peer-domain-id {
         type int32;
         description
           "Peer-domain-id";
       }
       leaf high-availability-peer-id {
         type int32;
         description
           "Peer identifier that is configured";
       }
       leaf high-availability-peer-ip-address {
         type jt:ipaddr;
         description
           "Peer remote IPv4 address that is configured";
       }
       leaf-list high-availability-local-interface {
         type string;
         description
           "Local interface";
       }
       leaf high-availability-peer-rt-instance {
         type string;
         description
           "Routing Instance name for HA peer";
       }
       leaf high-availability-peer-encryption-status {
         type string;
         description
           "Encryption status of the current node";
       }
       leaf high-availability-peer-bfd-status {
         type string;
         description
           "BFD Status of the current node";
       }
       leaf cold-sync-status {
         type string;
         description
           "Cold synchronization status";
       }
       leaf peer-hw-incompatible {
         type string;
         description
           "Peer hardware compatible status";
       }
       leaf peer-internal-interface {
         type string;
         description
           "Peer internal interface";
       }
       leaf peer-internal-local-ip {
         type jt:ipaddr;
         description
           "Internal local IPv4 address";
       }
       leaf peer-internal-peer-ip {
         type jt:ipaddr;
         description
           "Internal peer IPv4 address";
       }
       leaf peer-internal-routing-instance {
         type string;
         description
           "Peer internal routing instance";
       }
       leaf high-availability-peer-detect-time {
         type string;
         description
           "Configured Peer BFD detection time";
       }
       leaf srg0-cold-sync-status {
         type string;
         description
           "SRG0 cold sync status";
       }
       container chassis-mnha-local-node-idl-info {
         description
           "Displays high-availability local node IDL BFD and CS state";
         leaf states-from-domain-id {
           type int32;
           description
             "States from domain id";
         }
         leaf states-from-node-id {
           type int32;
           description
             "States from node id";
         }
         leaf domain-id {
           type int32;
           description
             "Domain-id";
         }
         leaf peer-id {
           type int32;
           description
             "Peer identifier";
         }
         leaf conn-state {
           type string;
           description
             "Conn state";
         }
         leaf rtt-result {
           type string;
           description
             "RTT result";
         }
         leaf cold-sync-status {
           type string;
           description
             "Cold synchronization status";
         }
         leaf srg0-idl-status {
           type string;
           description
             "SRG0 idl status";
         }
       }
       container chassis-mnha-peer-node-icl-info {
         description
           "Displays high-availability icl info";
         leaf states-from-domain-id {
           type int32;
           description
             "States from domain id";
         }
         leaf states-from-node-id {
           type int32;
           description
             "States from node id";
         }
         leaf icl-conn-state {
           type string;
           description
             "ICL Conn state";
         }
         leaf cold-sync-status {
           type string;
           description
             "Cold synchronization status";
         }
       }
       container chassis-mnha-peer-node-idl-info {
         description
           "Displays high-availability peer node IDL BFD and CS state";
         leaf states-from-domain-id {
           type int32;
           description
             "States from domain id";
         }
         leaf states-from-node-id {
           type int32;
           description
             "States from node id";
         }
         leaf domain-id {
           type int32;
           description
             "Domain-id";
         }
         leaf peer-id {
           type int32;
           description
             "Peer identifier";
         }
         leaf conn-state {
           type string;
           description
             "Conn state";
         }
         leaf rtt-result {
           type string;
           description
             "RTT result";
         }
         leaf cold-sync-status {
           type string;
           description
             "Cold synchronization status";
         }
         leaf srg0-idl-status {
           type string;
           description
             "SRG0 idl status";
         }
       }
       list high-availability-peer-packet-stats {
         description
           "Peer Packet Stats";
         leaf packet-send-err-cnt {
           type int32;
           description
             "Peer packet send error cnt";
         }
         leaf packet-recv-err-cnt {
           type int32;
           description
             "Peer packet recv error cnt";
         }
         list peer-packet-send-rcv-stats {
           description
             "Peer Packet Send receive Stats";
           list peer-packet-stats-list {
             description
               "Stats for each peer packet type";
             leaf peer-packet-type {
               type string;
               description
                 "Peer packet Type";
             }
             leaf peer-packet-send-cnt {
               type int32;
               description
                 "Peer packet sent count";
             }
             leaf peer-packet-rcv-cnt {
               type int32;
               description
                 "Peer packet rcv cnt";
             }
           }
         }
       }
     }
     list chassis-mnha-idl-peer-info {
       description
         "Displays mnha idl peer related info";
       leaf high-availability-peer-desc {
         type string;
         description
           "Peer description";
       }
       leaf peer-domain-id {
         type int32;
         description
           "Peer-domain-id";
       }
       leaf high-availability-peer-id {
         type int32;
         description
           "Peer identifier that is configured";
       }
       leaf high-availability-peer-ip-address {
         type jt:ipaddr;
         description
           "Peer remote IPv4 address that is configured";
       }
       leaf-list high-availability-local-interface {
         type string;
         description
           "Local interface";
       }
       leaf high-availability-peer-rt-instance {
         type string;
         description
           "Routing Instance name for HA peer";
       }
       leaf high-availability-peer-encryption-status {
         type string;
         description
           "Encryption status of the current node";
       }
       leaf high-availability-peer-idl-bfd-status {
         type string;
         description
           "IDL BFD Status of the current node";
       }
       leaf cold-sync-status {
         type string;
         description
           "Cold synchronization status";
       }
       leaf peer-hw-incompatible {
         type string;
         description
           "Peer hardware compatible status";
       }
       leaf peer-internal-interface {
         type string;
         description
           "Peer internal interface";
       }
       leaf peer-internal-local-ip {
         type jt:ipaddr;
         description
           "Internal local IPv4 address";
       }
       leaf peer-internal-peer-ip {
         type jt:ipaddr;
         description
           "Internal peer IPv4 address";
       }
       leaf peer-internal-routing-instance {
         type string;
         description
           "Peer internal routing instance";
       }
       leaf high-availability-peer-detect-time {
         type string;
         description
           "Configured Peer BFD detection time";
       }
       container chassis-mnha-peer-node-icl-info {
         description
           "Displays high-availability icl info";
         leaf states-from-domain-id {
           type int32;
           description
             "States from domain id";
         }
         leaf states-from-node-id {
           type int32;
           description
             "States from node id";
         }
         leaf icl-conn-state {
           type string;
           description
             "ICL Conn state";
         }
         leaf cold-sync-status {
           type string;
           description
             "Cold synchronization status";
         }
       }
       container chassis-mnha-peer-domain-idl-info {
         description
           "Displays high-availability peer domain IDL BFD and CS state";
         leaf states-from-domain-id {
           type int32;
           description
             "States from domain id";
         }
         leaf states-from-node-id {
           type int32;
           description
             "States from node id";
         }
         leaf domain-id {
           type int32;
           description
             "Domain-id";
         }
         leaf peer-id {
           type int32;
           description
             "Peer identifier";
         }
         leaf conn-state {
           type string;
           description
             "Conn state";
         }
         leaf rtt-result {
           type string;
           description
             "RTT result";
         }
         leaf cold-sync-status {
           type string;
           description
             "Cold synchronization status";
         }
         leaf srg0-idl-status {
           type string;
           description
             "SRG0 idl status";
         }
       }
       list high-availability-peer-packet-stats {
         description
           "Peer Packet Stats";
         leaf packet-send-err-cnt {
           type int32;
           description
             "Peer packet send error cnt";
         }
         leaf packet-recv-err-cnt {
           type int32;
           description
             "Peer packet recv error cnt";
         }
         list peer-packet-send-rcv-stats {
           description
             "Peer Packet Send receive Stats";
           list peer-packet-stats-list {
             description
               "Stats for each peer packet type";
             leaf peer-packet-type {
               type string;
               description
                 "Peer packet Type";
             }
             leaf peer-packet-send-cnt {
               type int32;
               description
                 "Peer packet sent count";
             }
             leaf peer-packet-rcv-cnt {
               type int32;
               description
                 "Peer packet rcv cnt";
             }
           }
         }
       }
     }
     list high-availability-peer-packet-stats {
       description
         "Peer Packet Stats";
       leaf packet-send-err-cnt {
         type int32;
         description
           "Peer packet send error cnt";
       }
       leaf packet-recv-err-cnt {
         type int32;
         description
           "Peer packet recv error cnt";
       }
       list peer-packet-send-rcv-stats {
         description
           "Peer Packet Send receive Stats";
         list peer-packet-stats-list {
           description
             "Stats for each peer packet type";
           leaf peer-packet-type {
             type string;
             description
               "Peer packet Type";
           }
           leaf peer-packet-send-cnt {
             type int32;
             description
               "Peer packet sent count";
           }
           leaf peer-packet-rcv-cnt {
             type int32;
             description
               "Peer packet rcv cnt";
           }
         }
       }
     }
   }
   grouping chassis-cluster-data-plane-statistics-block {
     list l3ha-services-synchronized {
       description
         "L3HA services synchronization statistics";
       leaf service-name {
         type string;
         description
           "Name of the service";
       }
       leaf rtos-sent {
         type uint32;
         description
           "RTOs sent";
       }
       leaf rtos-received {
         type uint32;
         description
           "RTOs received";
       }
     }
     list l3ha-icd-pkt-stats {
       description
         "L3HA ICD packet statistics";
       leaf service-name {
         type string;
         description
           "Name of the service";
       }
       leaf pkts-sent {
         type uint32;
         description
           "RTOs sent";
       }
       leaf pkts-received {
         type uint32;
         description
           "RTOs received";
       }
     }
   }
   grouping chassis-high-availability-srg-terse-info-block {
     container chassis-high-availability-srg-info {
       description
         "Displays high-availability services redundancy group info";
       container chassis-high-availability-srg-info-list {
         description
           "Displays each services redundancy group info";
         leaf srg-id {
           type int32;
           description
             "Current services redundancy group identifier";
         }
         leaf deployment-type {
           type string;
           description
             "Deployment Type";
         }
         leaf node-role {
           type string;
           description
             "Local node role";
         }
         leaf activeness-priority {
           type int32;
           description
             "SRG activeness priority";
         }
         leaf preemption {
           type string;
           description
             "Preemption enable flag Status";
         }
         leaf process-pkt-in-bkp-state {
           type string;
           description
             "SRG backup state pkt processing info";
         }
         leaf control-plane {
           type string;
           description
             "Control plane status";
         }
         leaf system-integrity-check {
           type string;
           description
             "Status of system integrity check";
         }
         leaf failure-events {
           type string;
           description
             "List of failure events";
         }
         leaf peer-id {
           type int32;
           description
             "Peer identifier";
         }
         leaf peer-node-role {
           type string;
           description
             "Peer node role";
         }
         leaf health-status {
           type string;
           description
             "Peer health status";
         }
         leaf failover-readiness {
           type string;
           description
             "SRG failover readiness";
         }
       }
     }
     container high-availability-srg-signal-rt-info {
       description
         "  SRG Signal route Info";
       list ha-srg-signal-rt-list {
         description
           "Display each signal route information";
         leaf ha-srg-signal-rt-type {
           type string;
           description
             "  SRG  Signal route type";
         }
         leaf ha-srg-signal-rt-ipaddr {
           type string;
           description
             "IP address configured as SRG active signal route";
         }
         leaf ha-srg-signal-rt-rt {
           type string;
           description
             "Routing table configured for active signal route";
         }
         leaf ha-srg-signal-rt-status {
           type string;
           description
             " SRG signal Route installation status";
         }
       }
     }
     container high-availability-srg-vip-info {
       description
         "  SRG Virtual IP Info";
       list ha-srg-vip-list {
         key "ha-srg-vip-index";
         description
           "Display each Virtual IP information";
         leaf ha-srg-vip-index {
           type string;
           description
             "  SRG  Signal Virtual IP Index";
         }
         leaf ha-srg-virtual-ipaddr {
           type string;
           description
             "IP address configured as SRG virtual IP";
         }
         leaf ha-srg-virtual-ipaddr2 {
           type string;
           description
             "IP address configured as SRG virtual IP";
         }
         leaf ha-srg-virtual-mac-address {
           type string;
           description
             "MAC address for the virtual IP.";
         }
         leaf ha-srg-vip-if-name {
           type string;
           description
             "Interface for the virtual IP assignment";
         }
         leaf ha-srg-vip-status {
           type string;
           description
             " SRG Virtual IP assignmentstatus";
         }
       }
     }
     container chassis-high-availability-srg-probe {
       description
         "SRG split brain prevention probe info";
       list chassis-high-availability-srg-probe-list {
         key "ha-srg-probe-dst-ipaddr";
         description
           "Display each probe information";
         leaf ha-srg-probe-dst-ipaddr {
           type string;
           description
             "Destination IP address used for probing";
         }
         leaf ha-srg-probe-src-ipaddr {
           type string;
           description
             "Source IP address used for probing";
         }
         leaf ha-srg-vip-if-name {
           type string;
           description
             "Interface for the virtual IP assignment";
         }
         leaf ha-srg-probe-rt {
           type string;
           description
             "Routing instance used for probing";
         }
         leaf ha-srg-probe-type {
           type string;
           description
             "Probing type";
         }
         leaf ha-probe-interval {
           type int32;
           description
             "HA probe interval in ms";
         }
         leaf ha-probe-multiplier {
           type int32;
           description
             "HA probe multiplier";
         }
         leaf ha-probe-status {
           type string;
           description
             "Probing status";
         }
         leaf ha-probe-result {
           type string;
           description
             "Probing result";
         }
         leaf ha-srg-probe-fail-reason {
           type string;
           description
             "Probing failure reason";
         }
       }
     }
     container chassis-high-availability-srg-ipmon {
       description
         "SRG IP monitoring Info";
       leaf ha-srg-ipmon-status {
         type string;
         description
           "SRG overall IP-monitoring status";
       }
       container chassis-high-availability-srg-ipmon-list {
         description
           " Display each IP monitoring entry";
         leaf ha-srg-ipmon-dst-ipaddr {
           type string;
           description
             "Destination IP address configured for HA ip-monitoring";
         }
         leaf ha-srg-ipmon-rt {
           type string;
           description
             "Routing instance configured for HA ip-monitoring";
         }
         leaf ha-ipmon-status {
           type string;
           description
             "HA ip-monitoring status";
         }
         leaf ha-srg-ipmon-reason {
           type string;
           description
             "HA ip-monitoring failure reason";
         }
       }
     }
     container chassis-high-availability-srg-bfdmon {
       description
         " SRG BFD mon information ";
       leaf ha-srg-bfdmon-status {
         type string;
         description
           "HA overall bfd-monitoring status";
       }
       container chassis-high-availability-srg-bfdmon-list {
         description
           " Display each BFD mon entry Information";
         leaf ha-srg-bfdmon-src-ipaddr {
           type string;
           description
             "Source IP address configured for HA bfd-monitoring";
         }
         leaf ha-srg-bfdmon-dst-ipaddr {
           type string;
           description
             "Destination IP address configured for HA bfd-monitoring";
         }
         leaf ha-srg-bfdmon-rt {
           type string;
           description
             "Routing instance configured for HA bfd-monitoring";
         }
         leaf ha-srg-bfdmon-type {
           type string;
           description
             "HA bfd-monitoring type";
         }
         leaf ha-srg-bfdmon-ifl-name {
           type string;
           description
             "HA bfd-monitoring IFL name";
         }
         leaf ha-srg-bfdmon-state {
           type string;
           description
             "HA bfd-monitoring state";
         }
       }
     }
     container chassis-high-availability-srg-ifmon {
       description
         "SRG Interface monitoring Info";
       leaf ha-srg-ifmon-status {
         type string;
         description
           "HA overall Interface-monitoring status";
       }
       container chassis-high-availability-srg-ifmon-list {
         description
           " Display each Interface monitoring entry";
         leaf ha-srg-ifmon-if-name {
           type string;
           description
             "HA Interface-monitoring IF name";
         }
         leaf ha-srg-ifmon-state {
           type string;
           description
             "HA Interface-monitoring state";
         }
       }
     }
     list high-availability-srg-state-events {
       description
         "List of service redundancy group state change events";
       leaf-list high-availability-srg-state-event {
         type string;
         description
           "Recorded service redundancy group state change event";
       }
     }
     list chassis-high-availability-prefix-information {
       container chassis-high-availability-prefix-srgid-information {
         description
           "Display ip prefix and srgid mapping info";
         list chassis-high-availability-prefix-srgid-information-list {
           leaf ha-mnha-ip-prefix-srgid {
             type string;
             description
               "MNHA srg-id";
           }
           leaf ha-mnha-ip-prefix {
             type string;
             description
               "IP Prefix";
           }
           leaf ha-mnha-ip-vrf {
             type string;
             description
               "Routing Table";
           }
         }
       }
       container chassis-high-availability-prefix-ip-information {
         description
           "Display srgid id info given an ip address";
         container chassis-high-availability-prefix-ip-information-list {
           leaf ha-mnha-ip-srgid {
             type int32;
             description
               "MNHA srg-id";
           }
         }
       }
     }
     list chassis-high-availability-srg-mon-obj-info {
       container chassis-high-availability-srg-mon-info {
         description
           "SRG global threshold info";
         leaf ha-srg-mon-status {
           type string;
           description
             "SRG monitor status";
         }
         leaf ha-srg-mon-threshold {
           type int32;
           description
             "SRG monitor threshold";
         }
         leaf ha-srg-mon-weight {
           type int32;
           description
             "SRG monitor weight";
         }
         leaf ha-srg-mon-failed-objects {
           type int32;
           description
             "SRG monitor failed objects";
         }
       }
       container chassis-high-availability-srg-obj-info {
         description
           "SRG monitor-object info";
         leaf ha-srg-obj-name {
           type string;
           description
             "SRG monitor object name";
         }
         leaf ha-srg-obj-status {
           type string;
           description
             "SRG monitor object status";
         }
         leaf ha-srg-obj-entries {
           type string;
           description
             "SRG monitor object monitored entries";
         }
         leaf ha-srg-obj-failure {
           type string;
           description
             "SRG monitor object monitored failures";
         }
         leaf ha-srg-obj-threshold {
           type int32;
           description
             "SRG monitor object threshold";
         }
         leaf ha-srg-obj-weight {
           type int32;
           description
             "SRG monitor object current weight";
         }
       }
       container chassis-high-availability-srg-obj-ipmon {
         description
           "SRG monitor object IP monitoring Info";
         leaf ha-srg-obj-ipmon-threshold {
           type int32;
           description
             "SRG monitor object IP-monitoring threshold";
         }
         leaf ha-srg-obj-ipmon-weight {
           type int32;
           description
             "SRG monitor object IP-monitoring weight";
         }
         leaf ha-srg-obj-ipmon-status {
           type string;
           description
             "SRG monitor object IP-monitoring global status";
         }
         container chassis-high-availability-srg-obj-ipmon-list {
           description
             " Display each monitor object IP monitoring entry status";
           leaf ha-srg-obj-ipmon-entry-status {
             type string;
             description
               "HA SRG monitor object ip-monitoring state";
           }
           leaf ha-srg-obj-ipmon-entry-weight {
             type int32;
             description
               "HA SRG monitor object ip-monitoring weight";
           }
           leaf ha-srg-obj-ipmon-entry-dst-ipaddr {
             type string;
             description
               "Destination IP address configured for HA ip-monitoring";
           }
         }
       }
       container chassis-high-availability-srg-obj-ipmon-detail {
         description
           "SRG monitor object IP monitoring detail Info";
         container chassis-high-availability-srg-ipmon-list {
           description
             " Display each IP monitoring entry";
           leaf ha-srg-ipmon-dst-ipaddr {
             type string;
             description
               "Destination IP address configured for HA ip-monitoring";
           }
           leaf ha-srg-ipmon-rt {
             type string;
             description
               "Routing instance configured for HA ip-monitoring";
           }
           leaf ha-ipmon-status {
             type string;
             description
               "HA ip-monitoring status";
           }
           leaf ha-srg-ipmon-reason {
             type string;
             description
               "HA ip-monitoring failure reason";
           }
         }
       }
       container chassis-high-availability-srg-obj-bfdmon {
         description
           "SRG monitor object BFD monitoring Info";
         leaf ha-srg-obj-bfdmon-threshold {
           type int32;
           description
             "SRG monitor object BFD-monitoring threshold";
         }
         leaf ha-srg-obj-bfdmon-weight {
           type int32;
           description
             "SRG monitor object BFD-monitoring weight";
         }
         leaf ha-srg-obj-bfdmon-status {
           type string;
           description
             "SRG monitor object BFD-monitoring global status";
         }
         container chassis-high-availability-srg-obj-bfdmon-list {
           description
             "Display each monitor object BFD monitoring entry status";
           leaf ha-srg-obj-bfdmon-entry-status {
             type string;
             description
               "HA SRG monitor object BFD-monitoring state";
           }
           leaf ha-srg-obj-bfdmon-entry-weight {
             type int32;
             description
               "HA SRG monitor object BFD-monitoring weight";
           }
           leaf ha-srg-obj-bfdmon-entry-dst-bfdaddr {
             type string;
             description
               "Destination BFD address configured for HA BFD-monitoring";
           }
         }
       }
       container chassis-high-availability-srg-obj-bfdmon-detail {
         description
           "SRG monitor object BFD mon information ";
         container chassis-high-availability-srg-bfdmon-list {
           description
             " Display each BFD mon entry Information";
           leaf ha-srg-bfdmon-src-ipaddr {
             type string;
             description
               "Source IP address configured for HA bfd-monitoring";
           }
           leaf ha-srg-bfdmon-dst-ipaddr {
             type string;
             description
               "Destination IP address configured for HA bfd-monitoring";
           }
           leaf ha-srg-bfdmon-rt {
             type string;
             description
               "Routing instance configured for HA bfd-monitoring";
           }
           leaf ha-srg-bfdmon-type {
             type string;
             description
               "HA bfd-monitoring type";
           }
           leaf ha-srg-bfdmon-ifl-name {
             type string;
             description
               "HA bfd-monitoring IFL name";
           }
           leaf ha-srg-bfdmon-state {
             type string;
             description
               "HA bfd-monitoring state";
           }
         }
       }
       container chassis-high-availability-srg-obj-ifmon {
         description
           "SRG monitor object IF monitoring Info";
         leaf ha-srg-obj-ifmon-threshold {
           type int32;
           description
             "SRG monitor object IF-monitoring threshold";
         }
         leaf ha-srg-obj-ifmon-weight {
           type int32;
           description
             "SRG monitor object IF-monitoring current weight";
         }
         leaf ha-srg-ifmon-status {
           type string;
           description
             "HA overall Interface-monitoring status";
         }
         container chassis-high-availability-srg-obj-ifmon-list {
           description
             "Display each monitor object IF monitoring entry status";
           leaf ha-srg-ifmon-entry-status {
             type string;
             description
               "HA SRG monitor object IF-monitoring entry status";
           }
           leaf ha-srg-obj-ifmon-entry-weight {
             type int32;
             description
               "HA SRG monitor object IF-monitoring entry weight";
           }
           leaf ha-srg-ifmon-if-name {
             type string;
             description
               "HA Interface-monitoring IF name";
           }
         }
       }
     }
   }
   grouping chassis-high-availability-prefix-information-block {
     container chassis-high-availability-prefix-srgid-information {
       description
         "Display ip prefix and srgid mapping info";
       list chassis-high-availability-prefix-srgid-information-list {
         leaf ha-mnha-ip-prefix-srgid {
           type string;
           description
             "MNHA srg-id";
         }
         leaf ha-mnha-ip-prefix {
           type string;
           description
             "IP Prefix";
         }
         leaf ha-mnha-ip-vrf {
           type string;
           description
             "Routing Table";
         }
       }
     }
     container chassis-high-availability-prefix-ip-information {
       description
         "Display srgid id info given an ip address";
       container chassis-high-availability-prefix-ip-information-list {
         leaf ha-mnha-ip-srgid {
           type int32;
           description
             "MNHA srg-id";
         }
       }
     }
   }
   grouping chassis-high-availability-prefix-ip-information-block {
     container chassis-high-availability-prefix-ip-information-list {
       leaf ha-mnha-ip-srgid {
         type int32;
         description
           "MNHA srg-id";
       }
     }
   }
   grouping chassis-high-availability-prefix-srgid-information-block {
     list chassis-high-availability-prefix-srgid-information-list {
       leaf ha-mnha-ip-prefix-srgid {
         type string;
         description
           "MNHA srg-id";
       }
       leaf ha-mnha-ip-prefix {
         type string;
         description
           "IP Prefix";
       }
       leaf ha-mnha-ip-vrf {
         type string;
         description
           "Routing Table";
       }
     }
   }
   grouping chassis-high-availability-prefix-policy-information-block {
     container chassis-high-availability-ip-prefix {
       description
         "Display ip and policy prefix mapping info";
       container chassis-high-availability-ip-prefix-list {
         leaf ha-policy-ip {
           type string;
           description
             "IP Prefix";
         }
         leaf ha-policy-prefix {
           type string;
           description
             "Policy Prefix";
         }
       }
     }
     container chassis-high-availability-prefix-srgid {
       description
         "Display ip prefix and srgid mapping info";
       container chassis-high-availability-prefix-srgid-list {
         leaf ha-mnha-srgid {
           type string;
           description
             "MNHA srg-id";
         }
         leaf ha-mnha-prefix-vrf {
           type string;
           description
             "Routing Table";
         }
         leaf ha-mnha-prefix-name {
           type string;
           description
             "IP Prefix";
         }
       }
     }
   }
   grouping satellite-information-block {
     list satellite {
       leaf slot-id {
         type int32;
       }
       leaf operation-state {
         type string;
       }
       leaf product-model {
         type string;
       }
       leaf number-of-extended-ports {
         type int32;
       }
       leaf number-of-extended-ports-up {
         type int32;
       }
       leaf version {
         type string;
       }
       list connectivity {
         leaf cascade-port {
           type string;
         }
         leaf interface-state {
           type string;
         }
         leaf uplink-interface-name {
           type string;
         }
         leaf adjacency-state {
           type string;
         }
         leaf remaining-time {
           type string;
         }
         leaf last-transition {
           type string;
         }
         leaf miswire-cause {
           type string;
         }
         leaf up-down-transition-count {
           type string;
         }
         leaf down-cause {
           type string;
         }
         leaf message-received-count {
           type int32;
         }
         leaf last-recv-packet-time {
           type string;
         }
         leaf message-error-count {
           type int32;
         }
         leaf last-error-packet-time {
           type string;
         }
         leaf error-cause {
           type string;
         }
         list peer-adjacency {
           leaf peer-adj-elapsed-time {
             type string;
           }
           leaf peer-up-down-transition-count {
             type int32;
           }
           leaf peer-down-cause {
             type string;
           }
           leaf peer-restart-count {
             type int32;
           }
           leaf gres-count {
             type int32;
           }
         }
       }
       leaf system-id {
         type string;
       }
       leaf serial-number {
         type string;
       }
       leaf satellite-alias {
         type string;
       }
       leaf reachability {
         type string;
       }
       leaf product-family {
         type string;
       }
       leaf host-sw-version {
         type string;
       }
       leaf downloaded-sw-version {
         type string;
       }
       leaf management-address {
         type string;
       }
       leaf ufd-config-state {
         type string;
       }
       leaf minimum-link {
         type int32;
       }
       leaf holddown-timer {
         type int32;
       }
       leaf ufd-operation-state {
         type string;
       }
       leaf uplink-port-pinning-state {
         type string;
       }
       leaf local-port-mirror-state {
         type string;
       }
       leaf mode-change-state {
         type string;
       }
       leaf extended-ports-template {
         type string;
       }
       leaf sw-incompatibility-reason {
         type string;
       }
       list process {
         leaf process-name {
           type string;
         }
         leaf process-id {
           type int32;
         }
         leaf process-state {
           type string;
         }
         leaf restart-count {
           type int32;
         }
         leaf last-restart-cause {
           type string;
         }
         leaf uptime {
           type string;
         }
       }
       list uplink-interface-list {
         leaf pic-id {
           type int32;
         }
         leaf port-id {
           type int32;
         }
       }
       list event-history {
         leaf event-timestamp {
           type string;
         }
         leaf event-id {
           type string;
         }
         leaf event-action {
           type string;
         }
         leaf event-information {
           type string;
         }
       }
     }
   }
   grouping multi-chassis-cluster-information-block {
     list multi-chassis-cluster {
       leaf multi-chassis-cluster-name {
         type string;
       }
       leaf multi-chassis-cluster-state {
         type string;
       }
       leaf peer-chassis-id {
         type int32;
       }
       leaf peer-chassis-serial-number {
         type string;
       }
       leaf local-chassis-id {
         type int32;
       }
       leaf peer-num-of-provisioning-devices {
         type int32;
       }
       leaf num-of-local-online-devices {
         type string;
       }
       leaf peer-num-of-online-devices {
         type int32;
       }
       list event-history {
         leaf event-timestamp {
           type string;
         }
         leaf event-id {
           type string;
         }
         leaf event-action {
           type string;
         }
         leaf event-information {
           type string;
         }
       }
     }
     list evpn-multi-chassis-cluster {
       leaf evpn-multi-chassis-cluster-name {
         type string;
       }
       leaf evpn-multi-chassis-cluster-state {
         type string;
       }
       leaf evpn-cluster-id {
         type int32;
       }
       leaf evpn-local-chassis-ip {
         type string;
       }
       leaf evpn-local-chassis-system-id {
         type string;
       }
       leaf evpn-member-nums {
         type int32;
       }
       list event-history {
         leaf event-timestamp {
           type string;
         }
         leaf event-id {
           type string;
         }
         leaf event-action {
           type string;
         }
         leaf event-information {
           type string;
         }
       }
       list evpn-multi-chassis-member {
         leaf evpn-multi-chassis-member-ip {
           type string;
         }
         leaf evpn-multi-chassis-member-state {
           type string;
         }
         leaf evpn-multi-chassis-member-chassis-id {
           type string;
         }
         leaf evpn-multi-chassis-member-system-id {
           type string;
         }
         leaf evpn-multi-chassis-member-device-total {
           type string;
         }
         leaf evpn-multi-chassis-member-device-online {
           type string;
         }
         list event-history {
           leaf event-timestamp {
             type string;
           }
           leaf event-id {
             type string;
           }
           leaf event-action {
             type string;
           }
           leaf event-information {
             type string;
           }
         }
         list evpn-multi-chassis-cluster-device {
           leaf slot-id {
             type int32;
           }
           leaf evpn-device-state {
             type string;
           }
           leaf evpn-device-ep-total {
             type string;
           }
           leaf evpn-device-ep-online {
             type string;
           }
           list event-history {
             leaf event-timestamp {
               type string;
             }
             leaf event-id {
               type string;
             }
             leaf event-action {
               type string;
             }
             leaf event-information {
               type string;
             }
           }
         }
       }
     }
   }
   grouping multi-chassis-cluster-device-information-block {
     list multi-chassis-cluster-device {
       leaf multi-chassis-cluster-name {
         type string;
       }
       leaf slot-id {
         type int32;
       }
       leaf local-state {
         type string;
       }
       leaf peer-state {
         type string;
       }
       leaf out-of-sync-cause {
         type string;
       }
       list event-history {
         leaf event-timestamp {
           type string;
         }
         leaf event-id {
           type string;
         }
         leaf event-action {
           type string;
         }
         leaf event-information {
           type string;
         }
       }
     }
     list evpn-multi-chassis-cluster-device {
       leaf slot-id {
         type int32;
       }
       leaf evpn-member {
         type string;
       }
       leaf evpn-device-state {
         type string;
       }
       leaf evpn-device-ep-total {
         type string;
       }
       leaf evpn-device-ep-online {
         type string;
       }
       list event-history {
         leaf event-timestamp {
           type string;
         }
         leaf event-id {
           type string;
         }
         leaf event-action {
           type string;
         }
         leaf event-information {
           type string;
         }
       }
     }
   }
   grouping multi-chassis-cluster-interface-information-block {
     list evpn-multi-chassis-cluster-ae-interface {
       leaf evpn-ae-interface-name {
         type string;
       }
       leaf evpn-ae-link {
         type string;
       }
       leaf evpn-ae-lacp {
         type string;
       }
       list evpn-multi-chassis-cluster-ae-member {
         leaf evpn-ae-member-name {
           type string;
         }
         leaf evpn-ae-member-link {
           type string;
         }
       }
       list event-history {
         leaf event-timestamp {
           type string;
         }
         leaf event-id {
           type string;
         }
         leaf event-action {
           type string;
         }
         leaf event-information {
           type string;
         }
       }
     }
     list evpn-multi-chassis-cluster-interface {
       leaf evpn-interface-name {
         type string;
       }
       leaf evpn-member {
         type string;
       }
       leaf evpn-link {
         type string;
       }
       leaf evpn-ae-id {
         type int32;
       }
       leaf evpn-interface-state {
         type string;
       }
       list event-history {
         leaf event-timestamp {
           type string;
         }
         leaf event-id {
           type string;
         }
         leaf event-action {
           type string;
         }
         leaf event-information {
           type string;
         }
       }
     }
   }
   grouping extended-port-information-block {
     list extended-port {
       leaf extended-port-name {
         type string;
       }
       leaf extended-port-state {
         type string;
       }
       leaf recv-request-state {
         type string;
       }
       leaf sent-request-state {
         type string;
       }
       leaf admin-state {
         type string;
       }
       leaf operation-state {
         type string;
       }
       leaf interface-index {
         type int32;
       }
       leaf port-channel-id {
         type int32;
       }
       list event-history {
         leaf event-timestamp {
           type string;
         }
         leaf event-id {
           type string;
         }
         leaf event-action {
           type string;
         }
         leaf event-information {
           type string;
         }
       }
     }
   }
   grouping upgrade-group-information-block {
     list upgrade-group {
       leaf group-name {
         type string;
       }
       leaf version {
         type string;
       }
       leaf state {
         type string;
       }
       list upgrade-group-satellite-information {
         leaf slot-id {
           type int32;
         }
         leaf upgrade-group-satellite-state {
           type string;
         }
       }
       leaf previous-version {
         type string;
       }
       leaf force-host {
         type string;
       }
     }
   }
   grouping adjacency-information-block {
     list adjacency-entry {
       leaf interface-name {
         type string;
       }
       leaf protocol-state {
         type string;
       }
       leaf port-information {
         type string;
       }
       leaf system-name {
         type string;
       }
       leaf product-model {
         type string;
       }
       leaf version {
         type string;
       }
       container adjacency-peer-entry {
         leaf up-down-transition-count {
           type string;
         }
         leaf last-transition {
           type string;
         }
         leaf serial-number {
           type string;
         }
         leaf chassis-id {
           type string;
         }
         leaf product-family {
           type string;
         }
         leaf version-seq-number {
           type int32;
         }
         leaf system-description {
           type string;
         }
       }
       container link-keepalive {
         leaf hello-interval {
           type int32;
         }
         leaf satellite-hello-interval {
           type int32;
         }
       }
       list adjacency-down-history {
         leaf down-cause {
           type string;
         }
         leaf down-timestamp {
           type string;
         }
         leaf down-information {
           type string;
         }
       }
       list local-assigned-primary-address {
         leaf local-end-address {
           type string;
         }
         leaf remote-end-address {
           type string;
         }
       }
       list event-history {
         leaf event-timestamp {
           type string;
         }
         leaf event-id {
           type string;
         }
         leaf event-action {
           type string;
         }
         leaf event-information {
           type string;
         }
       }
     }
   }
   grouping adjacency-statistics-block {
     container adjacency-statistics-entry {
       leaf interface-name {
         type string;
       }
       list interface-statistics {
         leaf message-statistics-name {
           type string;
         }
         leaf message-received-count {
           type int32;
         }
         leaf message-sent-count {
           type int32;
         }
         leaf message-error-count {
           type int32;
         }
       }
       list general-statistics {
         leaf statistics-name {
           type string;
         }
         leaf count {
           type int32;
         }
       }
     }
   }
   grouping satellite-interface-information-block {
     list interface-entry {
       leaf interface-name {
         type string;
       }
       leaf interface-state {
         type string;
       }
       leaf interface-type {
         type string;
       }
       leaf interface-df-role {
         type string;
       }
       leaf interface-df-address {
         type string;
       }
       list operation-address-list {
         leaf address {
           type string;
         }
       }
       list event-history {
         leaf event-timestamp {
           type string;
         }
         leaf event-id {
           type string;
         }
         leaf event-action {
           type string;
         }
         leaf event-information {
           type string;
         }
       }
     }
   }
   grouping satellite-software-information-block {
     list satellite-package {
       leaf version {
         type string;
       }
       leaf package-targets {
         type string;
       }
       leaf group-name {
         type string;
       }
       list package-platform {
         leaf product-family {
           type string;
         }
         leaf host-sw-version {
           type string;
         }
         list model-list {
           leaf product-model {
             type string;
           }
         }
       }
       leaf previous-group-name {
         type string;
       }
     }
   }
   grouping satellite-cluster-information-block {
     list satellite-cluster {
       list cluster-info {
         leaf cluster-name {
           type string;
         }
         leaf number-of-dev-provisioned {
           type int32;
         }
         leaf number-of-dev-present {
           type int32;
         }
         leaf number-of-dev-online {
           type int32;
         }
         leaf number-of-dev-unprovisioned {
           type int32;
         }
         leaf number-of-dev-misconfig {
           type int32;
         }
         leaf number-of-dev-offline {
           type int32;
         }
       }
       list cluster-device-info {
         leaf slot-id {
           type int32;
         }
         leaf operation-state {
           type string;
         }
         container transit-slot {
           leaf distance {
             type int32;
           }
           leaf transit-slot-id {
             type string;
           }
         }
         list cluster-connectivity {
           leaf interface-name {
             type string;
           }
           leaf peer-interface-name {
             type string;
           }
           leaf interface-state {
             type string;
           }
           leaf up-down-transition-count {
             type string;
           }
           leaf last-transition {
             type string;
           }
         }
       }
       list event-history {
         leaf event-timestamp {
           type string;
         }
         leaf event-id {
           type string;
         }
         leaf event-action {
           type string;
         }
         leaf event-information {
           type string;
         }
       }
     }
   }
   grouping chassis-pic-mode-information-block {
     leaf chassis-pic-mode {
       type string;
       description
         "Pic Mode";
     }
   }
 }
