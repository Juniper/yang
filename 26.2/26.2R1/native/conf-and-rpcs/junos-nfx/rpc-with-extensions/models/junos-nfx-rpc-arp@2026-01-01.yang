/*
 * Copyright (c) 2026 Juniper Networks, Inc.
 * All rights reserved.
 */
 module junos-nfx-rpc-arp {
   namespace "http://yang.juniper.net/junos-nfx/rpc/arp";

   prefix arp;

   import junos-common-ddl-extensions {
     prefix junos;
     revision-date 2026-01-01;
   }

   import junos-common-types {
     prefix jt;
     revision-date 2026-01-01;
   }

   organization "Juniper Networks, Inc.";

   contact "yang-support@juniper.net";

   description "Junos RPC YANG module for arp command(s)";

   revision 2026-01-01 {
     description "Junos: 26.2R1.7";
   }

   rpc get-arp-table-information {
     description "Show system Address Resolution Protocol table entries";
     junos:command "show arp";
     input {
       uses command-forwarding;
       leaf hostname {
         description "Name of host";
         type string;
       }
       leaf interface {
         description "Name of the interface";
         type string;
       }
       leaf no-resolve {
         description "Don't attempt to print addresses symbolically";
         type empty;
       }
       leaf expiration-time {
         description "Show seconds remaining before expiration";
         type empty;
       }
       leaf vpn {
         description "Name of VPN routing table";
         type string;
       }
       leaf reference-count {
         description "Next hop reference count";
         type empty;
       }
       leaf state {
         description "Next hop current state";
         type empty;
       }
     }
     output {
       choice output-tags {
         case actual-tag {
           container arp-table-information {
             uses arp-table-information-block;
           }
         }
         case multichassis-tag {
           container multi-routing-engine-results {
             list multi-routing-engine-item {
               leaf re-name {
                 type string;
               }
               choice output-tags {
                 case actual-tag {
                   container arp-table-information {
                     uses arp-table-information-block;
                   }
                 }
               }
             }
           }
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping arp-table-information-block {
     leaf arp-entry-count {
       type int32;
       description
         "Total number of ARP table entries";
     }
     list arp-table-entry {
       key "mac-address ip-address";
       description
         "Information about an entry in the ARP table";
       leaf mac-address {
         type jt:mac-addr;
         description
           "Hardware MAC address associated with the ARP entry";
       }
       leaf ip-address {
         type jt:ipaddr;
         description
           "IP address of the ARP entry";
       }
       leaf hostname {
         type string;
         description
           "Resolved hostname of the ARP entry";
       }
       leaf interface-name {
         type string;
         description
           "Name of the interface associated with the ARP entry";
       }
       leaf time-to-expire {
         type string;
         description
           "Seconds remaining until the entry expires";
       }
       leaf state {
         type string;
         description
           "Next hop current state";
       }
       leaf reference-count {
         type int32;
         description
           "Next hop reference count";
       }
       container arp-table-entry-flags {
         description
           "One or more status flags for the ARP entry";
         leaf none {
           type empty;
           description
             "ARP entry has no flags";
         }
         leaf permanent {
           type empty;
           description
             "ARP entry is permanent";
         }
         leaf published {
           type empty;
           description
             "ARP entry is published";
         }
         leaf dead {
           type empty;
           description
             "ARP entry is dead";
         }
         leaf free {
           type empty;
           description
             "ARP entry is free";
         }
         leaf virtual-gateway-address {
           type empty;
           description
             "ARP entry is for virtual gateway address";
         }
         leaf remotely-learnt-address {
           type empty;
           description
             "ARP entry learnt from remote and installed by protocol";
         }
         leaf flood-as-unknown-unicast {
           type empty;
           description
             "ARP entry to be flooded as unknown unicast traffic";
         }
       }
     }
   }
 }
