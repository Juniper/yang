/*
 * Copyright (c) 2026 Juniper Networks, Inc.
 * All rights reserved.
 */
 module junos-nfx-rpc-lldp {
   namespace "http://yang.juniper.net/junos-nfx/rpc/lldp";

   prefix lldp;

   import junos-common-ddl-extensions {
     prefix junos;
     revision-date 2026-01-01;
   }

   import junos-common-types {
     prefix jt;
     revision-date 2026-01-01;
   }

   organization "Juniper Networks, Inc.";

   contact "yang-support@juniper.net";

   description "Junos RPC YANG module for lldp command(s)";

   revision 2026-01-01 {
     description "Junos: 26.2R1.7";
   }

   rpc get-lldp-information {
     description "Show Link Layer Discovery Protocol information";
     junos:command "show lldp";
     output {
       choice output-tags {
         case actual-tag {
           container lldp {
             uses lldp-block;
           }
         }
         case multichassis-tag {
           container multi-routing-engine-results {
             list multi-routing-engine-item {
               leaf re-name {
                 type string;
               }
               choice output-tags {
                 case actual-tag {
                   container lldp {
                     uses lldp-block;
                   }
                 }
               }
             }
           }
         }
       }
     }
   }
   rpc get-lldp-information-detail {
     description "Show detailed LLDP information";
     junos:command "show lldp detail";
     output {
       choice output-tags {
         case actual-tag {
           container lldp {
             uses lldp-block;
           }
         }
         case multichassis-tag {
           container multi-routing-engine-results {
             list multi-routing-engine-item {
               leaf re-name {
                 type string;
               }
               choice output-tags {
                 case actual-tag {
                   container lldp {
                     uses lldp-block;
                   }
                 }
               }
             }
           }
         }
       }
     }
   }
   rpc get-lldp-neighbors-information {
     description "Show LLDP neighbor information";
     junos:command "show lldp neighbors";
     output {
       choice output-tags {
         case actual-tag {
           container lldp-neighbors-information {
             uses lldp-neighbors-information-block;
           }
         }
         case multichassis-tag {
           container multi-routing-engine-results {
             list multi-routing-engine-item {
               leaf re-name {
                 type string;
               }
               choice output-tags {
                 case actual-tag {
                   container lldp-neighbors-information {
                     uses lldp-neighbors-information-block;
                   }
                 }
               }
             }
           }
         }
       }
     }
   }
   rpc get-lldp-interface-neighbors {
     description "Show LLDP neighbors on this interface";
     junos:command "show lldp neighbors interface";
     input {
       leaf interface-device {
         description "Name of interface";
         junos:cli-feature "nokeyword";
         type union {
           type jt:interface-device;
           type string {
             pattern "<.*>|$.*";
           }
         }
       }
     }
     output {
       choice output-tags {
         case actual-tag {
           container lldp-neighbors-information {
             uses lldp-neighbors-information-block;
           }
         }
         case multichassis-tag {
           container multi-routing-engine-results {
             list multi-routing-engine-item {
               leaf re-name {
                 type string;
               }
               choice output-tags {
                 case actual-tag {
                   container lldp-neighbors-information {
                     uses lldp-neighbors-information-block;
                   }
                 }
               }
             }
           }
         }
       }
     }
   }
   rpc get-lldp-neighbor-detail-information {
     description "Show detailed LLDP neighbor information";
     junos:command "show lldp neighbors detail";
     output {
       choice output-tags {
         case actual-tag {
           container lldp-neighbors-information {
             uses lldp-neighbors-information-block;
           }
         }
         case multichassis-tag {
           container multi-routing-engine-results {
             list multi-routing-engine-item {
               leaf re-name {
                 type string;
               }
               choice output-tags {
                 case actual-tag {
                   container lldp-neighbors-information {
                     uses lldp-neighbors-information-block;
                   }
                 }
               }
             }
           }
         }
       }
     }
   }
   rpc get-lldp-neighbors-vlan-name-tlv-list {
     description " Show Vlan name TLVs received from LLDP neighbor";
     junos:command "show lldp neighbors-vlan-name-tlv-list";
     input {
       leaf interface {
         description "Display vlan name tlvs received on this interface from LLDP neighbor";
         type union {
           type jt:interface-device;
           type string {
             pattern "<.*>|$.*";
           }
         }
       }
     }
     output {
       choice output-tags {
         case actual-tag {
           container lldp-neighbors-vlan-name-tlv-list {
             uses lldp-neighbors-vlan-name-tlv-list-block;
           }
         }
         case multichassis-tag {
           container multi-routing-engine-results {
             list multi-routing-engine-item {
               leaf re-name {
                 type string;
               }
               choice output-tags {
                 case actual-tag {
                   container lldp-neighbors-vlan-name-tlv-list {
                     uses lldp-neighbors-vlan-name-tlv-list-block;
                   }
                 }
               }
             }
           }
         }
       }
     }
   }
   rpc get-lldp-statistics-information {
     description "Show LLDP statistics";
     junos:command "show lldp statistics";
     output {
       choice output-tags {
         case actual-tag {
           container lldp-statistics {
             uses lldp-statistics-block;
           }
         }
         case multichassis-tag {
           container multi-routing-engine-results {
             list multi-routing-engine-item {
               leaf re-name {
                 type string;
               }
               choice output-tags {
                 case actual-tag {
                   container lldp-statistics {
                     uses lldp-statistics-block;
                   }
                 }
               }
             }
           }
         }
       }
     }
   }
   rpc get-lldp-interface-statistics {
     description "Show LLDP statistics for this interface";
     junos:command "show lldp statistics interface";
     input {
       leaf interface-device {
         description "Show LLDP statistics for this interface";
         junos:cli-feature "nokeyword";
         type union {
           type jt:interface-device;
           type string {
             pattern "<.*>|$.*";
           }
         }
       }
     }
     output {
       choice output-tags {
         case actual-tag {
           container lldp-statistics {
             uses lldp-statistics-block;
           }
         }
         case multichassis-tag {
           container multi-routing-engine-results {
             list multi-routing-engine-item {
               leaf re-name {
                 type string;
               }
               choice output-tags {
                 case actual-tag {
                   container lldp-statistics {
                     uses lldp-statistics-block;
                   }
                 }
               }
             }
           }
         }
       }
     }
   }
   rpc get-lldp-local-info {
     description "Show LLDP information of local device";
     junos:command "show lldp local-information";
     input {
       leaf interface {
         description "Show LLDP local information of interface";
         type union {
           type jt:interface-device;
           type string {
             pattern "<.*>|$.*";
           }
         }
       }
     }
     output {
       choice output-tags {
         case actual-tag {
           container lldp-local-info {
             uses lldp-local-info-block;
           }
         }
         case multichassis-tag {
           container multi-routing-engine-results {
             list multi-routing-engine-item {
               leaf re-name {
                 type string;
               }
               choice output-tags {
                 case actual-tag {
                   container lldp-local-info {
                     uses lldp-local-info-block;
                   }
                 }
               }
             }
           }
         }
       }
     }
   }
   rpc get-lldp-remote-global-statistics {
     description "Show LLDP remote global statistics information";
     junos:command "show lldp remote-global-statistics";
     output {
       choice output-tags {
         case actual-tag {
           container lldp-remote-global-statistics {
             uses lldp-remote-global-statistics-block;
           }
         }
         case multichassis-tag {
           container multi-routing-engine-results {
             list multi-routing-engine-item {
               leaf re-name {
                 type string;
               }
               choice output-tags {
                 case actual-tag {
                   container lldp-remote-global-statistics {
                     uses lldp-remote-global-statistics-block;
                   }
                 }
               }
             }
           }
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping lldp-block {
     leaf lldp-global-status {
       type string;
       description
         "Global administration status";
     }
     leaf lldp-advertisement-interval {
       type uint32;
       description
         "Advertisement interval";
     }
     leaf lldp-transmit-delay-interval {
       type uint32;
       description
         "Transmit delay interval";
     }
     leaf lldp-hold-time-interval {
       type uint32;
       description
         "Hold time interval";
     }
     leaf lldp-notification-interval {
       type uint32;
       description
         "LLDP notification interval";
     }
     leaf lldp-tx-fast-init {
       type uint32;
       description
         "LLDP Tx Fast Init";
     }
     leaf ptopo-configuration-trap-interval {
       type uint32;
       description
         "Physical topology configuration change trap interval";
     }
     leaf ptopo-maximum-hold-time {
       type uint32;
       description
         "Physical topology connections maximum hold time interval";
     }
     leaf lldp-med-global-status {
       type string;
       description
         "LLDP-MED administrative status";
     }
     leaf lldp-med-fast-start-count {
       type uint32;
       description
         "Fast-start count for LLDP-MED";
     }
     leaf lldp-port-id-subtype {
       type string;
       description
         "Sub-type to be used for Port ID TLV generation";
     }
     leaf lldp-port-description-type {
       type string;
       description
         "The Interfaces Group MIB object to be used for Port Description 
         TLV generation";
     }
     leaf lldp-selected-management-interface {
       type string;
       description
         "Selected management-interface name";
     }
     leaf lldp-configured-management-interface {
       type string;
       description
         "Configured management-interface name";
     }
     leaf lldp-tlv-select {
       type string;
       description
         "LLDP tlv-select";
     }
     leaf lldp-tlv-filter {
       type string;
       description
         "LLDP tlv-filter";
     }
     leaf lldp-med-tlv-select {
       type string;
       description
         "LLDP-MED tlv-select";
     }
     leaf lldp-med-tlv-filter {
       type string;
       description
         "LLDP-MED tlv-filter";
     }
     list lldp-interface-information {
       key "lldp-interface-name";
       leaf lldp-interface-name {
         type string;
         description
           "Interface name";
       }
       leaf lldp-parent-interface-name {
         type string;
         description
           "Parent interface name";
       }
       leaf lldp-interface-status {
         type string;
         description
           "Per interface administrative status for basic LLDP";
       }
       leaf lldp-med-interface-status {
         type string;
         description
           "Per interface administrative status for LLDP-MED";
       }
       leaf lldp-interface-power-negotiation-status {
         type string;
         description
           "Per interface power negotiation status for LLDP";
       }
       leaf lldp-interface-neighbor-count {
         type uint32;
         description
           "Number of neighbors on this interface";
       }
       leaf lldp-interface-dest-mac {
         type string;
         description
           "Per interface LLDP PDU dest MAC address";
       }
     }
     leaf lldp-basic-tlv-supported {
       type string;
     }
     leaf lldp-802-tlv-supported {
       type string;
     }
     leaf lldp-med-tlv-supported {
       type string;
     }
     list lldp-exported-vlan-information {
       key "lldp-vlan-interface-name";
       leaf lldp-vlan-interface-name {
         type string;
         description
           "VLAN interface name";
       }
       leaf lldp-vlan-parent-interface-name {
         type string;
         description
           "Parent interface name of VLAN interface";
       }
       leaf lldp-vlan-tag {
         type uint32;
         description
           "VLAN tag";
       }
       leaf lldp-vlan-name {
         type string;
         description
           "VLAN name";
       }
     }
   }
   grouping lldp-neighbors-information-block {
     list lldp-neighbor-information {
       key "lldp-local-interface";
       leaf lldp-local-interface {
         type string;
         description
           "Interface on which neighbor information was received";
       }
       leaf lldp-index {
         type uint32;
         description
           "LLDP index";
       }
       leaf lldp-ttl {
         type uint32;
         description
           "How long until the neighbor record expired";
       }
       leaf lldp-timemark {
         type string;
         description
           "When neighbor information was received";
       }
       leaf lldp-age {
         type uint32;
         description
           "Age of record";
       }
       leaf lldp-local-parent-interface-name {
         type string;
         description
           "Parent interface of local interface on which neighbor 
           informationwas received";
       }
       leaf lldp-local-port-id {
         type string;
         description
           "Port on which neighbor information was received";
       }
       leaf lldp-local-port-ageout-count {
         type uint32;
         description
           "Number of age-outs that occured on a given port";
       }
       leaf lldp-remote-chassis-id-subtype {
         type string;
         description
           "LLDP remote chassis ID subtype";
       }
       leaf lldp-remote-chassis-id {
         type string;
         description
           "LLDP remote chassis ID";
       }
       leaf lldp-remote-port-id-subtype {
         type string;
         description
           "LLDP remote port ID subtype";
       }
       leaf lldp-remote-port-id {
         type string;
         description
           "LLDP remote port ID";
       }
       leaf lldp-remote-port-description {
         type string;
         description
           "LLDP remote port ID";
       }
       leaf lldp-remote-system-name {
         type string;
         description
           "Administratively assigned host name of remote neighbor";
       }
       leaf lldp-remote-system-capabilities-supported {
         type string;
       }
       leaf lldp-remote-system-capabilities-enabled {
         type string;
       }
       leaf lldp-remote-inventory-hardware-revision {
         type string;
       }
       leaf lldp-remote-inventory-firmware-revision {
         type string;
       }
       leaf lldp-remote-inventory-software-revision {
         type string;
       }
       leaf lldp-remote-inventory-serial-number {
         type string;
       }
       leaf lldp-remote-inventory-manufacturer-name {
         type string;
       }
       leaf lldp-remote-inventory-model-name {
         type string;
       }
       leaf lldp-remote-inventory-asset-id {
         type string;
       }
       leaf lldp-remote-inventory-network-policy {
         type string;
       }
       leaf lldp-med-remote-system-class {
         type string;
         description
           "LLDP remote MED system class";
       }
       container lldp-system-description {
         leaf lldp-remote-system-description {
           type string;
           description
             "System information";
         }
       }
       list lldp-remote-management-address-info {
         key "lldp-remote-management-address";
         leaf lldp-remote-management-address-type {
           type string;
           description
             "Management address for use by SNMP manager query";
         }
         leaf lldp-remote-management-address {
           type string;
           description
             "Management address for use by SNMP manager query";
         }
         leaf lldp-remote-management-address-port-id {
           type uint32;
           description
             "Port ID of Management address for use by SNMP manager query";
         }
         leaf lldp-remote-management-address-interface-subtype {
           type string;
           description
             "Enumeration value that identifies the interface numbering 
             method used for defining the interface number associated with 
             the remote system";
         }
         leaf lldp-remote-management-addr-oid {
           type string;
           description
             "LLDP OID value advertised by the remote system";
         }
         leaf lldp-remote-management-address-sub-type {
           type uint32;
           description
             "LLDP remote system management address Subtype";
         }
       }
       list lldp-org-specific-tlv {
         key "lldp-remote-index";
         leaf lldp-remote-oui-802-3 {
           type string;
           description
             "Organizationally Unique Identifier globally unique assigned  
             number of IEEE 802.3 information received from the remote 
             system";
         }
         leaf lldp-remote-oui-802-1 {
           type string;
           description
             "Organizationally Unique Identifier globally unique assigned  
             number of IEEE 802.1 information received from the remote 
             system";
         }
         leaf lldp-remote-org-def-info-oui {
           type string;
           description
             "Organizationally Unique Identifier globally unique 
             assignednumber of the information received from the remote 
             system";
         }
         leaf lldp-remote-oui-juniper {
           type string;
           description
             "Juniper specific information received from the remote system";
         }
         leaf lldp-remote-oui-tia {
           type string;
           description
             "Organizationally Unique Identifier globally unique assigned  
             number of TIA TR-41 committee information received from the 
             remote system";
         }
         leaf lldp-remote-subtype {
           type uint32;
           description
             "Subtype of the organizationally defined information received 
             from the remote system";
         }
         leaf lldp-remote-subtype-vlan {
           type uint32;
           description
             "Subtype of the IEEE 802.1 VLAN name organizationally 
             definedinformation received from the remote system";
         }
         leaf lldp-remote-subtype-port-vid {
           type uint32;
           description
             "Subtype of the IEEE 802.1 VLAN id organizationally 
             definedinformation received from the remote system";
         }
         leaf lldp-remote-subtype-port-protocol-vid {
           type uint32;
           description
             "Subtype of the IEEE 802.1 VLAN id organizationally 
             definedinformation received from the remote system";
         }
         leaf lldp-remote-subtype-protocol-id {
           type uint32;
           description
             "Subtype of the IEEE 802.1 VLAN id organizationally 
             definedinformation received from the remote system";
         }
         leaf lldp-remote-subtype-link-aggregation-8021 {
           type uint32;
           description
             "Subtype of the IEEE 802.1 Link Aggregation 
             organizationallydefined information received from the remote 
             system";
         }
         leaf lldp-remote-subtype-mac {
           type uint32;
           description
             "Subtype of the IEEE 802.3 MAC/PHY 
             configuration/statusorganizationally defined information 
             received from the remote system";
         }
         leaf lldp-remote-subtype-lag {
           type uint32;
           description
             "Subtype of the IEEE 802.3 Link Aggregation 
             organizationallydefined information received from the remote 
             system";
         }
         leaf lldp-remote-subtype-mdi-power {
           type uint32;
           description
             "Subtype of the IEEE 802.3 MDI Power organizationallydefined 
             information received from the remote system";
         }
         leaf lldp-remote-subtype-serial {
           type uint32;
           description
             "Subtype of the Juniper specific information received from the 
             remote system";
         }
         leaf lldp-remote-subtype-vcp {
           type uint32;
           description
             "Subtype of the Juniper specific information received from the 
             remote system";
         }
         leaf lldp-remote-subtype-cloud-reach-event {
           type uint32;
           description
             "Subtype of the Juniper specific information receivedfrom the 
             remote system";
         }
         leaf lldp-remote-subtype-phone-home-active {
           type uint32;
           description
             "Subtype of the Juniper specific information receivedfrom the 
             remote system";
         }
         leaf lldp-remote-subtype-cloud-connect-event {
           type uint32;
           description
             "Subtype of the Juniper specific information receivedfrom the 
             remote system";
         }
         leaf lldp-remote-subtype-uap-enabled {
           type uint32;
           description
             "Subtype of the Juniper specific information receivedfrom the 
             remote system";
         }
         leaf lldp-remote-subtype-mtu {
           type uint32;
           description
             "Subtype of the IEEE 802.3 Maximum Frame Size 
             organizationallydefined information received from the remote 
             system";
         }
         leaf lldp-remote-index {
           type uint32;
           description
             "Value used by agent to identify a particular unrecognized 
             organizationally defined information";
         }
         leaf lldp-remote-value {
           type string;
           description
             "Value used to identify the organizationally defined 
             information of the remote system";
         }
         leaf lldp-remote-subtype-vlan-id {
           type uint32;
           description
             "IEEE 802.1 VLAN name subtype VLAN ID value of 
             theorganizationally defined information received from the 
             remote system";
         }
         leaf lldp-remote-subtype-vlan-name {
           type string;
           description
             "IEEE 802.1 VLAN name subtype VLAN name value of 
             theorganizationally defined information received from the 
             remote system";
         }
         leaf lldp-remote-subtype-link-aggregation-8021-status {
           type string;
           description
             "IEEE 802.1 Link Aggregation subtype status value 
             oforganizationally defined information received from the 
             remote system";
         }
         leaf lldp-remote-subtype-link-aggregation-8021-portid {
           type uint32;
           description
             "IEEE 802.1 Link Aggregation subtype aggregated port ID valueof
             organizationally defined information received from the remote 
             system";
         }
         leaf lldp-remote-subtype-mac-autonegotiation {
           type string;
           description
             "IEEE 802.3 MAC/PHY configuration/status subtype 
             autonegotiationsupport/status value of organizationally 
             defined information receivedfrom the remote system";
         }
         leaf lldp-remote-subtype-mac-pmd {
           type string;
           description
             "IEEE 802.3 MAC/PHY configuration/status subtype 
             PMDautonegotiation advertised capability value of 
             organizationally definedinformation received from the remote 
             system";
         }
         leaf lldp-remote-subtype-mac-mau {
           type uint32;
           description
             "IEEE 802.3 MAC/PHY configuration/status subtype operational 
             MAUtype value of organizationally defined information received
             from theremote system";
         }
         leaf lldp-remote-subtype-power-support {
           type string;
           description
             "Subtype of the IEEE 802.3 MDI Power support 
             organizationallydefined information received from the remote 
             system";
         }
         leaf lldp-remote-subtype-power-pair {
           type string;
           description
             "Subtype of the IEEE 802.3 MDI Power pair 
             organizationallyeefined information received from the remote 
             system";
         }
         leaf lldp-remote-subtype-power-class {
           type string;
           description
             "Subtype of the IEEE 802.3 MDI Power class 
             organizationallydefined information received from the remote 
             system";
         }
         leaf lldp-remote-subtype-slot-serial {
           type string;
           description
             "Juniper specific ifl slot serial information receivedfrom the 
             remote system";
         }
         leaf lldp-remote-subtype-cloud-reach-event-info {
           type string;
           description
             "Juniper specific cloud reachability event information 
             receivedfrom the remote system";
         }
         leaf lldp-remote-subtype-phone-home-active-info {
           type string;
           description
             "Juniper specific phone home activity information receivedfrom 
             the remote system";
         }
         leaf lldp-remote-subtype-cloud-connect-event-info {
           type string;
           description
             "Juniper specific cloud connectivity event information 
             receivedfrom the remote system";
         }
         leaf lldp-remote-cc-state {
           type uint32;
           description
             "CC state of the Juniper specific information receivedfrom the 
             remote system";
         }
         leaf lldp-remote-cc-error-code {
           type uint32;
           description
             "Error code of the Juniper specific information receivedfrom 
             the remote system";
         }
         leaf lldp-remote-subtype-uap-enabled-info {
           type string;
           description
             "Juniper specific uap enabled information receivedfrom the 
             remote system";
         }
         leaf lldp-remote-subtype-vcp-info {
           type string;
           description
             "Juniper specific ifl vcp information receivedfrom the remote 
             system";
         }
         leaf lldp-remote-subtype-juniper-mode-change {
           type uint32;
           description
             "Juniper specific ifl slot serial information receivedfrom the 
             remote system";
         }
         leaf lldp-remote-subtype-juniper-mode-change-error {
           type uint32;
           description
             "Juniper specific ifl slot serial information receivedfrom the 
             remote system";
         }
         leaf lldp-remote-subtype-juniper-mode-change-ip-address {
           type uint32;
           description
             "Juniper specific ifl slot serial information receivedfrom the 
             remote system";
         }
         leaf lldp-remote-subtype-juniper-mode-change-image-name {
           type uint32;
           description
             "Juniper specific ifl slot serial information receivedfrom the 
             remote system";
         }
         leaf lldp-remote-subtype-juniper-mode-change-ftp-login {
           type uint32;
           description
             "Juniper specific ifl slot serial information receivedfrom the 
             remote system";
         }
         leaf lldp-remote-subtype-juniper-mode-change-image-md5 {
           type uint32;
           description
             "Juniper specific ifl slot serial information receivedfrom the 
             remote system";
         }
         leaf lldp-remote-subtype-lag-status {
           type string;
           description
             "IEEE 802.3 Link Aggregation subtype status value 
             oforganizationally defined information received from the 
             remote system";
         }
         leaf lldp-remote-subtype-lag-portid {
           type uint32;
           description
             "IEEE 802.3 Link Aggregation subtype aggregated port ID value 
             oforganizationally defined information received from the 
             remote system";
         }
         leaf lldp-remote-subtype-mtu-size {
           type uint32;
           description
             "IEEE 802.3 Maximum Frame Size subtype frame size value 
             oforganizationally defined information received from the 
             remote system";
         }
         leaf lldp-med-remote-application-attributes {
           type string;
           description
             "Application which MED runs and its configuration parameters";
         }
         leaf lldp-remote-subtype-med-capabilities {
           type string;
           description
             "Organizationally Unique Identifier globally unique assigned  
             number of TIA TR-41 committee information received from the 
             remote system";
         }
         leaf lldp-remote-subtype-med-cap-status {
           type string;
           description
             "Organizationally Unique Identifier globally unique assigned  
             number of TIA TR-41 committee information received from the 
             remote system";
         }
         leaf lldp-remote-subtype-med-class-type {
           type string;
           description
             "Organizationally Unique Identifier globally unique assigned  
             number of TIA TR-41 committee information received from the 
             remote system";
         }
         leaf lldp-remote-subtype-policy-type {
           type string;
           description
             "Organizationally Unique Identifier globally unique assigned  
             number of TIA TR-41 committee information received from the 
             remote system";
         }
         leaf lldp-remote-subtype-nw-app-type {
           type string;
           description
             "Organizationally Unique Identifier globally unique assigned  
             number of TIA TR-41 committee information received from the 
             remote system";
         }
         leaf lldp-remote-subtype-nw-policy-info {
           type string;
           description
             "Organizationally Unique Identifier globally unique assigned  
             number of TIA TR-41 committee information received from the 
             remote system";
         }
         leaf lldp-remote-subtype-loc-id-type {
           type string;
           description
             "Organizationally Unique Identifier globally unique assigned  
             number of TIA TR-41 committee information received from the 
             remote system";
         }
         leaf lldp-remote-subtype-loc-data-format {
           type string;
           description
             "Organizationally Unique Identifier globally unique assigned  
             number of TIA TR-41 committee information received from the 
             remote system";
         }
         leaf lldp-remote-subtype-loc-lci-len {
           type string;
           description
             "Organizationally Unique Identifier globally unique assigned  
             number of TIA TR-41 committee information received from the 
             remote system";
         }
         leaf lldp-remote-subtype-ext-power-vi-mdi {
           type string;
           description
             "Organizationally Unique Identifier globally unique assigned  
             number of TIA TR-41 committee information received from the 
             remote system";
         }
         leaf lldp-remote-subtype-med-power-type {
           type string;
           description
             "Organizationally Unique Identifier globally unique assigned  
             number of TIA TR-41 committee information received from the 
             remote system";
         }
         leaf lldp-remote-subtype-med-power-source {
           type string;
           description
             "Organizationally Unique Identifier globally unique assigned  
             number of TIA TR-41 committee information received from the 
             remote system";
         }
         leaf lldp-remote-subtype-med-power-priority {
           type string;
           description
             "Organizationally Unique Identifier globally unique assigned  
             number of TIA TR-41 committee information received from the 
             remote system";
         }
         leaf lldp-remote-subtype-med-power-value {
           type string;
           description
             "Organizationally Unique Identifier globally unique assigned  
             number of TIA TR-41 committee information received from the 
             remote system";
         }
         leaf lldp-remote-subtype-port-protocol-vid-status {
           type string;
           description
             "IEEE 802.1 VLAN name subtype VLAN name value of 
             theorganizationally defined information received from the 
             remote system";
         }
         leaf lldp-remote-subtype-port-protocol-vid-id {
           type string;
           description
             "IEEE 802.1 VLAN name subtype VLAN name value of 
             theorganizationally defined information received from the 
             remote system";
         }
         leaf lldp-remote-subtype-protocol-id-length {
           type string;
           description
             "IEEE 802.1 VLAN name subtype VLAN name value of 
             theorganizationally defined information received from the 
             remote system";
         }
       }
       list lldp-remote-unknown-tlv {
         key "lldp-remote-unknown-tlv-type";
         leaf lldp-remote-unknown-tlv-type {
           type uint32;
           description
             "Type extracted from the TLV";
         }
         leaf lldp-remote-unknown-tlv-info {
           type string;
           description
             "Value extracted from the value field of TLV";
         }
       }
       leaf lldp-remote-management-address-type {
         type string;
         description
           "Management address for use by SNMP manager query";
       }
       leaf lldp-remote-management-address {
         type string;
         description
           "Management address for use by SNMP manager query";
       }
       leaf lldp-remote-management-address-port-id {
         type uint32;
         description
           "Port ID of Management address for use by SNMP manager query";
       }
       leaf lldp-remote-management-address-sub-type {
         type uint32;
         description
           "LLDP remote system management address Subtype";
       }
       leaf lldp-remote-management-address-interface-subtype {
         type string;
         description
           "Enumeration value that identifies the interface numbering method
           used for defining the interface number associated with the 
           remote system";
       }
       leaf lldp-remote-management-addr-oid {
         type string;
         description
           "LLDP OID value advertised by the remote system";
       }
       leaf lldp-remote-oui-802-3 {
         type string;
         description
           "Organizationally Unique Identifier globally unique 
           assignednumber of IEEE 802.3 information received from the 
           remote system";
       }
       leaf lldp-remote-oui-802-1 {
         type string;
         description
           "Organizationally Unique Identifier globally unique 
           assignednumber of IEEE 802.1 information received from the 
           remote system";
       }
       leaf lldp-remote-oui-juniper {
         type string;
         description
           "Juniper specific information received from the remote system";
       }
       leaf lldp-remote-subtype {
         type uint32;
         description
           "Subtype of the organizationally defined information receivedfrom
           the remote system";
       }
       leaf lldp-remote-subtype-vlan {
         type uint32;
         description
           "Subtype of the IEEE 802.1 VLAN name organizationally 
           definedinformation received from the remote system";
       }
       leaf lldp-remote-subtype-port-vid {
         type uint32;
         description
           "Subtype of the IEEE 802.1 VLAN id organizationally 
           definedinformation received from the remote system";
       }
       leaf lldp-remote-subtype-mac {
         type uint32;
         description
           "Subtype of the IEEE 802.3 MAC/PHY 
           configuration/statusorganizationally defined information 
           received from the remote system";
       }
       leaf lldp-remote-subtype-lag {
         type uint32;
         description
           "Subtype of the IEEE 802.3 Link Aggregation 
           organizationallydefined information received from the remote 
           system";
       }
       leaf lldp-remote-subtype-mdi-power {
         type uint32;
         description
           "Subtype of the IEEE 802.3 MDI Power organizationallydefined 
           information received from the remote system";
       }
       leaf lldp-remote-subtype-serial {
         type uint32;
         description
           "Subtype of the Juniper specific information received from the 
           remote system";
       }
       leaf lldp-remote-subtype-vcp {
         type uint32;
         description
           "Subtype of the Juniper specific information received from the 
           remote system";
       }
       leaf lldp-remote-subtype-mtu {
         type uint32;
         description
           "Subtype of the IEEE 802.3 Maximum Frame Size 
           organizationallydefined information received from the remote 
           system";
       }
       leaf lldp-remote-index {
         type uint32;
         description
           "Value used by agent to identify a particular 
           unrecognizedorganizationally defined information";
       }
       leaf lldp-remote-value {
         type string;
         description
           "Value used to identify the organizationally defined 
           informationof the remote system";
       }
       leaf lldp-remote-subtype-vlan-id {
         type uint32;
         description
           "IEEE 802.1 VLAN name subtype VLAN ID value of 
           theorganizationally defined information received from the remote
           system";
       }
       leaf lldp-remote-subtype-vlan-name {
         type string;
         description
           "IEEE 802.1 VLAN name subtype VLAN name value of 
           theorganizationally defined information received from the remote
           system";
       }
       leaf lldp-remote-subtype-mac-autonegotiation {
         type string;
         description
           "IEEE 802.3 MAC/PHY configuration/status subtype 
           autonegotiationsupport/status value of organizationally defined 
           information receivedfrom the remote system";
       }
       leaf lldp-remote-subtype-mac-pmd {
         type string;
         description
           "IEEE 802.3 MAC/PHY configuration/status subtype 
           PMDautonegotiation advertised capability value of 
           organizationally definedinformation received from the remote 
           system";
       }
       leaf lldp-remote-subtype-mac-mau {
         type uint32;
         description
           "IEEE 802.3 MAC/PHY configuration/status subtype operational 
           MAUtype value of organizationally defined information received 
           from theremote system";
       }
       leaf lldp-remote-subtype-power-support {
         type string;
         description
           "Subtype of the IEEE 802.3 MDI Power support 
           organizationallydefined information received from the remote 
           system";
       }
       leaf lldp-remote-subtype-power-pair {
         type string;
         description
           "Subtype of the IEEE 802.3 MDI Power pair organizationallydefined
           information received from the remote system";
       }
       leaf lldp-remote-subtype-power-class {
         type string;
         description
           "Subtype of the IEEE 802.3 MDI Power class 
           organizationallydefined information received from the remote 
           system";
       }
       leaf lldp-remote-subtype-slot-serial {
         type string;
         description
           "Juniper specific ifl slot serial information receivedfrom the 
           remote system";
       }
       leaf lldp-remote-subtype-vcp-info {
         type string;
         description
           "Juniper specific ifl vcp information receivedfrom the remote 
           system";
       }
       leaf lldp-remote-subtype-lag-status {
         type string;
         description
           "IEEE 802.3 Link Aggregation subtype status value 
           oforganizationally defined information received from the remote 
           system";
       }
       leaf lldp-remote-subtype-lag-portid {
         type uint32;
         description
           "IEEE 802.3 Link Aggregation subtype aggregated port ID value 
           oforganizationally defined information received from the remote 
           system";
       }
       leaf lldp-remote-subtype-mtu-size {
         type uint32;
         description
           "IEEE 802.3 Maximum Frame Size subtype frame size value 
           oforganizationally defined information received from the remote 
           system";
       }
       leaf lldp-remote-unknown-tlv-type {
         type uint32;
         description
           "Type extracted from the TLV";
       }
       leaf lldp-remote-unknown-tlv-info {
         type string;
         description
           "Value extracted from the value field of TLV";
       }
       leaf lldp-remote-org-def-info-oui {
         type string;
         description
           "Organizationally Unique Identifier globally unique assigned  
           number of the information received from the remote system";
       }
       leaf lldp-remote-org-def-info-subtype {
         type uint32;
         description
           "Subtype of the organizationally defined information received 
           from the remote system";
       }
       leaf lldp-remote-org-def-info {
         type string;
         description
           "Value used to identify the organizationally defined information 
           of the remote system";
       }
       leaf lldp-med-remote-application-attributes {
         type string;
         description
           "Application which MED runs and its configuration parameters";
       }
     }
   }
   grouping lldp-neighbors-vlan-name-tlv-list-block {
     list lldp-interface-information-list {
       key "lldp-local-interface-name";
       leaf lldp-local-interface-name {
         type string;
       }
       list lldp-remote-interface-information {
         key "lldp-remote-chassis-id";
         leaf lldp-remote-chassis-id-subtype {
           type string;
           description
             "LLDP remote chassis ID subtype";
         }
         leaf lldp-remote-chassis-id {
           type string;
           description
             "LLDP remote chassis ID";
         }
         leaf lldp-remote-port-description {
           type string;
           description
             "LLDP remote port ID";
         }
         leaf lldp-remote-system-name {
           type string;
           description
             "Administratively assigned host name of remote neighbor";
         }
         leaf lldp-vlan-name-tlv-oui {
           type string;
           description
             "Organizationally Unique Identifier globally unique 
             assignednumber of the information received from the remote 
             system";
         }
         leaf lldp-vlan-name-tlv-subtype {
           type string;
           description
             "IEEE 802.1 VLAN name subtype VLAN name value of 
             theorganizationally defined information received from the 
             remote system";
         }
         list lldp-neighbor-vlan-name-tlv-list {
           key "lldp-vlan-name-tlv-name";
           leaf lldp-vlan-name-tlv-tag {
             type uint32;
             description
               "VLAN tag";
           }
           leaf lldp-vlan-name-tlv-name {
             type string;
             description
               "VLAN name";
           }
           leaf lldp-vlan-name-tlv-remote-index {
             type uint32;
             description
               "Value used by agent to identify a particular 
               unrecognizedorganizationally defined information";
           }
         }
       }
     }
   }
   grouping lldp-statistics-block {
     list lldp-interface-statistics {
       key "lldp-statistics-interface-name";
       description
         "Interface statistics";
       leaf lldp-statistics-interface-name {
         type string;
       }
       leaf lldp-parent-intf-name {
         type string;
         description
           "Parent interface for which statistics are shown";
       }
       leaf lldp-receive-packet-count {
         type uint32;
       }
       leaf lldp-receive-packet-unknown-tlvs {
         type uint32;
         description
           "Number of received LLDP packets with unknown TLVs";
       }
       leaf lldp-receive-packet-error-count {
         type uint32;
       }
       leaf lldp-receive-tlv-discard-count {
         type uint32;
       }
       leaf lldp-transmit-packet-count {
         type uint32;
       }
       leaf lldp-transmit-packet-error-count {
         type uint32;
       }
     }
   }
   grouping lldp-local-info-block {
     leaf lldp-local-chassis-id {
       type string;
     }
     leaf lldp-local-chassis-id-type {
       type string;
     }
     leaf lldp-local-system-name {
       type string;
     }
     leaf lldp-local-system-description {
       type string;
     }
     leaf lldp-local-system-capabilities-supported {
       type string;
       description
         "LLDP local system capabilities supported";
     }
     leaf lldp-local-system-capabilities-enabled {
       type string;
       description
         "LLDP local system capabilities enabled";
     }
     leaf lldp-local-redundancy-group-name {
       type string;
     }
     leaf lldp-local-redundancy-group-address {
       type string;
     }
     leaf lldp-local-cloud-reach-event {
       type string;
     }
     leaf lldp-local-phone-home-active {
       type string;
     }
     list lldp-local-interface-info {
       key "lldp-local-interface-name";
       leaf lldp-local-interface-name {
         type string;
       }
       leaf lldp-parent-local-interface-name {
         type string;
         description
           "Parent interface name of local interface";
       }
       leaf lldp-local-interface-id {
         type uint32;
       }
       leaf lldp-local-interface-description {
         type string;
       }
       leaf lldp-local-interface-status {
         type string;
         description
           "Interface status";
       }
       leaf lldp-tlv-select {
         type string;
         description
           "LLDP tlv-select";
       }
       leaf lldp-tlv-filter {
         type string;
         description
           "LLDP tlv-filter";
       }
       leaf lldp-med-tlv-select {
         type string;
         description
           "LLDP-MED tlv-select";
       }
       leaf lldp-med-tlv-filter {
         type string;
         description
           "LLDP-MED tlv-filter";
       }
       leaf lldp-local-interface-descr {
         type string;
         description
           "Interface description";
       }
       leaf lldp-local-interface-tunneling {
         type string;
         description
           "Tunneling enabled on that interface";
       }
     }
     list lldp-local-cloud-connect-info {
       key "cc-state";
       leaf cc-state {
         type uint32;
         description
           "Controller connectivity state";
       }
       leaf cc-message {
         type string;
         description
           "Controller connectivity state message";
       }
       leaf cc-errno {
         type uint32;
         description
           "Controller connectivity error code";
       }
     }
     list lldp-local-management-address-info {
       key "lldp-local-management-address-address";
       leaf lldp-local-management-address-interface-name {
         type string;
         description
           "LLDP local management interaface name";
       }
       leaf lldp-local-management-address-subtype {
         type string;
         description
           "LLDP local management interface address subtype ";
       }
       leaf lldp-local-management-address-address {
         type string;
         description
           "LLDP local management interface address ";
       }
       leaf lldp-local-management-address-interface-number-subtype {
         type string;
         description
           "LLDP local management interface number subtype";
       }
       leaf lldp-local-management-address-interface-number {
         type uint32;
         description
           "LLDP local management address interface number";
       }
     }
     leaf lldp-local-system-descr {
       type string;
     }
     leaf lldp-local-port-description {
       type string;
       description
         "LLDP local port description";
     }
     leaf lldp-local-management-address {
       type string;
       description
         "LLDP local management address";
     }
     leaf lldp-local-management-address-type {
       type string;
       description
         "LLDP local management address type";
     }
     leaf lldp-local-management-address-interface-id {
       type uint32;
       description
         "LLDP local management address interface id";
     }
     leaf lldp-local-port-id-sub-type {
       type uint32;
       description
         "LLDP local port id subtype ";
     }
     leaf lldp-local-management-address-interface-sub-type {
       type uint32;
       description
         "LLDP local management interface number";
     }
   }
   grouping lldp-remote-global-statistics-block {
     leaf lldp-last-change-time {
       type string;
       description
         "LLDP last change time";
     }
     leaf lldp-inserts {
       type uint32;
       description
         "LLDP inserts";
     }
     leaf lldp-deletes {
       type uint32;
       description
         "LLDP deletes";
     }
     leaf lldp-drops {
       type uint32;
       description
         "LLDP drops";
     }
     leaf lldp-ageouts {
       type uint32;
       description
         "LLDP ageouts";
     }
     list lldp-remote-global-stats {
       leaf lldp-last-change-time {
         type uint32;
         description
           "LLDP last change time";
       }
       leaf lldp-inserts {
         type uint32;
         description
           "LLDP inserts";
       }
       leaf lldp-deletes {
         type uint32;
         description
           "LLDP deletes";
       }
       leaf lldp-drops {
         type uint32;
         description
           "LLDP drops";
       }
       leaf lldp-ageouts {
         type uint32;
         description
           "LLDP ageouts";
       }
     }
   }
 }
