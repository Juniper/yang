/*
 * Copyright (c) 2026 Juniper Networks, Inc.
 * All rights reserved.
 */
 module junos-nfx-rpc-firewall {
   namespace "http://yang.juniper.net/junos-nfx/rpc/firewall";

   prefix firewall;

   import junos-common-ddl-extensions {
     prefix junos;
     revision-date 2026-01-01;
   }

   import junos-common-types {
     prefix jt;
     revision-date 2026-01-01;
   }

   organization "Juniper Networks, Inc.";

   contact "yang-support@juniper.net";

   description "Junos RPC YANG module for firewall command(s)";

   revision 2026-01-01 {
     description "Junos: 26.2R1.7";
   }

   rpc get-firewall-information {
     description "Show firewall information";
     junos:command "show firewall";
     input {
       uses command-forwarding;
       leaf control-plane-instance {
         description "Control plane instance name";
         type string;
         mandatory true;
       }
       leaf get-firewall-information {
         description "Display extensive firewall output";
         type empty;
       }
       leaf application {
         description "Owner application";
         type enumeration {
           enum "cfm" {
             description "Statistics for implicit filters for CFM";
           }
           enum "rmps" {
             description "Statistics for implicit filters for RMPS";
           }
           enum "eswd" {
             description "Statistics for implicit filters for eswd";
           }
           enum "lsp" {
             description "Statistics for implicit filters for lsp";
           }
           enum "routing" {
             description "Statistics for implicit bgp flowspec filters for routing";
           }
           enum "ecmp-tracer" {
             description "Statistics for implicit filters for ecmp-tracer debug tool";
           }
           enum "ecmp-tracer-server" {
             description "Statistics for implicit filters for ecmp-tracer JET clients";
           }
           enum "dot1xd" {
             description "Statistics for implicit filters for dot1xd";
           }
           enum "ppmd" {
             description "Statistics for implicit filters for Periodic packet Management Daemon";
           }
           enum "cosd" {
             description "Statistics for implicit filters for cosd";
           }
           enum "l2cpd" {
             description "Statistics for implicit filters for l2cpd";
           }
           enum "p4-switch" {
             description "Statistics for implicit filters for p4-switch";
           }
           enum "jdhcpd" {
             description "Statistics for implicit filters for jdhcpd";
           }
         }
       }
       choice daemon-select {
         case logical-system {
         }
       }
       leaf user-plane {
         description "User plane name";
         type string;
       }
       leaf terse {
         description "Show filter names only";
         type empty;
       }
       leaf detail {
         description "Show filter statistics with enhanced policer statistics";
         type empty;
       }
       leaf detailed {
         description "Show all filters with their errorred bindpoints";
         type empty;
       }
     }
     output {
       choice output-tags {
         case actual-tag {
           container firewall-information {
             uses firewall-information-block;
           }
         }
         case multichassis-tag {
           container multi-routing-engine-results {
             list multi-routing-engine-item {
               leaf re-name {
                 type string;
               }
               choice output-tags {
                 case actual-tag {
                   container firewall-information {
                     uses firewall-information-block;
                   }
                 }
               }
             }
           }
         }
       }
     }
   }
   rpc get-firewall-counter-information {
     description "Counter name";
     junos:command "show firewall counter";
     input {
       uses command-forwarding;
       leaf countername {
         description "Counter name";
         junos:cli-feature "nokeyword";
         type string;
         mandatory true;
       }
       leaf filter {
         description "Filter name";
         type string;
         mandatory true;
       }
       leaf detail {
         description "Show filter statistics with enhanced policer statistics";
         type empty;
       }
       leaf application {
         description "Owner application";
         type enumeration {
           enum "cfm" {
             description "Statistics for implicit filters for CFM";
           }
           enum "rmps" {
             description "Statistics for implicit filters for RMPS";
           }
           enum "eswd" {
             description "Statistics for implicit filters for eswd";
           }
           enum "lsp" {
             description "Statistics for implicit filters for lsp";
           }
           enum "routing" {
             description "Statistics for implicit bgp flowspec filters for routing";
           }
           enum "ecmp-tracer" {
             description "Statistics for implicit filters for ecmp-tracer debug tool";
           }
           enum "ecmp-tracer-server" {
             description "Statistics for implicit filters for ecmp-tracer JET clients";
           }
           enum "dot1xd" {
             description "Statistics for implicit filters for dot1xd";
           }
           enum "ppmd" {
             description "Statistics for implicit filters for Periodic packet Management Daemon";
           }
           enum "cosd" {
             description "Statistics for implicit filters for cosd";
           }
           enum "l2cpd" {
             description "Statistics for implicit filters for l2cpd";
           }
           enum "p4-switch" {
             description "Statistics for implicit filters for p4-switch";
           }
           enum "jdhcpd" {
             description "Statistics for implicit filters for jdhcpd";
           }
         }
       }
       choice daemon-select {
         case logical-system {
         }
       }
     }
     output {
       choice output-tags {
         case actual-tag {
           container firewall-information {
             uses firewall-information-block;
           }
         }
         case multichassis-tag {
           container multi-routing-engine-results {
             list multi-routing-engine-item {
               leaf re-name {
                 type string;
               }
               choice output-tags {
                 case actual-tag {
                   container firewall-information {
                     uses firewall-information-block;
                   }
                 }
               }
             }
           }
         }
       }
     }
   }
   rpc get-firewall-filter-programming-status {
     description "Show firewall filter-programming-status";
     junos:command "show firewall filter-programming-status";
     input {
       leaf verbosity {
         junos:cli-feature "nokeyword";
         type enumeration {
           enum "summary" {
             description "Display summary output";
           }
         }
       }
     }
     output {
       choice output-tags {
         case actual-tag {
           container firewall-filter-programming-status {
             uses firewall-filter-programming-status-block;
           }
         }
         case multichassis-tag {
           container multi-routing-engine-results {
             list multi-routing-engine-item {
               leaf re-name {
                 type string;
               }
               choice output-tags {
                 case actual-tag {
                   container firewall-filter-programming-status {
                     uses firewall-filter-programming-status-block;
                   }
                 }
               }
             }
           }
         }
       }
     }
   }
   rpc get-firewall-filter-programming-status-filter {
     description "Filter name";
     junos:command "show firewall filter-programming-status filter";
     input {
       leaf filtername {
         description "Filter name";
         junos:cli-feature "nokeyword";
         type string;
         mandatory true;
       }
       choice which-cmd {
         case bind {
           leaf bind {
             description "Bind name";
             type string;
           }
         }
         case detail {
           leaf detail {
             description "Show filter programming failure for all bindpoints in PFE";
             type empty;
           }
         }
       }
     }
     output {
       choice output-tags {
         case actual-tag {
           container firewall-filter-programming-status-filter {
             uses firewall-filter-programming-status-filter-block;
           }
         }
         case multichassis-tag {
           container multi-routing-engine-results {
             list multi-routing-engine-item {
               leaf re-name {
                 type string;
               }
               choice output-tags {
                 case actual-tag {
                   container firewall-filter-programming-status-filter {
                     uses firewall-filter-programming-status-filter-block;
                   }
                 }
               }
             }
           }
         }
       }
     }
   }
   rpc get-firewall-filter-information {
     description "Filter name";
     junos:command "show firewall filter";
     input {
       uses command-forwarding;
       leaf control-plane-instance {
         description "Control plane instance name";
         type string;
         mandatory true;
       }
       leaf filtername {
         description "Filter name";
         junos:cli-feature "nokeyword";
         type string;
         mandatory true;
       }
       leaf counter {
         description "Counter name";
         type string;
       }
       leaf detail {
         description "Show filter statistics with enhanced policer statistics";
         type empty;
       }
       leaf detailed {
         description "Show all filters with their errorred bindpoints";
         type empty;
       }
       leaf application {
         description "Owner application";
         type enumeration {
           enum "cfm" {
             description "Statistics for implicit filters for CFM";
           }
           enum "rmps" {
             description "Statistics for implicit filters for RMPS";
           }
           enum "eswd" {
             description "Statistics for implicit filters for eswd";
           }
           enum "lsp" {
             description "Statistics for implicit filters for lsp";
           }
           enum "routing" {
             description "Statistics for implicit bgp flowspec filters for routing";
           }
           enum "ecmp-tracer" {
             description "Statistics for implicit filters for ecmp-tracer debug tool";
           }
           enum "ecmp-tracer-server" {
             description "Statistics for implicit filters for ecmp-tracer JET clients";
           }
           enum "dot1xd" {
             description "Statistics for implicit filters for dot1xd";
           }
           enum "ppmd" {
             description "Statistics for implicit filters for Periodic packet Management Daemon";
           }
           enum "cosd" {
             description "Statistics for implicit filters for cosd";
           }
           enum "l2cpd" {
             description "Statistics for implicit filters for l2cpd";
           }
           enum "p4-switch" {
             description "Statistics for implicit filters for p4-switch";
           }
           enum "jdhcpd" {
             description "Statistics for implicit filters for jdhcpd";
           }
         }
       }
       choice daemon-select {
         case logical-system {
         }
       }
       leaf user-plane {
         description "User plane name";
         type string;
       }
     }
     output {
       choice output-tags {
         case actual-tag {
           container firewall-information {
             uses firewall-information-block;
           }
         }
         case multichassis-tag {
           container multi-routing-engine-results {
             list multi-routing-engine-item {
               leaf re-name {
                 type string;
               }
               choice output-tags {
                 case actual-tag {
                   container firewall-information {
                     uses firewall-information-block;
                   }
                 }
               }
             }
           }
         }
       }
     }
   }
   rpc get-filter-version {
     description "Show filter version installed";
     junos:command "show firewall filter version";
     input {
       leaf filtername {
         description "Filter name";
         junos:cli-feature "nokeyword";
         type string;
       }
     }
     output {
       choice output-tags {
         case actual-tag {
           container firewall-information {
             uses firewall-information-block;
           }
         }
         case multichassis-tag {
           container multi-routing-engine-results {
             list multi-routing-engine-item {
               leaf re-name {
                 type string;
               }
               choice output-tags {
                 case actual-tag {
                   container firewall-information {
                     uses firewall-information-block;
                   }
                 }
               }
             }
           }
         }
       }
     }
   }
   rpc get-firewall-filter-regex-information {
     description "Show filter using regular expression";
     junos:command "show firewall filter regex";
     input {
       leaf control-plane-instance {
         description "Control plane instance name";
         type string;
         mandatory true;
       }
       leaf filtername {
         description "Regular expression of filter names";
         junos:cli-feature "nokeyword";
         type jt:regular-expression;
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output-tags {
         case actual-tag {
           container firewall-information {
             uses firewall-information-block;
           }
         }
         case multichassis-tag {
           container multi-routing-engine-results {
             list multi-routing-engine-item {
               leaf re-name {
                 type string;
               }
               choice output-tags {
                 case actual-tag {
                   container firewall-information {
                     uses firewall-information-block;
                   }
                 }
               }
             }
           }
         }
       }
     }
   }
   rpc get-firewall-log-information {
     description "Show log entries for firewall activity";
     junos:command "show firewall log";
     input {
       leaf get-firewall-log-detailed-information {
         description "Display detailed output";
         type empty;
       }
       leaf interface {
         description "Interface name";
         type string;
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output-tags {
         case actual-tag {
           container firewall-log-information {
             uses firewall-log-information-block;
           }
         }
         case multichassis-tag {
           container multi-routing-engine-results {
             list multi-routing-engine-item {
               leaf re-name {
                 type string;
               }
               choice output-tags {
                 case actual-tag {
                   container firewall-log-information {
                     uses firewall-log-information-block;
                   }
                 }
               }
             }
           }
         }
       }
     }
   }
   rpc get-firewall-prefix-action-information {
     description "Show prefix-action statistics for a filter";
     junos:command "show firewall prefix-action-stats";
     input {
       leaf filter {
         description "Filter name";
         type string;
         mandatory true;
       }
       leaf prefix-action {
         description "Prefix-action name";
         type string;
         mandatory true;
       }
       leaf from {
         description "Starting counter or policer";
         default "0";
         type union {
           type string {
             pattern "<.*>|$.*";
           }
           type uint32 {
             range "0 .. 65535";
           }
         }
       }
       leaf to {
         description "Ending counter or policer";
         default "65535";
         type union {
           type string {
             pattern "<.*>|$.*";
           }
           type uint32 {
             range "0 .. 65535";
           }
         }
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output-tags {
         case actual-tag {
           container firewall-prefix-action-information {
             uses firewall-prefix-action-information-block;
           }
         }
         case multichassis-tag {
           container multi-routing-engine-results {
             list multi-routing-engine-item {
               leaf re-name {
                 type string;
               }
               choice output-tags {
                 case actual-tag {
                   container firewall-prefix-action-information {
                     uses firewall-prefix-action-information-block;
                   }
                 }
               }
             }
           }
         }
       }
     }
   }
   rpc get-firewall-configured {
     description "Filter name";
     junos:command "show firewall configuration filter";
     input {
       leaf filtername {
         description "Filter name";
         junos:cli-feature "nokeyword";
         type string;
         mandatory true;
       }
       leaf application {
         description "Owner application";
         type enumeration {
           enum "firewalld" {
             description "Cli filters";
           }
           enum "routing" {
             description "Bgp flowspec filters";
           }
           enum "ppmd" {
             description "Periodic packet management daemon";
           }
           enum "cosd" {
             description "Cosd filters";
           }
           enum "l2cpd" {
             description "L2cpd filters";
           }
           enum "lsp" {
             description "Lsp filters";
           }
           enum "p4-switch" {
             description "P4-switch filters";
           }
           enum "jdhcpd" {
             description "Jdhcpd filters";
           }
         }
       }
       leaf information-type {
         description "Filter information type";
         type enumeration {
           enum "configured" {
             description "Display configured filter information";
           }
           enum "compiled" {
             description "Display compiled filter information";
           }
         }
         mandatory true;
       }
       leaf brief {
         description "Display filter related information only";
         type empty;
       }
     }
     output {
       choice output-tags {
         case output-tag {
           leaf output {
             type string;
           }
         }
         case actual-tag {
           anyxml firewall-filter;
         }
         case multichassis-tag {
           anyxml multi-routing-engine-results;
         }
       }
     }
   }
   rpc get-firewall-policer-counter-information {
     description "Display policer counter statistics in short form";
     junos:command "show firewall policer counters";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf detail {
         description "Display policer counter statistics in detail";
         type empty;
       }
     }
     output {
       choice output-tags {
         case actual-tag {
           container firewall-policer-counter-information {
             uses firewall-policer-counter-information-block;
           }
         }
         case multichassis-tag {
           container multi-routing-engine-results {
             list multi-routing-engine-item {
               leaf re-name {
                 type string;
               }
               choice output-tags {
                 case actual-tag {
                   container firewall-policer-counter-information {
                     uses firewall-policer-counter-information-block;
                   }
                 }
               }
             }
           }
         }
       }
     }
   }
   rpc get-firewall-policer-per-counter-information {
     description "Display particular policer counter statistics";
     junos:command "show firewall policer counters counter-id";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf counter-id {
         description "Counter Index";
         junos:cli-feature "nokeyword";
         type union {
           type string {
             pattern "<.*>|$.*";
           }
           type uint32 {
             range "0 .. 2";
           }
         }
         mandatory true;
       }
       leaf detail {
         description "Display particular policer counter statistics in detail";
         type empty;
       }
     }
     output {
       choice output-tags {
         case output-tag {
           leaf output {
             type string;
           }
         }
         case actual-tag {
           anyxml firewall-policer-per-counter-information;
         }
         case multichassis-tag {
           anyxml multi-routing-engine-results;
         }
       }
     }
   }
   rpc get-firewall-templates-reference-counts {
     description "Show filter templates reference count for subscribers";
     junos:command "show firewall templates-in-use";
     input {
       leaf control-plane-instance {
         description "Control plane instance name";
         type string;
         mandatory true;
       }
       leaf user-plane {
         description "User plane name";
         type string;
       }
     }
     output {
       choice output-tags {
         case actual-tag {
           container firewall-templates-in-use {
             uses firewall-templates-in-use-block;
           }
         }
         case multichassis-tag {
           container multi-routing-engine-results {
             list multi-routing-engine-item {
               leaf re-name {
                 type string;
               }
               choice output-tags {
                 case actual-tag {
                   container firewall-templates-in-use {
                     uses firewall-templates-in-use-block;
                   }
                 }
               }
             }
           }
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping firewall-information-block {
     list filter-information {
       key "filter-name";
       description
         "Details of a firewall filter";
       leaf filter-name {
         type string;
         description
           "Name of filter";
       }
       leaf user-plane-name {
         type string;
         description
           "Name of the User Plane";
       }
       container error-status {
         leaf status {
           type string;
           description
             "Error status of the filter";
         }
       }
       list bind-error-status {
         leaf-list bind-name {
           type string;
           description
             "Error status of the filter bind point";
         }
       }
       list counter {
         key "counter-name";
         description
           "Counter information";
         leaf counter-name {
           type string;
           description
             "Counter name";
         }
         leaf byte-count {
           type uint64;
           description
             "Bytes counted";
         }
         leaf packet-count {
           type uint64;
           description
             "Packets counted";
         }
       }
       list policer {
         key "policer-name";
         description
           "Policer information";
         leaf policer-name {
           type string;
           description
             "Name of this policer";
         }
         leaf byte-count {
           type uint64;
           description
             "Bytes counted";
         }
         leaf packet-count {
           type uint64;
           description
             "Packets counted";
         }
       }
       list enhanced-hierarchical-policer {
         description
           "Hierarchical Policer information";
         leaf policer-name {
           type string;
           description
             "Name of this policer";
         }
         leaf byte-count-high {
           type uint64;
           description
             "Bytes counted";
         }
         leaf packet-count-high {
           type uint64;
           description
             "Packets counted";
         }
         leaf byte-count-medium-high {
           type uint64;
           description
             "Bytes counted";
         }
         leaf packet-count-medium-high {
           type uint64;
           description
             "Packets counted";
         }
         leaf byte-count-medium-low {
           type uint64;
           description
             "Bytes counted";
         }
         leaf packet-count-medium-low {
           type uint64;
           description
             "Packets counted";
         }
         leaf byte-count-low {
           type uint64;
           description
             "Bytes counted";
         }
         leaf packet-count-low {
           type uint64;
           description
             "Packets counted";
         }
         leaf packet-count {
           type uint64;
           description
             "Packets counted";
         }
         leaf byte-count {
           type uint64;
           description
             "Bytes counted";
         }
       }
       list filter-version {
         key "filter-name";
         description
           "Filter version information";
         leaf filter-name {
           type string;
           description
             "Name of filter";
         }
         leaf version {
           type uint32;
           description
             "Filter version";
         }
       }
     }
     list user-plane-filter-information {
       key "filter-name";
       description
         "Details of a user-plane firewall filter";
       leaf filter-name {
         type string;
         description
           "Name of filter";
       }
       leaf user-plane-name {
         type string;
         description
           "Name of the User Plane";
       }
       list counter {
         key "counter-name";
         description
           "Counter information";
         leaf counter-name {
           type string;
           description
             "Counter name";
         }
         leaf byte-count {
           type uint64;
           description
             "Bytes counted";
         }
         leaf packet-count {
           type uint64;
           description
             "Packets counted";
         }
       }
       list enhanced-hierarchical-policer-userplane {
         description
           "Enhanced Hierarchical Policer information";
         leaf policer-name {
           type string;
           description
             "Name of this policer";
         }
         leaf byte-count-high {
           type uint64;
           description
             "Bytes counted";
         }
         leaf packet-count-high {
           type uint64;
           description
             "Packets counted";
         }
         leaf byte-count-medium-high {
           type uint64;
           description
             "Bytes counted";
         }
         leaf packet-count-medium-high {
           type uint64;
           description
             "Packets counted";
         }
         leaf byte-count-medium-low {
           type uint64;
           description
             "Bytes counted";
         }
         leaf packet-count-medium-low {
           type uint64;
           description
             "Packets counted";
         }
         leaf byte-count-low {
           type uint64;
           description
             "Bytes counted";
         }
         leaf packet-count-low {
           type uint64;
           description
             "Packets counted";
         }
         leaf packet-count {
           type uint64;
           description
             "Packets counted";
         }
         leaf byte-count {
           type uint64;
           description
             "Bytes counted";
         }
       }
       list filter-version {
         key "filter-name";
         description
           "Filter version information";
         leaf filter-name {
           type string;
           description
             "Name of filter";
         }
         leaf version {
           type uint32;
           description
             "Filter version";
         }
       }
     }
     list subscribers-filter-information {
       key "filter-name";
       description
         "Details of subscribers firewall filter";
       leaf filter-name {
         type string;
         description
           "Name of filter";
       }
       leaf user-plane-name {
         type string;
         description
           "Name of the User Plane";
       }
       list counter {
         key "counter-name";
         description
           "Counter information";
         leaf counter-name {
           type string;
           description
             "Counter name";
         }
         leaf byte-count {
           type uint64;
           description
             "Bytes counted";
         }
         leaf packet-count {
           type uint64;
           description
             "Packets counted";
         }
       }
       list enhanced-hierarchical-policer-userplane {
         description
           "Enhanced Hierarchical Policer information";
         leaf policer-name {
           type string;
           description
             "Name of this policer";
         }
         leaf byte-count-high {
           type uint64;
           description
             "Bytes counted";
         }
         leaf packet-count-high {
           type uint64;
           description
             "Packets counted";
         }
         leaf byte-count-medium-high {
           type uint64;
           description
             "Bytes counted";
         }
         leaf packet-count-medium-high {
           type uint64;
           description
             "Packets counted";
         }
         leaf byte-count-medium-low {
           type uint64;
           description
             "Bytes counted";
         }
         leaf packet-count-medium-low {
           type uint64;
           description
             "Packets counted";
         }
         leaf byte-count-low {
           type uint64;
           description
             "Bytes counted";
         }
         leaf packet-count-low {
           type uint64;
           description
             "Packets counted";
         }
         leaf packet-count {
           type uint64;
           description
             "Packets counted";
         }
         leaf byte-count {
           type uint64;
           description
             "Bytes counted";
         }
       }
       list filter-version {
         key "filter-name";
         description
           "Filter version information";
         leaf filter-name {
           type string;
           description
             "Name of filter";
         }
         leaf version {
           type uint32;
           description
             "Filter version";
         }
       }
     }
   }
   grouping firewall-filter-programming-status-block {
     list firewall-status {
       key "filter-name";
       description
         "Programming details of a single firewall";
       leaf filter-name {
         type string;
         description
           "Name of filter";
       }
       leaf filter-direction {
         type string;
         description
           "Direction of filter";
       }
       leaf filter-type {
         type string;
         description
           "Type of filter";
       }
       leaf filter-status {
         type string;
         description
           "Status of filter";
       }
       leaf total-filters-programmed {
         type uint64;
         description
           "Total filters programmed";
       }
       leaf total-filters-failed {
         type uint64;
         description
           "Total filters failed";
       }
       leaf filter-fpc {
         type uint64;
         description
           "FPC of filter programmed";
       }
       leaf filter-pfe {
         type uint64;
         description
           "PFE of filter programmed";
       }
       leaf filter-dp {
         type uint64;
         description
           "DP of filter programmed";
       }
       leaf interface-name {
         type string;
         description
           "Name of interface";
       }
       leaf filter-family {
         type string;
         description
           "Filter family name";
       }
       leaf filter-isf {
         type string;
         description
           "Filter Interface specific or not";
       }
       leaf filter-details {
         type string;
         description
           "Filter programming details";
       }
     }
   }
   grouping firewall-filter-programming-status-filter-block {
     list firewall-status {
       key "filter-name";
       description
         "Programming details of a single firewall";
       leaf total-filters-programmed {
         type uint64;
         description
           "Total filters programmed";
       }
       leaf total-filters-failed {
         type uint64;
         description
           "Total filters failed";
       }
       leaf filter-fpc {
         type uint64;
         description
           "FPC of filter programmed";
       }
       leaf filter-pfe {
         type uint64;
         description
           "PFE of filter programmed";
       }
       leaf filter-dp {
         type uint64;
         description
           "DP of filter programmed";
       }
       leaf filter-direction {
         type string;
         description
           "Direction of filter";
       }
       leaf filter-type {
         type string;
         description
           "Type of filter";
       }
       leaf filter-status {
         type string;
         description
           "Status of filter";
       }
       leaf interface-name {
         type string;
         description
           "Name of interface";
       }
       leaf filter-name {
         type string;
         description
           "Name of filter";
       }
       leaf filter-family {
         type string;
         description
           "Filter family name";
       }
       leaf filter-isf {
         type string;
         description
           "Filter Interface specific or not";
       }
       leaf filter-details {
         type string;
         description
           "Filter programming details";
       }
     }
   }
   grouping firewall-log-information-block {
     list log-information {
       key "filter-name";
       description
         "Details of a single firewall log entry";
       leaf time {
         type string;
         description
           "Time of log";
       }
       leaf filter-name {
         type string;
         description
           "Name of filter";
       }
       leaf action-name {
         type string;
         description
           "Filter action";
       }
       leaf interface-name {
         type string;
         description
           "Name of interface";
       }
       leaf protocol-name {
         type string;
         description
           "Name of protocol";
       }
       leaf source-address {
         type string;
         description
           "Source address";
       }
       leaf destination-address {
         type string;
         description
           "Destination address";
       }
       leaf packet-length {
         type int32;
         description
           "Packet length";
       }
       leaf icmp-type {
         type int32;
         description
           "ICMP type";
       }
       leaf icmp-code {
         type int32;
         description
           "ICMP code";
       }
       leaf hex-dump-line {
         type string;
         description
           "Packet in Hex format";
       }
       leaf hex-dump-line1 {
         type string;
         description
           "Packet in Hex format";
       }
       leaf hex-dump-line2 {
         type string;
         description
           "Packet in Hex format";
       }
       leaf hex-dump-line3 {
         type string;
         description
           "Packet in Hex format";
       }
       leaf hex-dump-line4 {
         type string;
         description
           "Packet in Hex format";
       }
       leaf hex-dump-line5 {
         type string;
         description
           "Packet in Hex format";
       }
       leaf hex-dump-line6 {
         type string;
         description
           "Packet in Hex format";
       }
       leaf hex-dump-line7 {
         type string;
         description
           "Packet in Hex format";
       }
     }
   }
   grouping firewall-prefix-action-information-block {
     leaf filter-name {
       type string;
       description
         "Name of filter";
     }
     list counter {
       key "counter-name";
       description
         "Counter information";
       leaf counter-name {
         type string;
         description
           "Counter name";
       }
       leaf byte-count {
         type uint64;
         description
           "Bytes counted";
       }
       leaf packet-count {
         type uint64;
         description
           "Packets counted";
       }
     }
     list policer {
       key "policer-name";
       description
         "Policer information";
       leaf policer-name {
         type string;
         description
           "Name of this policer";
       }
       leaf byte-count {
         type uint64;
         description
           "Bytes counted";
       }
       leaf packet-count {
         type uint64;
         description
           "Packets counted";
       }
     }
   }
   grouping firewall-policer-counter-information-block {
     list policer-counter {
       list policer-counter-entry {
         leaf counter-id {
           type int32;
         }
         leaf green-bytes {
           type int32;
         }
         leaf green-packets {
           type int32;
         }
         leaf yellow-bytes {
           type int32;
         }
         leaf yellow-packets {
           type int32;
         }
         leaf discard-bytes {
           type int32;
         }
         leaf discard-packets {
           type int32;
         }
       }
     }
   }
   grouping firewall-templates-in-use-block {
     leaf firewall-templates-in-use-none {
       type string;
     }
   }
 }
