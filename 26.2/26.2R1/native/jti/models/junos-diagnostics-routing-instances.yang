module junos-diagnostics-routing-instances {
  yang-version 1.1;
  namespace "http://yang.juniper.net/junos/diagnostics/routing-instances";
  prefix jd-ri;

  import junos-extensions {
    prefix jx;
  }

  import junos-diagnostics {
    prefix jd;
  }

  organization
    "Juniper Networks, Inc.";

  contact
    "Juniper Networks, Inc.

     1133 Innovation Way
     Sunnyvale, CA 94089

     +1 888 314-5822

     E-mail: yang-support@juniper.net";

  description
    "This module contains a collection of top level nodes for JUNOS
     Routing Instances diagnostics data.

     Copyright (c) 2025 Juniper Networks, Inc.
     All rights reserved.";

  revision 2025-07-01 {
    description
      "Initial revision.";
    reference "0.1.0";
  }

  jx:version "0.1.0";
  jx:origin "experimental";

  grouping routing-instances-top {
    description
      "Top-level grouping for JUNOS routing-instances diagnostics data";

    container routing-instances {
      description
        "Encapsulating container for all JUNOS routing-instances diagnostics";

      list routing-instance {
        key name;

        description
          "List of all JUNOS routing-instances";

        leaf name {
          type string;
          description
            "Name of the routing instance";
        }
      }
    }
  }

  augment "/jd:diagnostics" {
    description
      "Adds routing-instances domain to top-level diagnostics data";

    uses routing-instances-top;
  }
}
