module junos-lldp-types {
  yang-version 1.1;
  namespace "http://yang.juniper.net/junos/lldp/types";
  prefix jlldpt;

  import junos-extensions {
    prefix jx;
  }

  import ietf-yang-types {
    prefix yang;
  }

  import ietf-inet-types {
    prefix inet;
  }

  organization
    "Juniper Networks, Inc.";

  contact
    "Juniper Networks, Inc.

     1133 Innovation Way
     Sunnyvale, CA 94089

     +1 888 314-5822

     E-mail: yang-support@juniper.net";

  description
    "This module contains a collection of JUNOS LLDP data types.

     Copyright (c) 2025 Juniper Networks, Inc.
     All rights reserved.";

  revision 2025-05-02 {
    description
      "Initial revision.";
    reference "0.1.0";
  }

  jx:version "0.1.0";

  identity mgmt-addr-type {
    description
      "Base identity for management address types.";
  }

  identity ipv4 {
    base mgmt-addr-type;
    description
      "IPv4 (1) Address Family ";
    reference "Sec 8.5.9.3 of IEEE 802.1AB-2009";
  }

  identity ipv6 {
    base mgmt-addr-type;
    description
      "IPv6 (1) Address Family ";
    reference "Sec 8.5.9.3 of IEEE 802.1AB-2009";
  }

  identity all-802 {
    base mgmt-addr-type;
    description
      "802 (6) Address Family, including all 802 media plus Ethernet";
    reference "Sec 8.5.9.3 of IEEE 802.1AB-2009";
  }

  typedef mgmt-addr {
    type union {
      type inet:ip-address;
      type yang:mac-address;
    }
    description
      "Union type for management addresses.";
  }

  typedef mgmt-interface-number-subtype {
    type enumeration {
      enum unknown {
        value 1;
        description
          "Interface is not known";
      }
      enum ifindex {
        value 2;
        description
          "Interface is based on the IF-MIB ifIndex";
      }
      enum system-port-number {
        value 3;
        description
          "Interface is based on the system port number";
      }
    }
    description
      "The Management address interface numbering subtype field
       indicating the numbering method used for defining the interface
       number.";
    reference
      "Sec 8.5.9.5 of IEEE Std 802.1AB-2016";
  }
}
