module junos-diagnostics {
  yang-version 1.1;
  namespace "http://yang.juniper.net/junos/diagnostics";
  prefix jd;

  import junos-extensions {
    prefix jx;
  }

  organization
    "Juniper Networks, Inc.";

  contact
    "Juniper Networks, Inc.

     1133 Innovation Way
     Sunnyvale, CA 94089

     +1 888 314-5822

     E-mail: yang-support@juniper.net";

  description
    "This module contains a collection of top level nodes for JUNOS
     diagnostics data.

     Copyright (c) 2025 Juniper Networks, Inc.
     All rights reserved.";

  revision 2025-07-01 {
    description
      "Initial revision.";
    reference "0.1.0";
  }

  jx:version "0.1.0";
  jx:origin "experimental";

  grouping diagnostics-top {
    description
      "Top-level grouping for JUNOS diagnostics data";

    container diagnostics {
      description
        "Encapsulating top-level diagnostics container for all JUNOS diagnostics";

      config false;
    }
  }

  uses diagnostics-top;
}
