module junos-state-protocols {
  yang-version 1.1;
  namespace "http://yang.juniper.net/junos/state/protocols";
  prefix js-pro;

  import junos-extensions {
    prefix jx;
  }

  import junos-state {
    prefix js;
  }

  import junos-state-routing-instances {
    prefix js-ri;
  }

  organization
    "Juniper Networks, Inc.";

  contact
    "Juniper Networks, Inc.

     1133 Innovation Way
     Sunnyvale, CA 94089

     +1 888 314-5822

     E-mail: yang-support@juniper.net";

  description
    "This module contains a collection of top level nodes for JUNOS
     protocols state data.

     Copyright (c) 2025 Juniper Networks, Inc.
     All rights reserved.";

  revision 2025-04-25 {
    description
     "Addition of jx:origin annotation";
    reference "0.2.1";
  }

  revision 2023-08-08 {
    description
      "Add protocols augment to routing-instances.";
    reference "0.2.0";
  }

  revision 2021-12-22 {
    description
      "Initial revision.";
    reference "0.1.0";
  }

  jx:version "0.2.1";
  jx:origin "juniper";

  grouping protocols-top {
    description
      "Top-level grouping for JUNOS protocols state data.";

    container protocols {
      description
        "Encapsulating container for all JUNOS protocol state.";
    }
  }

  augment "/js:state" {
    description
      "Adds protocols domain to top-level state.";

    uses protocols-top;
  }

  augment "/js:state/js-ri:routing-instances/js-ri:routing-instance" {
    description
      "Adds protocols domain to top-level routing-instance state.";

    uses protocols-top;
  }
}
