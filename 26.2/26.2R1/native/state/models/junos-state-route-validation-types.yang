module junos-state-route-validation-types {
  yang-version 1.1;
  namespace "http://yang.juniper.net/junos/state/route-validation/types";
  prefix js-rv-types;

  import junos-extensions {
    prefix jx;
  }

  organization
    "Juniper Networks, Inc.";

  contact
    "Juniper Networks, Inc.

     1133 Innovation Way
     Sunnyvale, CA 94089

     +1 888 314-5822

     E-mail: yang-support@juniper.net";

  description
    "This module contains a collection of JUNOS route validation data
     types.

     Copyright (c) 2025 Juniper Networks, Inc.
     All rights reserved.";

  revision 2025-04-25 {
    description
     "Addition of jx:origin annotation";
    reference "0.1.1";
  }

  revision 2023-08-08 {
    description
      "Initial revision.";
    reference "0.1.0";
  }

  jx:version "0.1.1";
  jx:origin "juniper";


  identity prefix-attr-type {
    description
      "Base identity for prefix attribute type; i.e., the attribute that
       is being validated.";
  }

  identity origin-as {
    base prefix-attr-type;
    description
      "Identity for the origin-AS part of the AS path.";
  }

  identity as-path {
    base prefix-attr-type;
    description
      "Identity for validating the as-path against the records in an
       ASPath Provider Authhorization (ASPA) database.";
  }

  identity none {
    base prefix-attr-type;
    description
      "No validation is performed.  Devolves to a simple prefix
       filter.";
  }

  identity rpki-rtr-session-state {
    description
      "Base identity for the RPKI-RTR session state.";
  }

  identity rpki-rtr-session-up {
    base rpki-rtr-session-state;
    description
      "The RPKI-RTR session is up.";
  }

  identity rpki-rtr-session-idle {
    base rpki-rtr-session-state;
    description
      "The RPKI-RTR session is idle.";
  }

  identity rpki-rtr-session-connect {
    base rpki-rtr-session-state;
    description
      "The RPKI-RTR session is in the process of connecting.";
  }

  identity rpki-rtr-session-exchange-full {
    base rpki-rtr-session-state;
    description
      "The RPKI-RTR session is receiving records in response to a full
       query.";
  }

  identity rpki-rtr-session-exchange-incr {
    base rpki-rtr-session-state;
    description
      "The RPKI-RTR session is receiving records in response to a
       incremental query.";
  }
}
