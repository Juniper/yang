module junos-pfe-npu-stats {

    yang-version "1";

    // namespace
    namespace "http://juniper.net/yang/junos-pfe-npu-stats";

    prefix "junos-pfe-npu-stats";

    // meta
    organization "Juniper Networks";

    contact
      "Juniper Networks, Inc.

       1133 Innovation Way
       Sunnyvale, CA 94089

       +1 888 314-5822

       E-mail: yang-support@juniper.net";

    description
        "This module provides data definitions for exporting npu Stats
        ";

    revision 2023-08-08 {
      description
        "Initial revision.";
      reference "0.1.0";
    }

    container junos {
        config false;
        description "JunOS OS";

        container system {
            description "Junos System";

            list linecard {
                description "Contains PFE resources";

                container npu {
                    description "npu sensor data";

                    container memory {
                        description "npu memory data";
                    }

                    container utilization {
                        description "npu utilization data";
                    }
                }
            }
        }
    }
}
