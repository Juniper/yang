module junos-pfe-interface-traffic-stats {

    yang-version "1";

    // namespace
    namespace "http://juniper.net/yang/junos-pfe-interface-traffic-stats";

    prefix "junos-pfe-interface-traffic-stats";

    // meta
    organization "Juniper Networks";

    contact
      "Juniper Networks, Inc.

       1133 Innovation Way
       Sunnyvale, CA 94089

       +1 888 314-5822

       E-mail: yang-support@juniper.net";

    description
        "This module provides data definitions for exporting Junos
	/junos/system/linecard/interface/traffic/ sensor";

    revision 2023-12-26 {
      description
        "Initial revision.";
      reference "0.1.0";
    }

    container junos {
        config false;
        description "JunOS OS";

        container system {
            description "Junos System";

            list linecard {
                description "Contains PFE resources";

                container interface {
                    description "interface sensor data";

                    container traffic {
                        description "interface traffic data";
                    }
                }
            }
        }
    }
}
