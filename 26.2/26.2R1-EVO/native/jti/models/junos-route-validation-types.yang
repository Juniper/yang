module junos-route-validation-types {
  yang-version 1.1;
  namespace "http://yang.juniper.net/junos/route-validation/types";
  prefix "junos-rv";

  import junos-extensions {
    prefix jx;
  }

  organization
    "Juniper Networks, Inc.";

  contact
    "Juniper Networks, Inc.

     1133 Innovation Way
     Sunnyvale, CA 94089

     +1 888 314-5822

     E-mail: yang-support@juniper.net";

  description
    "This module contains the definitions for types of
     origin-validation-state data.

     Copyright (c) 2025 Juniper Networks, Inc.
     All rights reserved.";

  revision 2025-04-25 {
    description
     "Addition of jx:origin annotation";
    reference "0.1.1";
  }

  revision 2023-08-08 {
    description
      "Initial revision.";
    reference "0.1.0";
  }

  jx:version "0.1.1";
  jx:origin "juniper";

  identity rpki-validation-state {
    description
      "Base identity for the state of route validation.";
    reference
        "RFC 6811 BGP Prefix Origin Validation
         Protocol Version 1";
  }

  identity rpki-validation-unverified {
    base rpki-validation-state;
    description
      "Route was not validated.";
  }

  identity rpki-validation-unknown {
    base rpki-validation-state;
    description
      "Route validation results is unknown because
       of lack of validation data that covers this route.";
  }

  identity rpki-validation-invalid {
    base rpki-validation-state;
    description
      "Route validation result is invalid.";
  }

  identity rpki-validation-valid {
    base rpki-validation-state;
    description
      "Route validation result is valid.";
  }

  identity rpki-validation-invalid-reason {
    description
      "Base identity for reason why route validation made route
       invalid.";
    reference
        "RFC 6811 BGP Prefix Origin Validation";
  }

  identity rpki-validation-invalid-origas {
    base rpki-validation-invalid-reason;
    description
      "Route failed validation due to invalid origin-as.";
  }

  identity rpki-validation-invalid-maxlen {
    base rpki-validation-invalid-reason;
    description
      "Route failed validation due to prefix length exceeding valid max
       length.";
  }
}
