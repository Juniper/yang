module junos-state-lldp {
  yang-version 1.1;
  namespace "http://yang.juniper.net/junos/state/lldp";
  prefix js-lldp;

  import junos-extensions {
    prefix jx;
  }

  import ietf-yang-types {
    prefix yang;
  }

  import junos-state {
    prefix js;
  }

  import junos-state-protocols {
    prefix js-pro;
  }

  import junos-lldp-types {
    prefix jlldpt;
  }

  organization
    "Juniper Networks, Inc.";

  contact
    "Juniper Networks, Inc.

     1133 Innovation Way
     Sunnyvale, CA 94089

     +1 888 314-5822

     E-mail: yang-support@juniper.net";

  description
    "This module contains a collection of top level nodes for JUNOS
     LLDP state data.

     Copyright (c) 2025 Juniper Networks, Inc.
     All rights reserved.";

  revision 2025-05-02 {
    description
      "Added management address and neighbor-count leafs";
    reference "0.2.0";
  }

  revision 2025-04-25 {
    description
     "Addition of jx:origin annotation";
    reference "0.1.1";
  }

  revision 2022-02-21 {
    description
      "Initial revision";
    reference "0.1.0";
  }

  jx:version "0.2.0";
  jx:origin "juniper";

  grouping lldp-management-address {
    description
      "Operational state data to represent local or remote Management
       Address TLV parameters.";

    container management-addresses {
      description
        "Enclosing container for list of LLDP management addresses.";

      list management-address {
        description
          "List of management addresses in use by the local/remote
           system.";

        key "address";

        leaf address {
          type jlldpt:mgmt-addr;
          description
            "Management address associated with the Management Address
             TLV.";
          reference
            "Sec 8.5.9.4 of IEEE Std 802.1AB-2016";
        }

        leaf subtype {
          type identityref {
            base jlldpt:mgmt-addr-type;
          }
          description
            "Management address subtype indicating the address family
             for the address.";
          reference
            "Sec 8.5.9.3 of IEEE Std 802.1AB-2016";
        }

        leaf interface-number {
          type uint32;
          description
            "Interface number that identifies the specific interface
             associated with this management address.";
          reference
            "Sec 8.5.9.6 of IEEE Std 802.1AB-2016";
        }

        leaf interface-number-subtype {
          type jlldpt:mgmt-interface-number-subtype;
          description
            "The Management address interface numbering subtype field
             indicating the numbering method used for defining the
             interface-number.";
          reference
            "Sec 8.5.9.5 of IEEE Std 802.1AB-2016";
        }

        leaf oid {
          type string;
          description
            "The OID that identifies the type of hardware component or
             protocol entity associated with the indicated management
             address.  If no OID is available, this leaf is optional.";
          reference
            "Sec 8.5.9.8 of IEEE Std 802.1AB-2016";
        }
      }
    }
  }

  grouping lldp-neighbors-top {
    description
      "Top-level grouping for LLDP neighbors";

    container neighbors {
      description
        "Enclosing container for the list of LLDP neighbors on an interface";

      list neighbor {
        key "id";
        description
          "List of LLDP neighbors";

        leaf id {
          type string;
          description
            "System generated identifier for the neighbor on the interface";
        }

        leaf system-name {
          type string;
          description
            "The system name field shall contain an alpha-numeric string that
            indicates the system's administratively assigned name.  The system
            name should be the system's fully qualified domain name. If
            implementations support IETF RFC 3418, the sysName object should be
            used for this field.";

        }

        leaf system-description {
          type string;
          description
            "The system description field shall contain an alpha-numeric string
            that is the textual description of the network entity.  The system
            description should include the full name and version identification
            of the system's hardware type, software operating system, and
            networking software. If implementations support IETF RFC 3418, the
            sysDescr object should be used for this field.";

        }

        leaf chassis-id {
          type string;
          description
            "The Chassis ID is a mandatory TLV which identifies the chassis
            component of the endpoint identifier associated with the
            transmitting LLDP agent";
        }

        leaf port-id {
          type string;
          description
            "The Port ID is a mandatory TLV which identifies the port component
            of the endpoint identifier associated with the transmitting LLDP
            agent. If the specified port is an IEEE 802.3 Repeater port, then
            this TLV is optional.";

        }

        leaf port-description {
          type string;
          description
            "The binary string containing the actual port identifier for the
            port which this LLDP PDU was transmitted. The source and format of
            this field is defined by PtopoPortId from RFC2922.";

        }

        leaf ttl {
          type uint16;
          units "seconds";
          description
            "The time-to-live (TTL) is a mandatory TLV which indicates how long
            information from the neighbor should be considered valid";
        }

        uses lldp-management-address;
      }
    }
  }

  grouping lldp-interface-counters {
    description
      "Grouping for per interface LLDP counters";

    leaf frame-in {
      type yang:counter64;
      description
        "The number of LLDP frames received";
    }

    leaf frame-out {
      type yang:counter64;
      description
        "The number of LLDP frames transmitted";
    }
  }

  grouping lldp-interfaces-top {
    description
      "Top-level grouping for LLDP interfaces";

    container interfaces {
      description
        "Enclosing container for the list of LLDP interfaces";

      list interface {
        key "name";
        description
          "List of LLDP interfaces";

        leaf name {
          type string;
          description
            "The name of the interface running LLDP";
        }

        leaf local-port-id {
          type string;
          description
            "The string value used to identify the port component associated
            with a given port in the local system";
        }

        leaf local-port-description {
          type string;
          description
            "The string value used to identify the IEEE 802 LAN station's port
            description associated with the local system. If the local agent
            supports IETF RFC 2863, lldpLocPortDesc object should have the same
            value of ifDescr object.";

        }

        leaf neighbor-count {
          type yang:gauge64;
          description
            "The count of neighbors on a single interface";
        }

        container counters {
          description
            "LLDP counters on each interface";

          uses lldp-interface-counters;
        }

        uses lldp-neighbors-top;
      }
    }
  }

  grouping lldp-top {
    description
      "Top-level grouping for LLDP state data";

    container lldp {
      description
        "Container for LLDP state";

      uses lldp-interfaces-top;
      uses lldp-management-address;
    }
  }

  augment "/js:state/js-pro:protocols" {
    description
      "Adds LLDP domain to protocol state";

    uses lldp-top;
  }
}
