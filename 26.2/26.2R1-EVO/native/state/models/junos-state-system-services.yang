module junos-state-system-services {
  yang-version 1.1;
  namespace "http://yang.juniper.net/junos/state/system/services";
  prefix js-sys-svc;

  import junos-extensions {
    prefix jx;
  }

  import junos-state {
    prefix js;
  }

  import junos-state-system {
    prefix js-sys;
  }

  organization
    "Juniper Networks, Inc.";

  contact
    "Juniper Networks, Inc.

     1133 Innovation Way
     Sunnyvale, CA

     +1 888 314-5822

     E-mail: yang-support@juniper.net";

  description
    "This module contains a collection of top level nodes for JUNOS
     system state data.

     Copyright (c) 2025 Juniper Networks, Inc.
     All rights reserved.";
  
  revision 2025-04-25 {
    description
     "Addition of jx:origin annotation";
    reference "0.1.1";
  }

  revision 2023-07-20 {
    description
      "Initial revision";
    reference "0.1.0";
  }

  jx:version "0.1.1";
  jx:origin "juniper";

  grouping system-services-top {
    description
      "Top-level grouping for JUNOS system state data";

    container services {
      description
        "Encapsulating container for all JUNOS system state";

    }
  }

  augment "/js:state/js-sys:system" {
    description
      "Adds services domain to top-level system state";

    uses system-services-top;
  }
}
