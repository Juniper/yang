module junos-state-poe {
  yang-version 1.1;
  namespace "http://yang.juniper.net/junos/state/poe";
  prefix js-poe;

  import junos-extensions {
    prefix jx;
  }

  import junos-state {
    prefix js;
  }

  organization
    "Juniper Networks, Inc";

  contact
    "Juniper Networks, Inc.

     1133 Innovation Way
     Sunnyvale, CA 94089

     +1 888 314-5822

     E-mail: yang-support@juniper.net";

  description
    "This module contains a collection of top level nodes for JUNOS
     PoE state data

     Copyright (c) 2025 Juniper Networks, Inc.
     All rights reserved.";

  revision 2025-05-31 {
    description
      "Style compliance, addition of oper-status-detail, power-reserved
       leafs";
    reference "1.0.0";
  }

  revision 2025-04-25 {
    description
      "Addition of jx:origin annotation";
    reference "0.1.1";
  }

  revision 2022-05-23 {
    description
      "Initial revision";
    reference "0.1.0";
  }

  jx:version "1.0.0";
  jx:origin "juniper";

  typedef power-class {
    type enumeration {
      enum class-0 {
        value 0;
        description
          "PoE power class 0";
      }
      enum class-1 {
        value 1;
        description
          "PoE power class 1";
      }
      enum class-2 {
        value 2;
        description
          "PoE power class 2";
      }
      enum class-3 {
        value 3;
        description
          "PoE power class 3";
      }
      enum class-4 {
        value 4;
        description
          "PoE power class 4";
      }
      enum class-5 {
        value 5;
        description
          "PoE power class 5";
      }
      enum class-6 {
        value 6;
        description
          "PoE power class 6";
      }
      enum class-7 {
        value 7;
        description
          "PoE power class 7";
      }
      enum class-8 {
        value 8;
        description
          "PoE power class 8";
      }
      enum not-applicable {
        value 9;
        description
          "PoE power class not applicable";
      }
      enum unknown {
        value 10;
        description
          "PoE power class unknown";
      }
    }
    description
      "IEEE 802.3 PoE power classes";
  }

  grouping poe-power-consumption {
    description
      "Grouping for per controller/interface power consumption";

    leaf power-consumption {
      type decimal64 {
        fraction-digits 2;
        range "0..max";
      }
      units watts;
      description
        "PoE power consumption by the connected power device(s)";
    }

    leaf power-over-consumed {
      type boolean;
      description
        "The connected power device(s) is consuming more power than
         allocated";
    }
  }

  grouping poe-controller-top {
    description
      "Top level grouping for PoE controllers";

    container controllers {
      description
        "Enclosing container for the list of PoE controllers and global
         controller state";

      leaf fast-poe-enabled {
        type boolean;
        description
          "Fast PoE enabled or not";
      }

      leaf perpetual-poe-enabled {
        type boolean;
        description
          "Perpetual PoE enabled or not";
      }

      list controller {
        key "index";
        description
          "List of PoE controllers";

        leaf index {
          type uint32;
          description
            "Virtual-chassis index/controller number";
        }

        leaf firmware-available {
          type boolean;
          description
            "New PoE firmware version available or not";
        }

        leaf max-power {
          type decimal64 {
            fraction-digits 2;
            range "0..max";
          }
          units watts;
          description
            "Total PoE power available";
        }

        leaf power-reserved {
          type decimal64 {
            fraction-digits 2;
            range "0..max";
          }
          units watts;
          description
            "Total PoE power reserved";
        }

        uses poe-power-consumption;

        leaf guard-band {
          type uint64;
          units watts;
          description
            "PoE guard band value";
        }

        leaf poe-management {
          type enumeration {
            enum static {
              description
                "Management is static";
            }
            enum dynamic {
              description
                "Management is dynamic";
            }
            enum class {
              description
                "Management is class";
            }
          }
          description
            "PoE management mode of the switch";
        }

        leaf poe-status {
          type enumeration {
            enum af-mode {
              description
                "IEEE 802.3AF mode";
            }
            enum af-enhance {
              description
                "IEEE 802.3AF enhancement mode";
            }
            enum at-mode {
              description
                "IEEE 802.3AT mode";
            }
            enum at-af-combo {
              description
                "IEEE 802.3AF/AT mode";
            }
            enum download-init {
              description
                "PoE firmware version upgrade - download started";
            }
            enum poe-sw-erase {
              description
                "PoE firmware version upgrade - software erase";
            }
            enum download-in-progress {
              description
                "PoE firmware version upgrade - download in progress";
            }
            enum download-fail {
              description
                "PoE firmware version upgrade - download failed";
            }
            enum reboot-required {
              description
                "PoE firmware version upgrade - reboot required";
            }
            enum download-required {
              description
                "PoE firmware version upgrade - download required";
            }
            enum not-ready {
              description
                "PoE module is not ready";
            }
            enum device-fail {
              description
                "PoE module is in device failed state";
            }
            enum poe-not-supported {
              description
                "PoE not supported";
            }
            enum bt-mode {
              description
                "IEEE 802.3BT mode";
            }
          }
          description
            "PoE status of the switch";
        }

        leaf lldp-priority {
          type enumeration {
            enum enabled {
              description
                "LLDP priority is enabled";
            }
            enum disabled {
              description
                "LLDP priority is disabled";
            }
          }
          description
            "PoE LLDP priority status";
        }
      }
    }
  }

  grouping poe-interface-top {
    description
      "Top level grouping for PoE interfaces";

    container interfaces {
      description
        "Enclosing container for the list of PoE interfaces";

      list interface {
        key "name";
        description
          "List of PoE interfaces";

        leaf name {
          type string;
          description
            "PoE interface name";
        }

        leaf admin-status {
          type enumeration {
            enum enabled {
              description
                "Administrative status is enabled";
            }
            enum disabled {
              description
                "Administrative status is disabled";
            }
          }
          description
            "PoE administrative status";
        }

        leaf oper-status {
          type enumeration {
            enum on {
              description
                "Operational status is on";
            }
            enum off {
              description
                "Operational status is off";
            }
            enum disabled {
              description
                "Operational status is disabled";
            }
            enum enabled {
              description
                "Operational status is enabled";
            }
          }
          description
            "PoE operational status";
        }

        leaf oper-status-detail {
          type string;
          description
            "PoE operational status detail";
        }

        leaf poe-four-pair {
          type enumeration {
            enum enabled {
              description
                "Four pair status is enabled";
            }
            enum disabled {
              description
                "Four pair status is disabled";
            }
          }
          description
            "PoE four pair status";
        }

        leaf poe-pair-status {
          type enumeration {
            enum 4p-poh {
              description
                "Four pair ultra high power mode";
            }
            enum 4p-bt {
              description
                "Four pair IEEE 802.3BT mode";
            }
            enum 4p-at {
              description
                "Four pair IEEE 802.3AT mode";
            }
            enum ss-bt {
              description
                "IEEE 802.3BT single signature";
            }
            enum ds-bt {
              description
                "IEEE 802.3BT dual signature";
            }
            enum 2p-poh {
              description
                "Two pair ultra high power mode";
            }
            enum 2p-at {
              description
                "Two pair IEEE 802.3AT mode";
            }
          }
          description
            "PoE pair status";
        }

        leaf power-limit {
          type decimal64 {
            fraction-digits 1;
            range "0..max";
          }
          units watts;
          description
            "Interface PoE power limit";
        }

        leaf power-limit-lldp-negotiated {
          type boolean;
          description
            "The power limit value is LLDP negotiated or not";
        }

        leaf priority {
          type enumeration {
            enum low {
              description
                "Priority is low";
            }
            enum high {
              description
                "Priority is high";
            }
            enum critical {
              description
                "Priority is critical";
            }
          }
          description
            "Interface PoE priority";
        }

        leaf priority-lldp-negotiated {
          type boolean;
          description
            "The priority value is LLDP negotiated or not";
        }

        uses poe-power-consumption;

        leaf power-class-a {
          type power-class;
          description
            "IEEE 802.3 power class value for the Alternative A
             pair-set";
        }

        leaf power-class-b {
          type power-class;
          description
            "IEEE 802.3 power class value for the Alternative B
             pair-set";
        }

        leaf poe-mode {
          type enumeration {
            enum 802-3af {
              description
                "PoE mode is IEEE 802.3AF";
            }
            enum 802-3at {
              description
                "PoE mode is IEEE 802.3AT";
            }
            enum ultra-poe {
              description
                "PoE mode is Ultra-PoE";
            }
            enum 802-3bt {
              description
                "PoE mode is IEEE 802.3BT";
            }
          }
          description
            "Interface PoE mode";
        }
      }
    }
  }

  grouping poe-top {
    description
      "Top-level grouping for PoE state data";

    container poe {
      description
        "Container for PoE state";

      uses poe-controller-top;
      uses poe-interface-top;

    }
  }

  augment "/js:state" {
    description
      "Adds PoE domain to top-level state";

    uses poe-top;
  }
}
