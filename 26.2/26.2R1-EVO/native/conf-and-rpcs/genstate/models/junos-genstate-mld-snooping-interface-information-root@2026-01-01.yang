module junos-genstate-mld-snooping-interface-information-root {
   yang-version 1;
   namespace "http://yang.juniper.net/junos/genstate/mld-snooping-interface-information-root";
   prefix jgmsiir;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for mld-snooping-interface-information-root.

      Copyright (c) 2026 Juniper Networks, Inc.
      All rights reserved.";

   revision 2026-01-01 {
     description "Junos: 26.2R1.7-EVO";
   }

   grouping mld-snooping-interface-information-root-top {
     description
       "Top-level grouping";
     container mld-snooping-interface-information-root {
       description
         "Top-level container";
       list mld-snooping-interface-information-per-instance {
         key "instance-name";
         leaf instance-name {
           type string;
         }
         list mld-snooping-interface-information-per-bridge-domain {
           key "bridge-domain";
           leaf bridge-domain {
             type string;
             description
               "Bridge Domain";
           }
           list mld-snooping-interface-information-per-learning-domain {
             key "learning-domain";
             leaf learning-domain {
               type string;
               description
                 "Bridge or VPLS learning domain";
             }
             list mgm-snooping-interface {
               key "interface-name";
               leaf interface-name {
                 type string;
                 description
                   "Name of interface";
               }
               leaf remote-pe-address {
                 type jt:ipaddr;
               }
               leaf mgm-interface-state {
                 type string;
               }
               leaf mgm-group-count {
                 type int32;
               }
               leaf mgm-mc-lag-state {
                 type string;
                 description
                   "State of the mc-lag interface";
               }
               leaf mgm-group-limit {
                 type uint32;
                 description
                   "Maximum number of (source,group) per interface";
               }
               leaf mgm-immediate-leave {
                 type string;
                 description
                   "Groups are removed immediately without sending last 
                   membership queries";
               }
               leaf mgm-snooping-router-interface {
                 type string;
                 description
                   "Interface connected to multicast routers";
               }
               leaf mgm-snooping-interswitch-interface {
                 type string;
                 description
                   "Interface connected to switch";
               }
               leaf mgm-snooping-rvlan-interface {
                 type string;
                 description
                   "Interface is part of Receiver Vlan";
               }
             }
             container mgm-configured-parameters {
               leaf query-interval {
                 type string;
               }
               leaf query-response-interval {
                 type string;
               }
               leaf last-member-query-interval {
                 type string;
               }
               leaf robustness-count {
                 type int32;
               }
               leaf mld-l2-querier {
                 type string;
                 description
                   "MLD L2 querier";
               }
               leaf l2-querier-source-address {
                 type jt:ipaddr;
               }
               leaf evpn-ssm-reports-only {
                 type string;
                 description
                   "EVPN SSM reports only";
               }
               leaf proto-version {
                 type uint32;
               }
               leaf multicast-router-no-flood {
                 type string;
               }
               leaf flood-reports-to-inter-switch-interface {
                 type string;
               }
               leaf immediate-leave-on-host-interface {
                 type string;
               }
               leaf evpn-query-relay-stop {
                 type string;
               }
             }
           }
         }
         list mld-snooping-interface-information-per-vlan {
           key "vlan";
           leaf vlan {
             type string;
             description
               "Vlan";
           }
           list mld-snooping-interface-information-per-learning-domain {
             key "learning-domain";
             leaf learning-domain {
               type string;
               description
                 "Bridge or VPLS learning domain";
             }
             list mgm-snooping-interface {
               key "interface-name";
               leaf interface-name {
                 type string;
                 description
                   "Name of interface";
               }
               leaf remote-pe-address {
                 type jt:ipaddr;
               }
               leaf mgm-interface-state {
                 type string;
               }
               leaf mgm-group-count {
                 type int32;
               }
               leaf mgm-mc-lag-state {
                 type string;
                 description
                   "State of the mc-lag interface";
               }
               leaf mgm-group-limit {
                 type uint32;
                 description
                   "Maximum number of (source,group) per interface";
               }
               leaf mgm-immediate-leave {
                 type string;
                 description
                   "Groups are removed immediately without sending last 
                   membership queries";
               }
               leaf mgm-snooping-router-interface {
                 type string;
                 description
                   "Interface connected to multicast routers";
               }
               leaf mgm-snooping-interswitch-interface {
                 type string;
                 description
                   "Interface connected to switch";
               }
               leaf mgm-snooping-rvlan-interface {
                 type string;
                 description
                   "Interface is part of Receiver Vlan";
               }
             }
             container mgm-configured-parameters {
               leaf query-interval {
                 type string;
               }
               leaf query-response-interval {
                 type string;
               }
               leaf last-member-query-interval {
                 type string;
               }
               leaf robustness-count {
                 type int32;
               }
               leaf mld-l2-querier {
                 type string;
                 description
                   "MLD L2 querier";
               }
               leaf l2-querier-source-address {
                 type jt:ipaddr;
               }
               leaf evpn-ssm-reports-only {
                 type string;
                 description
                   "EVPN SSM reports only";
               }
               leaf proto-version {
                 type uint32;
               }
               leaf multicast-router-no-flood {
                 type string;
               }
               leaf flood-reports-to-inter-switch-interface {
                 type string;
               }
               leaf immediate-leave-on-host-interface {
                 type string;
               }
               leaf evpn-query-relay-stop {
                 type string;
               }
             }
           }
         }
       }
     }
   }
   augment "/jgs:genstate" {
     description
       "Adds mld-snooping-interface-information-root container to top-level 
       genstate container";
     uses mld-snooping-interface-information-root-top;
   }
 }
