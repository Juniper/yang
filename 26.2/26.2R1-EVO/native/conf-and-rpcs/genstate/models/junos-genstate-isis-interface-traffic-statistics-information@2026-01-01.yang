module junos-genstate-isis-interface-traffic-statistics-information {
   yang-version 1;
   namespace "http://yang.juniper.net/junos/genstate/isis-interface-traffic-statistics-information";
   prefix jgiitsi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for isis-interface-traffic-statistics-information.

      Copyright (c) 2026 Juniper Networks, Inc.
      All rights reserved.";

   revision 2026-01-01 {
     description "Junos: 26.2R1.7-EVO";
   }

   grouping isis-interface-traffic-statistics-information-top {
     description
       "Top-level grouping";
     container isis-interface-traffic-statistics-information {
       description
         "Top-level container";
       list isis-interface-traffic-statistics {
         key "interface-name";
         description
           "ISIS SPRING aggregate traffic statistics on interface";
         leaf interface-name {
           type string;
           description
             "Name of interface";
         }
         leaf isis-output-bytes {
           type int32;
         }
         leaf isis-output-packets {
           type int32;
         }
       }
     }
   }
   augment "/jgs:genstate" {
     description
       "Adds isis-interface-traffic-statistics-information container to 
       top-level genstate container";
     uses isis-interface-traffic-statistics-information-top;
   }
 }
