module junos-genstate-bgp-output-queue-scheduler {
   yang-version 1;
   namespace "http://yang.juniper.net/junos/genstate/bgp-output-queue-scheduler";
   prefix jgboqs;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for bgp-output-queue-scheduler.

      Copyright (c) 2026 Juniper Networks, Inc.
      All rights reserved.";

   revision 2026-01-01 {
     description "Junos: 26.2R1.7-EVO";
   }

   grouping bgp-output-queue-scheduler-top {
     description
       "Top-level grouping";
     container bgp-output-queue-scheduler {
       description
         "BGP output queue scheduler information";
       leaf bgp-output-queue-scheduler-instance {
         type string;
       }
       list bgp-output-queue-scheduler-classes {
         key "output-queue-class";
         leaf output-queue-class {
           type string;
         }
         leaf output-queue-tokens {
           type int32;
         }
       }
       list bgp-output-queue-scheduler-defaults {
         key "output-queue-default-priority";
         leaf output-queue-default-priority {
           type string;
         }
         leaf output-queue-class {
           type string;
         }
       }
     }
   }
   augment "/jgs:genstate" {
     description
       "Adds bgp-output-queue-scheduler container to top-level genstate 
       container";
     uses bgp-output-queue-scheduler-top;
   }
 }
