module junos-genstate-isis-backup-coverage-information {
   yang-version 1;
   namespace "http://yang.juniper.net/junos/genstate/isis-backup-coverage-information";
   prefix jgibci;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for isis-backup-coverage-information.

      Copyright (c) 2026 Juniper Networks, Inc.
      All rights reserved.";

   revision 2026-01-01 {
     description "Junos: 26.2R1.7-EVO";
   }

   grouping isis-backup-coverage-information-top {
     description
       "Top-level grouping";
     container isis-backup-coverage-information {
       description
         "ISIS backup coverage information";
       list isis-backup-coverage {
         key "isis-topology-id level";
         leaf isis-topology-id {
           type string;
         }
         leaf level {
           type int32;
           description
             "IS-IS Level";
         }
         leaf isis-node-coverage {
           type string;
         }
         leaf isis-route-coverage-ipv4 {
           type string;
         }
         leaf isis-route-coverage-ipv4-mpls {
           type string;
         }
         leaf isis-route-coverage-ipv4-mpls-sspf {
           type string;
         }
         leaf isis-route-coverage-ipv6 {
           type string;
         }
         leaf isis-route-coverage-ipv6-mpls {
           type string;
         }
         leaf isis-route-coverage-ipv6-mpls-sspf {
           type string;
         }
         leaf isis-route-coverage-clns {
           type string;
         }
       }
     }
   }
   augment "/jgs:genstate" {
     description
       "Adds isis-backup-coverage-information container to top-level 
       genstate container";
     uses isis-backup-coverage-information-top;
   }
 }
