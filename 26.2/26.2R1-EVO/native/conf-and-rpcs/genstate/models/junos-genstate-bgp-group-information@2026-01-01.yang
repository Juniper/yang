module junos-genstate-bgp-group-information {
   yang-version 1;
   namespace "http://yang.juniper.net/junos/genstate/bgp-group-information";
   prefix jgbgi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for bgp-group-information.

      Copyright (c) 2026 Juniper Networks, Inc.
      All rights reserved.";

   revision 2026-01-01 {
     description "Junos: 26.2R1.7-EVO";
   }

   grouping bgp-group-information-top {
     description
       "Top-level grouping";
     container bgp-group-information {
       description
         "Operational and configuration information for BGP groups";
       list bgp-group {
         key "name";
         description
           "Operational and configuration information for a BGP group";
         leaf type {
           type string;
         }
         leaf peer-as {
           type int32;
           description
             "Peer AS number";
         }
         leaf local-as {
           type int32;
           description
             "Local AS number";
         }
         leaf group-state {
           type string;
         }
         leaf name {
           type string;
         }
         leaf group-index {
           type int32;
         }
         leaf group-flags {
           type string;
         }
         leaf group-uio-count {
           type int32;
         }
         leaf group-uio-name {
           type string;
         }
         leaf orr {
           type string;
         }
         leaf orr-igp-primary {
           type string;
         }
         leaf orr-igp-backup {
           type string;
         }
         leaf orr-export {
           type string;
         }
         leaf peer-count {
           type int32;
           description
             "Total number of peers";
         }
         leaf established-count {
           type int32;
           description
             "Number of peers within the group that are in the established 
             state";
         }
         leaf-list peer-address {
           type jt:ipaddr;
         }
         leaf uio-group-info {
           type string;
         }
         leaf uio-tuple-dequeued {
           type int32;
         }
         leaf uio-last-sec-rtos-rcvd {
           type int32;
         }
         leaf uio-rto-churn-count {
           type int32;
         }
         leaf uio-cfg-seq {
           type int32;
         }
         leaf uio-dom-id {
           type int32;
         }
         leaf uio-inst-dynid {
           type int32;
         }
         leaf uio-fwd-inst-name {
           type string;
         }
         leaf uio-peer-close-count {
           type int32;
         }
         leaf uio-rtinfo-write-suspend-count {
           type int32;
         }
         leaf bgp-options {
           type string;
         }
         leaf bgp-options2 {
           type string;
         }
         leaf bgp-options-extended {
           type string;
         }
         leaf bgp-options-extended2 {
           type string;
         }
         leaf remove-private-options {
           type string;
         }
         leaf flap-count {
           type int32;
           description
             "Number of times BGP sessions have gone down";
         }
         container route-queue {
           leaf timer {
             type string;
           }
           leaf state {
             type string;
             description
               "HFRR profile Current state";
           }
           leaf element {
             type string;
           }
         }
         container bgp-option-information {
           leaf export-policy {
             type string;
           }
           leaf import-policy {
             type string;
           }
           leaf advertise-bgp-static-policy {
             type string;
           }
           leaf bgp-options {
             type string;
           }
           leaf bgp-options2 {
             type string;
           }
           leaf bgp-options-extended {
             type string;
           }
           leaf bgp-options-extended2 {
             type string;
           }
           leaf remove-private-options {
             type string;
           }
           leaf authentication-key-chain {
             type string;
             description
               "Name of authentication key chain";
           }
           leaf authentication-algorithm {
             type string;
             description
               "Name of authentication algorithm";
           }
           leaf authentication-configured {
             type empty;
           }
           leaf gshut-recv-local-preference {
             type uint32;
           }
           leaf gshut-send-local-preference {
             type uint32;
           }
           leaf holdtime {
             type int32;
             description
               "Delay before timing out the adjacency (default is 180 
               seconds)";
           }
           leaf metric-out {
             type int32;
           }
           leaf preference {
             type int32;
             description
               "Preference for the route";
           }
           leaf local-preference {
             type int32;
           }
           leaf local-as {
             type int32;
             description
               "Local AS number";
           }
           leaf local-as-private {
             type empty;
           }
           leaf local-system-as {
             type int32;
           }
           leaf receive-buffer-size {
             type int32;
           }
           leaf send-buffer-size {
             type int32;
           }
           leaf outbound-timer {
             type int32;
           }
           leaf med-action {
             type string;
           }
           list nlri-policy {
             key "nlri-type";
             leaf nlri-type {
               type string;
               description
                 "Type of NLRI being limited";
             }
             leaf nlri-export-policy {
               type string;
             }
             leaf nlri-import-policy {
               type string;
             }
           }
           container addpath-send {
             leaf nlri-type {
               type string;
               description
                 "Type of NLRI being limited";
             }
             leaf addpath-send-type {
               type string;
             }
             leaf addpath-send-count {
               type int32;
             }
             leaf addpath-send-policy {
               type string;
             }
           }
           container addpath-receive {
             leaf nlri-type {
               type string;
               description
                 "Type of NLRI being limited";
             }
             leaf addpath-receive-type {
               type string;
             }
           }
           container nlri-information {
             leaf nlri-type {
               type string;
               description
                 "Type of NLRI being limited";
             }
             leaf nlri-flow-novalidate {
               type string;
               description
                 "Policy to accept flow routes without validation";
             }
             leaf nlri-output-queue-priority {
               type string;
               description
                 "Default address family output queue priority";
             }
             leaf nlri-route-refresh-priority {
               type string;
               description
                 "Default address family route-refresh priority";
             }
             leaf nlri-withdraw-priority {
               type string;
               description
                 "Default address family withdraw priority";
             }
             container nlri-flags {
               leaf bgp-nlri-flag-explicit-null-for-all-routes {
                 type empty;
               }
               leaf bgp-nlri-flag-explicit-null-for-connected-routes {
                 type empty;
               }
               leaf bgp-nlri-flag-aggregate-label {
                 type empty;
               }
               leaf bgp-nlri-flag-per-prefix-label {
                 type empty;
               }
               leaf bgp-nlri-flag-per-group-label {
                 type empty;
               }
               leaf bgp-nlri-flag-no-install-forwarding {
                 type empty;
               }
               leaf bgp-nlri-flag-rtage-refl-upd-msgs {
                 type empty;
               }
               leaf bgp-nlri-flag-no-resolution {
                 type empty;
               }
               leaf bgp-nlri-flag-resolve-preserve-hier {
                 type empty;
               }
               leaf bgp-nlri-flag-delay-route-advt {
                 type empty;
               }
               leaf bgp-nlri-flag-traffic-stats {
                 type empty;
               }
               leaf bgp-nlri-flag-l2vpn-status-vector {
                 type empty;
               }
               leaf bgp-nlri-flag-no-l2vpn-status-vector {
                 type empty;
               }
               leaf bgp-nlri-flag-accept-local-addr-pnh {
                 type empty;
               }
               leaf bgp-nlri-flag-accept-own {
                 type empty;
               }
               leaf bgp-nlri-flag-strip-nexthop {
                 type empty;
               }
               leaf bgp-nlri-flag-allow-po-add-nexthop {
                 type empty;
               }
               leaf bgp-nlri-flag-per-nexthop-label {
                 type empty;
               }
             }
             container nlri-traffic-stats {
               leaf traffic-stats-interval {
                 type int32;
               }
             }
             container output-queues {
               description
                 "BGP output queues statistics";
               leaf time-series {
                 type string;
               }
             }
           }
         }
         list bgp-rib {
           key "name";
           leaf name {
             type string;
           }
           leaf active-prefix-count {
             type int32;
             description
               "Number of active prefixes";
           }
           leaf suppressed-prefix-count {
             type int32;
             description
               "Number of prefixes suppressed due to damping";
           }
           leaf received-prefix-count {
             type int32;
             description
               "For a peer RIB, number of prefixes received from this peer";
           }
           leaf accepted-prefix-count {
             type int32;
             description
               "For a peer RIB, number of prefixes from this peer accepted 
               by policy";
           }
           leaf advertised-prefix-count {
             type int32;
             description
               "Number of prefixes present in the RIB-OUT";
           }
         }
       }
       container bgp-information {
         description
           "Operational and configuration information for BGP";
         leaf group-count {
           type int32;
         }
         leaf peer-count {
           type int32;
           description
             "Total number of peers";
         }
         leaf external-peer-count {
           type int32;
         }
         leaf internal-peer-count {
           type int32;
         }
         leaf down-peer-count {
           type int32;
         }
         leaf flap-count {
           type int32;
           description
             "Number of times BGP sessions have gone down";
         }
         leaf default-ebgp-advertise-mode {
           type string;
           description
             "Default eBGP advertisement mode";
         }
         leaf default-ebgp-receive-mode {
           type string;
           description
             "Default eBGP receive mode";
         }
         container bgp-updio-globals {
           leaf bgp-updio-cfg-seq {
             type int32;
           }
           leaf bgp-updio-shutting-down {
             type int32;
           }
           leaf bgp-updio-shutdown-rcvd {
             type string;
           }
           leaf bgp-updio-shutdown-sent {
             type int32;
           }
           leaf bgp-updio-gc-timer {
             type int32;
           }
           leaf bgp-updio-gc-count {
             type int32;
           }
           leaf bgp-updio-gc-job {
             type string;
           }
         }
         list bgp-rib {
           key "name";
           leaf name {
             type string;
           }
           leaf total-prefix-count {
             type int32;
             description
               "Total number of prefixes in this RIB";
           }
           leaf active-prefix-count {
             type int32;
             description
               "Number of active prefixes";
           }
           leaf history-prefix-count {
             type int32;
             description
               "Number of prefixes with damping history maintained";
           }
           leaf damped-prefix-count {
             type int32;
             description
               "Number of prefixes in any damped state";
           }
           leaf pending-prefix-count {
             type int32;
             description
               "Number of prefixes with pending changes";
           }
           leaf received-prefix-count {
             type int32;
             description
               "For a peer RIB, number of prefixes received from this peer";
           }
           leaf accepted-prefix-count {
             type int32;
             description
               "For a peer RIB, number of prefixes from this peer accepted 
               by policy";
           }
           leaf active-external-prefix-count {
             type int32;
             description
               "Number of active prefixes received from external peers";
           }
           leaf total-external-prefix-count {
             type int32;
             description
               "Total number of prefixes received from external peers";
           }
           leaf accepted-external-prefix-count {
             type int32;
             description
               "Number of accepted prefixes received from external peers";
           }
           leaf suppressed-external-prefix-count {
             type int32;
             description
               "Number of external prefixes suppressed due to damping";
           }
           leaf active-internal-prefix-count {
             type int32;
             description
               "Number of active prefixes received from internal peers";
           }
           leaf total-internal-prefix-count {
             type int32;
             description
               "Total number of prefixes received from internal peers";
           }
           leaf accepted-internal-prefix-count {
             type int32;
             description
               "Number of accepted prefixes received from internal peers";
           }
           leaf suppressed-internal-prefix-count {
             type int32;
             description
               "Number of internal prefixes suppressed due to damping";
           }
         }
       }
     }
   }
   augment "/jgs:genstate" {
     description
       "Adds bgp-group-information container to top-level genstate container";
     uses bgp-group-information-top;
   }
 }
