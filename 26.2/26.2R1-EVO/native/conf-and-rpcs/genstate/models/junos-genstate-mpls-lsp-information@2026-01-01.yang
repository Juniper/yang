module junos-genstate-mpls-lsp-information {
   yang-version 1;
   namespace "http://yang.juniper.net/junos/genstate/mpls-lsp-information";
   prefix jgmli;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for mpls-lsp-information.

      Copyright (c) 2026 Juniper Networks, Inc.
      All rights reserved.";

   revision 2026-01-01 {
     description "Junos: 26.2R1.7-EVO";
   }

   grouping mpls-lsp-information-top {
     description
       "Top-level grouping";
     container mpls-lsp-information {
       description
         "Top-level container";
       list rsvp-session-data {
         key "session-type";
         leaf session-type {
           type string;
           description
             "Type of session with respect to this router";
         }
         leaf count {
           type int32;
         }
         leaf display-count {
           type int32;
           description
             "Number of sessions displayed";
         }
         leaf up-count {
           type int32;
           description
             "Number of sessions in up state";
         }
         leaf down-count {
           type int32;
           description
             "Number of sessions in down state";
         }
         list rsvp-session {
           key "name";
           description
             "Single RSVP session";
           leaf destination-address {
             type jt:ipaddr;
             description
               "Session destination address";
           }
           leaf source-address {
             type jt:ipaddr;
           }
           leaf lsp-state {
             type string;
             description
               "State of an LSP";
           }
           leaf route-count {
             type int32;
             description
               "Number of active routes";
           }
           leaf rsb-count {
             type int32;
             description
               "Number of RSBs";
           }
           leaf resv-style {
             type string;
           }
           leaf label-in {
             type string;
             description
               "Incoming label";
           }
           leaf label-out {
             type string;
             description
               "Outgoing label";
           }
           leaf name {
             type string;
           }
           leaf bidirectional {
             type empty;
             description
               "LSP is bidirectional";
           }
           leaf associated-bidirectional {
             type empty;
             description
               "LSP is associated-bidirectional";
           }
         }
       }
       list mpls-lsp-autobandwidth-information {
         key "lsp-name";
         leaf lsp-name {
           type string;
           description
             "Tunneled into an RSVP LSP";
         }
         leaf autobw-last-bw {
           type string;
         }
         leaf autobw-requested-bw {
           type string;
         }
         leaf autobw-signaled-bw {
           type string;
         }
         leaf autobw-high-watermark-bw {
           type string;
           description
             "Highest BW sample seen so far in LSP life time";
         }
         leaf autobw-time-to-adjust {
           type string;
         }
         leaf autobw-time-last-adjust {
           type string;
         }
         leaf destination-address {
           type jt:ipaddr;
           description
             "Session destination address";
         }
         leaf source-address {
           type jt:ipaddr;
         }
         leaf autobw-monitor-lsp-bandwidth {
           type empty;
         }
         leaf autobw-minimum-bandwidth {
           type string;
         }
         leaf autobw-maximum-bandwidth {
           type string;
         }
         leaf autobw-max-average-bandwidth {
           type string;
         }
         leaf polling-profile {
           type string;
         }
         leaf statistics-interval {
           type int32;
         }
         leaf overflow-limit {
           type int32;
           description
             "Configured limit of consecutive overflow samples for LSP";
         }
         leaf overflow-sample-count {
           type int32;
           description
             "Number of consecutive overflow samples encountered";
         }
         leaf overflow-threshold {
           type int32;
         }
         leaf underflow-limit {
           type int32;
           description
             "Configured limit of consecutive underflow samples for LSP";
         }
         leaf underflow-sample-count {
           type int32;
           description
             "Number of consecutive underflow samples encountered";
         }
         leaf underflow-threshold {
           type int32;
         }
         leaf underflow-max-avg-bandwidth {
           type string;
           description
             "Highest average bandwidth recorded so far for underflow 
             samples";
         }
         leaf autobw-adjust-timer {
           type string;
           description
             "Configured LSP adjust timer";
         }
         leaf autobw-adjust-threshold {
           type int32;
         }
         leaf autobw-adjust-threshold-absolute {
           type string;
         }
         leaf autobw-adjust-threshold-activate-bandwidth {
           type string;
         }
         leaf autobw-total-adjustments {
           type int32;
           description
             "Total number of autobandwidth adjustment attempts";
         }
         leaf autobw-total-successful-adjustments {
           type int32;
           description
             "Total number of successful autobandwidth adjustments";
         }
         leaf autobw-total-unsuccessful-adjustments {
           type int32;
           description
             "Total number of unsuccessful autobandwidth adjustments";
         }
       }
     }
   }
   augment "/jgs:genstate" {
     description
       "Adds mpls-lsp-information container to top-level genstate container";
     uses mpls-lsp-information-top;
   }
 }
