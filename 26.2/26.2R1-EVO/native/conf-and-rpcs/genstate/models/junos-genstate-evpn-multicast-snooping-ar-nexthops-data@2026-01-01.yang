module junos-genstate-evpn-multicast-snooping-ar-nexthops-data {
   yang-version 1;
   namespace "http://yang.juniper.net/junos/genstate/evpn-multicast-snooping-ar-nexthops-data";
   prefix jgemsand;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for evpn-multicast-snooping-ar-nexthops-data.

      Copyright (c) 2026 Juniper Networks, Inc.
      All rights reserved.";

   revision 2026-01-01 {
     description "Junos: 26.2R1.7-EVO";
   }

   grouping evpn-multicast-snooping-ar-nexthops-data-top {
     description
       "Top-level grouping";
     container evpn-multicast-snooping-ar-nexthops-data {
       description
         "Top-level container";
       list evpn-multicast-snooping-ar-nexthops-per-instance {
         key "evpn-instance-name";
         leaf evpn-instance-name {
           type string;
         }
         leaf evpn-ar-role {
           type string;
         }
         list evpn-multicast-snooping-ar-nexthops-per-domain {
           key "vni-id";
           leaf vni-id {
             type int32;
           }
           leaf evpn-ar-load-balance-nexthop-index {
             type int32;
           }
           list evpn-ar-load-balance-nexthops-member {
             key "evpn-neighbor-nexthop-index";
             leaf evpn-neighbor-nexthop-index {
               type int32;
             }
             leaf evpn-neighbor-interface {
               type string;
             }
             leaf evpn-ar-ip {
               type jt:ipaddr;
             }
             leaf designated-node {
               type empty;
             }
           }
         }
       }
     }
   }
   augment "/jgs:genstate" {
     description
       "Adds evpn-multicast-snooping-ar-nexthops-data container to top-level
       genstate container";
     uses evpn-multicast-snooping-ar-nexthops-data-top;
   }
 }
