module junos-genstate-msdp-statistics-information {
   yang-version 1;
   namespace "http://yang.juniper.net/junos/genstate/msdp-statistics-information";
   prefix jgmsi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for msdp-statistics-information.

      Copyright (c) 2026 Juniper Networks, Inc.
      All rights reserved.";

   revision 2026-01-01 {
     description "Junos: 26.2R1.7-EVO";
   }

   grouping msdp-statistics-information-top {
     description
       "Top-level grouping";
     container msdp-statistics-information {
       description
         "Top-level container";
       list msdp-instance {
         key "instance-name";
         leaf instance-name {
           type string;
         }
         leaf msdp-global-active-source-limit-exceeded {
           type uint32;
         }
         leaf msdp-global-active-source-limit-maximum {
           type uint32;
         }
         leaf msdp-global-active-source-limit-threshold {
           type uint32;
         }
         leaf msdp-global-active-source-limit-log-warning {
           type uint32;
         }
         leaf msdp-global-active-source-limit-log-interval {
           type uint32;
         }
         list msdp-peer-statistics {
           key "msdp-peer-address";
           leaf msdp-peer-address {
             type jt:ipaddr;
           }
           leaf msdp-state-change-absolute {
             type string;
           }
           leaf msdp-state-change {
             type string;
           }
           leaf msdp-message-received-absolute {
             type string;
           }
           leaf msdp-message-received {
             type string;
           }
           leaf msdp-rpf-failures {
             type int32;
           }
           leaf msdp-remote-closes {
             type int32;
           }
           leaf msdp-peer-timeouts {
             type int32;
           }
           leaf msdp-sa-messages-sent {
             type int32;
           }
           leaf msdp-sa-messages-received {
             type int32;
           }
           leaf msdp-sa-requests-sent {
             type int32;
           }
           leaf msdp-sa-requests-received {
             type int32;
           }
           leaf msdp-sa-responses-sent {
             type int32;
           }
           leaf msdp-sa-responses-received {
             type int32;
           }
           leaf msdp-active-source-limit-exceeded {
             type int32;
           }
           leaf msdp-active-source-limit-maximum {
             type uint32;
           }
           leaf msdp-active-source-limit-threshold {
             type uint32;
           }
           leaf msdp-active-source-limit-log-warning {
             type uint32;
           }
           leaf msdp-active-source-limit-log-interval {
             type uint32;
           }
           leaf msdp-keepalives-sent {
             type int32;
           }
           leaf msdp-keepalives-received {
             type int32;
           }
           leaf msdp-unknowns-received {
             type int32;
           }
           leaf msdp-sa-zero-entry-received {
             type uint32;
           }
           leaf msdp-errors-received {
             type int32;
           }
         }
       }
     }
   }
   augment "/jgs:genstate" {
     description
       "Adds msdp-statistics-information container to top-level genstate 
       container";
     uses msdp-statistics-information-top;
   }
 }
