module junos-genstate-msdp-source-information {
   yang-version 1;
   namespace "http://yang.juniper.net/junos/genstate/msdp-source-information";
   prefix jgmsi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for msdp-source-information.

      Copyright (c) 2026 Juniper Networks, Inc.
      All rights reserved.";

   revision 2026-01-01 {
     description "Junos: 26.2R1.7-EVO";
   }

   grouping msdp-source-information-top {
     description
       "Top-level grouping";
     container msdp-source-information {
       description
         "Top-level container";
       list msdp-instance {
         key "instance-name";
         leaf instance-name {
           type string;
         }
         list msdp-source {
           key "msdp-source-prefix";
           leaf msdp-source-prefix {
             type jt:ipaddr;
           }
           leaf msdp-source-prefix-length {
             type uint32;
           }
           leaf msdp-source-type {
             type string;
           }
           leaf msdp-source-limit-maximum {
             type string;
           }
           leaf msdp-source-limit-threshold {
             type string;
           }
           leaf msdp-source-limit-exceeded {
             type int32;
           }
           leaf msdp-source-limit-log-warning {
             type string;
           }
           leaf msdp-source-limit-log-interval {
             type string;
           }
         }
       }
     }
   }
   augment "/jgs:genstate" {
     description
       "Adds msdp-source-information container to top-level genstate 
       container";
     uses msdp-source-information-top;
   }
 }
