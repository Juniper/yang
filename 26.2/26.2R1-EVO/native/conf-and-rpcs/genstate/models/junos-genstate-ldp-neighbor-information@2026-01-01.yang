module junos-genstate-ldp-neighbor-information {
   yang-version 1;
   namespace "http://yang.juniper.net/junos/genstate/ldp-neighbor-information";
   prefix jglni;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for ldp-neighbor-information.

      Copyright (c) 2026 Juniper Networks, Inc.
      All rights reserved.";

   revision 2026-01-01 {
     description "Junos: 26.2R1.7-EVO";
   }

   grouping ldp-neighbor-information-top {
     description
       "Top-level grouping";
     container ldp-neighbor-information {
       description
         "Top-level container";
       list ldp-neighbor {
         key "ldp-neighbor-address";
         leaf ldp-neighbor-address {
           type jt:ipaddr;
         }
         leaf interface-name {
           type string;
           description
             "Name of interface";
         }
         leaf ldp-label-space-id {
           type string;
         }
         leaf ldp-remaining-time {
           type int32;
         }
         leaf ldp-local-transport-address {
           type jt:ipaddr;
         }
         leaf ldp-transport-address {
           type jt:ipaddr;
         }
         leaf ldp-transport-preference {
           type string;
         }
         leaf ldp-config-sequence {
           type uint32;
         }
         leaf ldp-up-time {
           type string;
         }
         leaf ldp-reference-count {
           type int32;
         }
         leaf ldp-auto-discovered-reference-count {
           type int32;
         }
         leaf ldp-holdtime {
           type int32;
         }
         leaf ldp-proposed-local-holdtime {
           type int32;
           description
             "The local value of the hold time";
         }
         leaf ldp-proposed-peer-holdtime {
           type int32;
           description
             "The peer's proposed value of the hold time";
         }
         leaf ldp-hello-interval {
           type int32;
         }
         container ldp-neighbor-hello-flags {
           description
             "LDP neighbor hello flags";
           leaf-list ldp-neighbor-hello-flag {
             type string;
             description
               "LDP neighbor hello flag";
           }
         }
         container ldp-neighbor-types {
           description
             "LDP neighbor types";
           leaf-list ldp-neighbor-type {
             type string;
             description
               "LDP neighbor type";
           }
         }
       }
     }
   }
   augment "/jgs:genstate" {
     description
       "Adds ldp-neighbor-information container to top-level genstate 
       container";
     uses ldp-neighbor-information-top;
   }
 }
