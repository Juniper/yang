module junos-genstate-spring-te-bfd-session-information {
   yang-version 1;
   namespace "http://yang.juniper.net/junos/genstate/spring-te-bfd-session-information";
   prefix jgstbsi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for spring-te-bfd-session-information.

      Copyright (c) 2026 Juniper Networks, Inc.
      All rights reserved.";

   revision 2026-01-01 {
     description "Junos: 26.2R1.7-EVO";
   }

   grouping spring-te-bfd-session-information-top {
     description
       "Top-level grouping";
     container spring-te-bfd-session-information {
       description
         "Top-level container";
       list spring-te-bfd-session {
         key "stl-path-bfd-name";
         leaf stl-path-bfd-name {
           type string;
         }
         leaf stl-path-bfd-status {
           type string;
         }
         container ste-bfd-ref-lsps {
           leaf-list ste-bfd-ref-lsp {
             type string;
           }
         }
         container stl-sr-ero-list {
           leaf stl-sr-ero-num-eros {
             type uint32;
           }
           list stl-sr-ero {
             key "stl-sr-ero-index";
             leaf stl-sr-ero-index {
               type uint32;
             }
             leaf stl-sr-ero-sid-value {
               type uint32;
             }
             leaf stl-sr-ero-sid-ttl {
               type uint32;
             }
             leaf stl-sr-ero-sid-exp {
               type uint32;
             }
           }
         }
         container stl-srv6-bfd-compressed-sid-list {
           leaf stl-srv6-bfd-compressed-num-sid {
             type uint32;
           }
           list stl-srv6-bfd-compressed-sid-info {
             key "stl-srv6-bfd-compressed-sid-index";
             leaf stl-srv6-bfd-compressed-sid-index {
               type string;
             }
             leaf stl-srv6-bfd-compressed-sid {
               type jt:ipaddr;
             }
           }
         }
         leaf stl-path-bfd-destination {
           type jt:ipaddr;
         }
         leaf stl-path-bfd-error-message {
           type string;
         }
         leaf stl-path-bfd-remote-discriminator {
           type uint32;
         }
         leaf stl-path-bfd-local-discriminator {
           type uint32;
         }
       }
       container spring-te-bfd-session-counts {
         leaf ste-bfd-session-total {
           type uint32;
         }
         leaf ste-bfd-session-up {
           type uint32;
         }
         leaf ste-bfd-session-down {
           type uint32;
         }
       }
     }
   }
   augment "/jgs:genstate" {
     description
       "Adds spring-te-bfd-session-information container to top-level 
       genstate container";
     uses spring-te-bfd-session-information-top;
   }
 }
