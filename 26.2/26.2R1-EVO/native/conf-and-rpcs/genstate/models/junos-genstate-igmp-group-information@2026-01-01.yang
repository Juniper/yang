module junos-genstate-igmp-group-information {
   yang-version 1;
   namespace "http://yang.juniper.net/junos/genstate/igmp-group-information";
   prefix jgigi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for igmp-group-information.

      Copyright (c) 2026 Juniper Networks, Inc.
      All rights reserved.";

   revision 2026-01-01 {
     description "Junos: 26.2R1.7-EVO";
   }

   grouping igmp-group-information-top {
     description
       "Top-level grouping";
     container igmp-group-information {
       description
         "Top-level container";
       list mgm-interface-groups {
         key "interface-name";
         leaf interface-name {
           type string;
           description
             "Name of interface";
         }
         leaf mgm-group-count {
           type int32;
         }
         list mgm-group {
           key "multicast-group-address";
           leaf multicast-group-address {
             type jt:ipaddr;
             description
               "Group address";
           }
           leaf mgm-group-mode-type {
             type string;
             description
               "Group operational mode (Include/Exclude).";
           }
           leaf multicast-source-address {
             type jt:ipaddr;
             description
               "Source address";
           }
           leaf last-address {
             type jt:ipaddr;
           }
           leaf mgm-timeout {
             type int32;
           }
           leaf mgm-type {
             type string;
           }
           leaf mgm-source-timeout {
             type int32;
             description
               "Amount of time for which the traffic from source is 
               forwarded.";
           }
           leaf mgm-type-instance {
             type string;
           }
           leaf mgm-group-output-interface {
             type string;
             description
               "Group output interface";
           }
         }
       }
     }
   }
   augment "/jgs:genstate" {
     description
       "Adds igmp-group-information container to top-level genstate 
       container";
     uses igmp-group-information-top;
   }
 }
