module junos-genstate-mvpn-instance-information {
   yang-version 1;
   namespace "http://yang.juniper.net/junos/genstate/mvpn-instance-information";
   prefix jgmii;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for mvpn-instance-information.

      Copyright (c) 2026 Juniper Networks, Inc.
      All rights reserved.";

   revision 2026-01-01 {
     description "Junos: 26.2R1.7-EVO";
   }

   grouping mvpn-instance-information-top {
     description
       "Top-level grouping";
     container mvpn-instance-information {
       description
         "Top-level container";
       container mvpn-instance {
         list instance-family {
           key "address-family";
           leaf address-family {
             type string;
           }
           list instance-entry {
             key "instance-name";
             leaf instance-name {
               type string;
             }
             leaf ngen-mvpn-mode {
               type string;
               description
                 "MVPN mode of operation";
             }
             leaf ngen-mvpn-hmcnh-usage {
               type string;
               description
                 "Forwarding Entry hierarchical nh usage";
             }
             leaf ngen-mvpn-sel-tun-nh-shared {
               type string;
               description
                 "Forwarding Entry for selective tunnel nh share usage";
             }
             leaf sender-based-rpf-status {
               type string;
               description
                 "Sender-Based RPF status";
             }
             leaf hot-root-standby-status {
               type string;
               description
                 "Hot Root Standby status";
             }
             container provider-tunnel {
               leaf provider-tunnel-id {
                 type string;
                 description
                   "Provider tunnel identifier";
               }
             }
             container neighbor {
               list neighbor-entry {
                 key "neighbor-identifier";
                 leaf neighbor-identifier {
                   type string;
                   description
                     "Neighbor IPv4 address";
                 }
                 leaf provider-tunnel-id {
                   type string;
                   description
                     "Provider tunnel identifier";
                 }
                 leaf label-in {
                   type string;
                   description
                     "Incoming label";
                 }
                 leaf neighbor-property {
                   type string;
                   description
                     "Special properties of the neighbor";
                 }
                 container mvpn-downstream-ptnl-segment {
                   list mvpn-downstream-ptnl-segment-entry {
                     key "mvpn-downstream-segment-name";
                     leaf provider-tunnel-id {
                       type string;
                       description
                         "Provider tunnel identifier";
                     }
                     leaf mvpn-downstream-segment-name {
                       type string;
                       description
                         "Downstream p-tunnel segment name";
                     }
                   }
                 }
               }
             }
             container c-multicast-ipv4 {
               list c-multicast-ipv4-entry {
                 key "c-multicast-address";
                 leaf c-multicast-address {
                   type string;
                   description
                     "Address of the c-multicast route";
                 }
                 leaf provider-tunnel-id {
                   type string;
                   description
                     "Provider tunnel identifier";
                 }
                 leaf label-in {
                   type string;
                   description
                     "Incoming label";
                 }
                 leaf c-multicast-property {
                   type string;
                   description
                     "Special properties of the c-multicast route";
                 }
                 leaf c-multicast-fwd-nh {
                   type string;
                   description
                     "C-multicast route Forwarding NH Id";
                 }
                 leaf backup-provider-tunnel-id {
                   type string;
                   description
                     "Backup Provider tunnel identifier";
                 }
                 leaf c-backup-multicast-fwd-nh {
                   type string;
                   description
                     "C-multicast route Forwarding NH Id for backup ptnl";
                 }
                 container mvpn-downstream-ptnl-segment {
                   list mvpn-downstream-ptnl-segment-entry {
                     key "mvpn-downstream-segment-name";
                     leaf provider-tunnel-id {
                       type string;
                       description
                         "Provider tunnel identifier";
                     }
                     leaf mvpn-downstream-segment-name {
                       type string;
                       description
                         "Downstream p-tunnel segment name";
                     }
                   }
                 }
               }
             }
             container c-multicast-ipv6 {
               list c-multicast-ipv6-entry {
                 key "c-multicast-address";
                 leaf c-multicast-address {
                   type string;
                   description
                     "Address of the c-multicast route";
                 }
                 leaf provider-tunnel-id {
                   type string;
                   description
                     "Provider tunnel identifier";
                 }
                 leaf label-in {
                   type string;
                   description
                     "Incoming label";
                 }
                 leaf c-multicast-property {
                   type string;
                   description
                     "Special properties of the c-multicast route";
                 }
                 leaf c-multicast-fwd-nh {
                   type string;
                   description
                     "C-multicast route Forwarding NH Id";
                 }
                 leaf backup-provider-tunnel-id {
                   type string;
                   description
                     "Backup Provider tunnel identifier";
                 }
                 leaf c-backup-multicast-fwd-nh {
                   type string;
                   description
                     "C-multicast route Forwarding NH Id for backup ptnl";
                 }
                 container mvpn-downstream-ptnl-segment {
                   list mvpn-downstream-ptnl-segment-entry {
                     key "mvpn-downstream-segment-name";
                     leaf provider-tunnel-id {
                       type string;
                       description
                         "Provider tunnel identifier";
                     }
                     leaf mvpn-downstream-segment-name {
                       type string;
                       description
                         "Downstream p-tunnel segment name";
                     }
                   }
                 }
               }
             }
             container inter-as-provider-tunnel {
               leaf provider-tunnel-id {
                 type string;
                 description
                   "Provider tunnel identifier";
               }
             }
           }
         }
       }
       container mvpn-instance-src-pe {
         list instance-family {
           key "address-family";
           leaf address-family {
             type string;
           }
           list instance-entry {
             key "instance-name";
             leaf instance-name {
               type string;
             }
             leaf ngen-mvpn-mode {
               type string;
               description
                 "MVPN mode of operation";
             }
             list c-multicast-source-pe-cmcast-addr {
               key "c-multicast-address";
               leaf c-multicast-address {
                 type string;
                 description
                   "Address of the c-multicast route";
               }
               container c-multicast-source-pe {
                 leaf mvpn-src-pe-string {
                   type string;
                   description
                     "Name of interface";
                 }
                 leaf-list extended-community {
                   type string;
                   description
                     "Extended community";
                 }
                 leaf route-distinguisher {
                   type string;
                   description
                     "Name of the route-distinguisher";
                 }
                 leaf as-number {
                   type int32;
                 }
                 leaf mvpn-interface-name {
                   type string;
                   description
                     "Name of interface";
                 }
                 leaf mvpn-interface-index {
                   type int32;
                   description
                     "Index of interface";
                 }
               }
               container c-multicast-pim-source-pe {
                 leaf pim-src-pe-string {
                   type string;
                   description
                     "Name of interface";
                 }
                 leaf-list extended-community {
                   type string;
                   description
                     "Extended community";
                 }
                 leaf route-distinguisher {
                   type string;
                   description
                     "Name of the route-distinguisher";
                 }
                 leaf as-number {
                   type int32;
                 }
                 leaf mvpn-interface-name {
                   type string;
                   description
                     "Name of interface";
                 }
                 leaf mvpn-interface-index {
                   type int32;
                   description
                     "Index of interface";
                 }
               }
             }
           }
         }
       }
     }
   }
   augment "/jgs:genstate" {
     description
       "Adds mvpn-instance-information container to top-level genstate 
       container";
     uses mvpn-instance-information-top;
   }
 }
