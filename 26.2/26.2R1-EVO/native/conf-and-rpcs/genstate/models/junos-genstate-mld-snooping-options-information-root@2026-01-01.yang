module junos-genstate-mld-snooping-options-information-root {
   yang-version 1;
   namespace "http://yang.juniper.net/junos/genstate/mld-snooping-options-information-root";
   prefix jgmsoir;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for mld-snooping-options-information-root.

      Copyright (c) 2026 Juniper Networks, Inc.
      All rights reserved.";

   revision 2026-01-01 {
     description "Junos: 26.2R1.7-EVO";
   }

   grouping mld-snooping-options-information-root-top {
     description
       "Top-level grouping";
     container mld-snooping-options-information-root {
       description
         "Top-level container";
       list mgm-snooping-options-information-per-instance {
         key "instance-name";
         leaf instance-name {
           type string;
         }
         leaf p2mp-lsp-in-use {
           type string;
         }
         leaf snoop-pw-in-use {
           type string;
         }
       }
     }
   }
   augment "/jgs:genstate" {
     description
       "Adds mld-snooping-options-information-root container to top-level 
       genstate container";
     uses mld-snooping-options-information-root-top;
   }
 }
