module junos-genstate-commit-synchronize-server {
   yang-version 1;
   namespace "http://yang.juniper.net/junos/genstate/commit-synchronize-server";
   prefix jgcss;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for commit-synchronize-server.

      Copyright (c) 2026 Juniper Networks, Inc.
      All rights reserved.";

   revision 2026-01-01 {
     description "Junos: 26.2R1.7-EVO";
   }

   grouping commit-synchronize-server-top {
     description
       "Top-level grouping";
     container commit-synchronize-server {
       description
         "Show commit synchronize server information";
       list commit-sync-jobs {
         key "job-id";
         description
           "Commit sync jobs details";
         leaf job-id {
           type int32;
           description
             "Job id";
         }
         leaf commit-sync-model {
           type string;
           description
             "Commit synchronize model";
         }
         leaf database {
           type string;
           description
             "Type of database";
         }
         leaf database-version {
           type string;
           description
             "New commit version";
         }
       }
     }
   }
   augment "/jgs:genstate" {
     description
       "Adds commit-synchronize-server container to top-level genstate 
       container";
     uses commit-synchronize-server-top;
   }
 }
