module junos-genstate-route-information {
   yang-version 1;
   namespace "http://yang.juniper.net/junos/genstate/route-information";
   prefix jgri;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for route-information.

      Copyright (c) 2026 Juniper Networks, Inc.
      All rights reserved.";

   revision 2026-01-01 {
     description "Junos: 26.2R1.7-EVO";
   }

   grouping route-information-top {
     description
       "Top-level grouping";
     container route-information {
       description
         "Top-level container";
       leaf as-number {
         type int32;
       }
       leaf router-id {
         type jt:ipaddr;
       }
       leaf maximum-ecmp {
         type int32;
       }
       leaf note-network-services-mode {
         type string;
       }
       list route-table {
         key "table-name";
         leaf table-name {
           type string;
           description
             "Unicast routing table";
         }
         leaf destination-count {
           type int32;
           description
             "Number of destinations in this rib";
         }
         leaf total-route-count {
           type int32;
         }
         leaf active-route-count {
           type int32;
           description
             "Active routes";
         }
         leaf holddown-route-count {
           type int32;
         }
         leaf hidden-route-count {
           type int32;
         }
         leaf restart-state {
           type string;
         }
         leaf family-prefix-max {
           type int32;
         }
         leaf family-prefix-threshold {
           type int32;
         }
         leaf family-prefix-label {
           type string;
         }
         leaf family-route-max {
           type int32;
         }
         leaf family-route-threshold {
           type int32;
         }
         leaf family-route-limit-label {
           type string;
         }
         leaf global-prefix-max {
           type int32;
         }
         leaf global-prefix-threshold {
           type int32;
         }
         leaf global-prefix-label {
           type string;
         }
         leaf global-route-max {
           type int32;
         }
         leaf global-route-threshold {
           type int32;
         }
         leaf global-route-limit-label {
           type string;
         }
         leaf prefix-max {
           type int32;
         }
         leaf prefix-threshold {
           type int32;
         }
         leaf prefix-label {
           type string;
         }
         leaf route-max {
           type int32;
         }
         leaf route-threshold {
           type int32;
         }
         leaf route-limit-label {
           type string;
         }
         list protocols {
           key "protocol-name";
           leaf protocol-name {
             type string;
           }
           leaf protocol-route-count {
             type int32;
             description
               "Total protocol routes";
           }
           leaf active-route-count {
             type int32;
             description
               "Active routes";
           }
         }
         list rt {
           key "rt-destination";
           leaf rt-destination {
             type string;
             description
               "Route prefixes awaiting ACK";
           }
           leaf rt-prefix-length {
             type string;
           }
           list rt-entry {
             leaf active-tag {
               type string;
               description
                 "Visual indication of active state of this route entry";
             }
             leaf validation-state {
               type string;
               description
                 "Validation-state of a route";
             }
             leaf protocol-name {
               type string;
             }
             leaf preference {
               type int32;
               description
                 "Preference for the route";
             }
             leaf metric {
               type int32;
             }
             leaf metric2 {
               type int32;
             }
             leaf nh-type {
               type string;
               description
                 "Special next hop: Reject, Blackhole, Receive, Multicast, 
                 Local, or Unused";
             }
             leaf as-path {
               type string;
               description
                 "Name of AS path regular expression (BGP only)";
             }
             leaf last-active {
               type empty;
               description
                 "This route entry was the last active route entry";
             }
             leaf current-active {
               type empty;
               description
                 "This route entry is currently active";
             }
             leaf bgp-rt-mult-nh-idx {
               type uint32;
               description
                 "BGP multipath nexthop index";
             }
             leaf deleted {
               type empty;
             }
             container route-record {
               leaf rt-recorded {
                 type string;
               }
               leaf nh-address {
                 type string;
                 description
                   "Address of next hop";
               }
               leaf as-index {
                 type int32;
               }
               leaf as-recorded {
                 type string;
               }
               leaf com-index {
                 type int32;
               }
               leaf com-recorded {
                 type string;
               }
             }
             list route-data-dcf {
               key "trunk-id snmp-idx";
               leaf trunk-id {
                 type int32;
                 description
                   "Trunk Identifier associated with the LAG port";
               }
               leaf snmp-idx {
                 type int32;
                 description
                   "IFD SNMP index";
               }
               leaf ts {
                 type int32;
                 description
                   "Timestamp associated with the route";
               }
               leaf class-id {
                 type int32;
                 description
                   "Class identifier associated with the route";
               }
               leaf rt-flags {
                 type string;
                 description
                   "Flags associated with the route";
               }
               leaf rt-type {
                 type string;
                 description
                   "Route type associated with the route";
               }
               leaf rt-proto {
                 type string;
                 description
                   "Protocol associated with the route";
               }
               leaf rt-l2domain {
                 type int32;
                 description
                   "L2domain associated with the route";
               }
               leaf rt-mac-addr {
                 type jt:mac-addr;
                 description
                   "Mac address associated with the route";
               }
               list snpa {
                 key "snpa-type";
                 leaf snpa-type {
                   type string;
                   description
                     "Type of SNPA";
                 }
                 list pfe-port-snpa {
                   key "pfe-id";
                   description
                     "PFE Port SNPA";
                   leaf pfe-id {
                     type int32;
                   }
                   leaf port-id {
                     type int32;
                   }
                 }
                 container network-element-port-snpa {
                   description
                     "Network Element Port SNPA";
                 }
                 container mstp-root-snpa {
                   description
                     "Multiple Spanning Tree Protocol Root SNPA";
                   leaf mstp-root-id {
                     type int32;
                   }
                 }
                 list gateway-snpa {
                   key "gateway-addr";
                   description
                     "Gateway SNPA";
                   leaf gateway-addr {
                     type jt:ipaddr;
                   }
                 }
                 container layer2-domain-port-snpa {
                   description
                     "Layer-2 Domain Port SNPA";
                 }
                 container replication-block-snpa {
                   description
                     "Replication Block SNPA";
                   leaf replication-block-id {
                     type int32;
                   }
                 }
                 container replication-route-snpa {
                   description
                     "Replication Route SNPA";
                   leaf network-element-id {
                     type jt:ipaddr;
                   }
                 }
                 container layer2-multicast-port-snpa {
                   description
                     "Layer-2 Multicast Port SNPA";
                   leaf layer2-multicast-port-id {
                     type int32;
                   }
                 }
                 container inh-snpa {
                   description
                     "Indirection SNPA";
                   leaf inh-id {
                     type int32;
                   }
                 }
               }
               leaf snpa-count {
                 type int32;
                 description
                   "Number of SNPAs in this route";
               }
               leaf snpa-length {
                 type int32;
                 description
                   "Total length of the SNPAs, in bytes";
               }
               container multicast-member-map-data {
                 description
                   "Multicast member map";
                 leaf multicast-root-hash {
                   type int32;
                 }
                 leaf multicast-core-hash {
                   type int32;
                 }
                 leaf multicast-edge-hash {
                   type int32;
                 }
                 leaf multicast-member-map {
                   type string;
                 }
               }
               container layer3-multicast-data {
                 description
                   "Layer3 multicast core key";
                 leaf layer3-multicast-corekey {
                   type int32;
                 }
               }
               container multicast-vsg-corekey-data {
                 description
                   "Vsg multicast core key";
                 leaf multicast-vsg-corekey-key {
                   type int32;
                 }
                 leaf multicast-vsg-corekey-len {
                   type int32;
                 }
               }
             }
             container rtd-flow-dep {
               leaf flow-dep-state {
                 type string;
               }
               leaf flow-origin {
                 type jt:ipaddr;
                 description
                   "Originator of the flow information";
               }
               leaf flow-next-as {
                 type uint32;
                 description
                   "Neighbor AS of the flow information";
               }
               container flow-ucast-rt {
                 description
                   "Unicast route used for resolution";
                 leaf flow-rtn-dest {
                   type jt:ipaddr;
                   description
                     "Destination address";
                 }
                 leaf flow-rtn-plen {
                   type int32;
                   description
                     "Prefix length";
                 }
                 leaf flow-rtn-state {
                   type string;
                   description
                     "Validation entry state";
                 }
               }
             }
             container bgp-path-attributes {
               container attr-as-path {
                 description
                   "AS Path Attribute";
                 leaf attr-length {
                   type string;
                 }
                 leaf flags {
                   type string;
                   description
                     "Enabled trace flags";
                 }
                 leaf path-length {
                   type string;
                 }
                 leaf attr-value {
                   type string;
                 }
               }
               container attr-as4-path {
                 description
                   "4-byte AS Path Attribute";
                 leaf attr-length {
                   type string;
                 }
                 leaf path-length {
                   type string;
                 }
                 leaf flags {
                   type string;
                   description
                     "Enabled trace flags";
                 }
                 leaf attr-value {
                   type string;
                 }
               }
               container attr-as-path-effective {
                 description
                   "Effective AS-Path Attribute";
                 leaf attr-length {
                   type string;
                 }
                 leaf aspath-effective-string {
                   type string;
                 }
                 leaf path-length {
                   type string;
                 }
                 leaf attr-value {
                   type string;
                 }
                 leaf flags {
                   type string;
                   description
                     "Enabled trace flags";
                 }
               }
               container attr-aggregator {
                 description
                   "Aggregator Attribute";
                 leaf attr-length {
                   type string;
                 }
                 leaf flags {
                   type string;
                   description
                     "Enabled trace flags";
                 }
                 leaf aggr-as-number {
                   type string;
                 }
                 leaf aggr-router-id {
                   type string;
                 }
               }
               container attr-aggregator4 {
                 description
                   "Aggregator4 Attribute";
                 leaf attr-length {
                   type string;
                 }
                 leaf flags {
                   type string;
                   description
                     "Enabled trace flags";
                 }
                 leaf aggr-as-number {
                   type string;
                 }
                 leaf aggr-router-id {
                   type string;
                 }
               }
               container attr-cluster-list {
                 description
                   "Cluster List Attribute";
                 leaf attr-length {
                   type string;
                 }
                 leaf attr-value {
                   type string;
                 }
               }
               container attr-originator-id {
                 description
                   "Originator Attribute";
                 leaf attr-length {
                   type string;
                 }
                 leaf attr-value {
                   type string;
                 }
               }
               leaf domain-path {
                 type string;
               }
               leaf attr-otc {
                 type int32;
                 description
                   "Only-to-customer attribute";
               }
               container attr-unrecognized {
                 description
                   "Unrecognized attributes";
                 leaf attr-length {
                   type string;
                 }
                 leaf attr-flags {
                   type string;
                 }
                 leaf attr-code {
                   type string;
                 }
                 leaf attr-value {
                   type string;
                 }
               }
             }
             container communities {
               leaf-list community {
                 type string;
                 description
                   "Basic community";
               }
               leaf-list extended-community {
                 type string;
                 description
                   "Extended community";
               }
               leaf-list ipv6-extended-community {
                 type string;
                 description
                   "IPv6 extended community";
               }
             }
             list bgp-tunnel-attribute {
               key "tunnel-attribute-type";
               description
                 "Tunne encap attribute information";
               leaf tunnel-attribute-type {
                 type string;
               }
               leaf tunnel-attribute-rpf {
                 type empty;
               }
               leaf tunnel-attribute-color {
                 type uint32;
               }
               leaf tunnel-attribute-destination {
                 type jt:ipaddr;
               }
             }
             container attrset {
               container bgp-prefix-sid-attr {
                 description
                   "BGP Prefix SID Attribute";
                 container bgp-prefix-sid-attr-label-idx-tlv {
                   leaf bgp-prefix-sid-label-idx-index {
                     type int32;
                   }
                   leaf bgp-prefix-sid-attr-status {
                     type string;
                   }
                 }
                 container bgp-prefix-sid-attr-srgb-tlv {
                   list bgp-prefix-sid-srgb-block {
                     key "bgp-prefix-sid-srgb-block-start-label";
                     leaf bgp-prefix-sid-srgb-block-start-label {
                       type int32;
                     }
                     leaf bgp-prefix-sid-srgb-block-range {
                       type int32;
                     }
                   }
                 }
                 container bgp-prefix-sid-attr-service-tlv {
                   leaf bgp-prefix-sid-srv6-sid-value {
                     type jt:ipaddr;
                   }
                   leaf bgp-prefix-sid-attr-service-tlv-type {
                     type uint32;
                   }
                   leaf bgp-prefix-sid-attr-tlv-type {
                     type uint32;
                   }
                   leaf bgp-prefix-sid-srv6-sid-bh {
                     type uint32;
                   }
                   leaf bgp-prefix-sid-srv6-sid-bl {
                     type uint32;
                   }
                   leaf bgp-prefix-sid-srv6-sid-nl {
                     type uint32;
                   }
                   leaf bgp-prefix-sid-srv6-sid-fl {
                     type uint32;
                   }
                   leaf bgp-prefix-sid-srv6-sid-al {
                     type uint32;
                   }
                   leaf bgp-prefix-sid-srv6-sid-tl {
                     type uint32;
                   }
                   leaf bgp-prefix-sid-srv6-sid-to {
                     type uint32;
                   }
                 }
                 container bgp-prefix-sid-attr-unknown-tlvs {
                   list bgp-prefix-sid-attr-unknown-tlv {
                     key "bgp-prefix-sid-unknown-tlv-type";
                     leaf bgp-prefix-sid-unknown-tlv-type {
                       type uint32;
                     }
                     leaf bgp-prefix-sid-unknown-tlv-len {
                       type uint32;
                     }
                   }
                 }
               }
               leaf attrset-as {
                 type int32;
                 description
                   "Originator AS";
               }
               leaf med {
                 type int32;
                 description
                   "Multiple exit discriminator";
               }
               leaf local-preference {
                 type int32;
               }
               leaf as-path {
                 type string;
                 description
                   "Name of AS path regular expression (BGP only)";
               }
               leaf pmsi {
                 type string;
                 description
                   "P-multicast service interface";
               }
               leaf cluster-id {
                 type string;
               }
               leaf originator {
                 type string;
               }
               leaf connector {
                 type string;
               }
               container communities {
                 leaf-list community {
                   type string;
                   description
                     "Basic community";
                 }
                 leaf-list extended-community {
                   type string;
                   description
                     "Extended community";
                 }
                 leaf-list ipv6-extended-community {
                   type string;
                   description
                     "IPv6 extended community";
                 }
               }
               list bgp-tunnel-attribute {
                 key "tunnel-attribute-type";
                 description
                   "Tunne encap attribute information";
                 leaf tunnel-attribute-type {
                   type string;
                 }
                 leaf tunnel-attribute-rpf {
                   type empty;
                 }
                 leaf tunnel-attribute-color {
                   type uint32;
                 }
                 leaf tunnel-attribute-destination {
                   type jt:ipaddr;
                 }
               }
             }
             container link-state-information {
               container link-state-link {
                 leaf link-name {
                   type string;
                 }
                 leaf color {
                   type int32;
                 }
                 leaf metric {
                   type int32;
                 }
                 leaf te-metric {
                   type int32;
                   description
                     "LSP TE metric";
                 }
                 leaf link-avg-delay {
                   type uint32;
                 }
                 leaf link-min-delay {
                   type uint32;
                 }
                 leaf link-max-delay {
                   type uint32;
                 }
                 leaf link-avg-delay-var {
                   type uint32;
                 }
                 leaf ldp-support {
                   type string;
                 }
                 leaf rsvpte-support {
                   type string;
                 }
                 leaf maximum-bw {
                   type uint64;
                 }
                 leaf reservable-bw {
                   type uint64;
                 }
                 container protections {
                   leaf-list protection-type {
                     type string;
                     description
                       "LSP protection desired";
                   }
                 }
                 container link-srlgs {
                   leaf-list link-srlg {
                     type string;
                   }
                 }
                 container unreserved-bws {
                   list unreserved-bw {
                     key "unreserved-bw-priority";
                     leaf unreserved-bw-priority {
                       type uint32;
                     }
                     leaf unreserved-bw-value {
                       type string;
                     }
                   }
                 }
                 container link-state-link-opaque-attrs {
                   leaf link-state-link-opaque-attrs-length {
                     type uint32;
                   }
                   leaf link-state-link-opaque-attrs-bytes {
                     type string;
                   }
                 }
                 container link-adj-sids {
                   list link-lan-adj-sid {
                     key "link-lan-adj-sid-label";
                     leaf link-lan-adj-sid-label {
                       type uint32;
                     }
                     leaf link-lan-adj-sid-flags {
                       type string;
                     }
                     leaf link-lan-adj-sid-weight {
                       type uint32;
                     }
                     leaf link-lan-adj-sid-neighbor {
                       type string;
                     }
                   }
                   list link-p2p-adj-sid {
                     key "link-p2p-adj-sid-label";
                     leaf link-p2p-adj-sid-label {
                       type uint32;
                     }
                     leaf link-p2p-adj-sid-flags {
                       type string;
                     }
                     leaf link-p2p-adj-sid-weight {
                       type uint32;
                     }
                   }
                 }
                 container link-bgp-peer-sids {
                   list link-bgp-peer-sid {
                     key "link-bgp-peer-sid-label";
                     leaf link-bgp-peer-sid-label {
                       type uint32;
                     }
                     leaf link-bgp-peer-sid-flags {
                       type string;
                     }
                     leaf link-bgp-peer-sid-weight {
                       type uint32;
                     }
                   }
                 }
                 container link-srv6-end-x-sids {
                   list link-srv6-end-x-sid {
                     key "link-srv6-end-x-sid-val";
                     leaf link-srv6-end-x-sid-type {
                       type string;
                     }
                     leaf link-srv6-end-x-sid-val {
                       type jt:ipv6addr;
                     }
                     leaf link-srv6-end-x-sid-flags {
                       type string;
                     }
                     leaf link-srv6-end-x-sid-weight {
                       type int32;
                     }
                     leaf link-srv6-end-x-sid-algo {
                       type int32;
                     }
                     leaf link-srv6-end-x-sid-func {
                       type string;
                     }
                     leaf link-srv6-end-x-sid-lan-neighbor-id {
                       type string;
                     }
                     container link-srv6-end-x-sid-sstlv {
                       leaf link-srv6-end-x-sid-sstlv-header {
                         type empty;
                       }
                       leaf link-srv6-end-x-sid-sstlv-blen {
                         type uint32;
                       }
                       leaf link-srv6-end-x-sid-sstlv-nlen {
                         type uint32;
                       }
                       leaf link-srv6-end-x-sid-sstlv-flen {
                         type uint32;
                       }
                       leaf link-srv6-end-x-sid-sstlv-alen {
                         type uint32;
                       }
                     }
                   }
                 }
                 container link-msd-types {
                   list link-msd-entry {
                     key "link-msd-type";
                     leaf link-msd-type {
                       type uint32;
                     }
                     leaf link-msd-value {
                       type uint32;
                     }
                   }
                 }
               }
               container link-state-node {
                 leaf node-name {
                   type string;
                 }
                 leaf area-border-router {
                   type string;
                 }
                 leaf external-router {
                   type string;
                 }
                 leaf attached {
                   type string;
                 }
                 leaf overload {
                   type string;
                 }
                 container node-areas {
                   leaf-list node-area {
                     type string;
                   }
                 }
                 container node-ipv4-router-ids {
                   leaf-list node-ipv4-router-id {
                     type jt:ipaddr;
                   }
                 }
                 container node-ipv6-router-ids {
                   leaf-list node-ipv6-router-id {
                     type jt:ipaddr;
                   }
                 }
                 container node-topologies {
                   list node-topology {
                     key "id";
                     leaf id {
                       type uint32;
                     }
                   }
                 }
                 container link-state-node-opaque-attrs {
                   leaf link-state-node-opaque-attrs-length {
                     type uint32;
                   }
                   leaf link-state-node-opaque-attrs-bytes {
                     type string;
                   }
                 }
                 container node-spring-capability {
                   list node-spring-srgb-block {
                     key "node-spring-srgb-block-start node-spring-srgb-block-range";
                     leaf node-spring-srgb-block-start {
                       type uint32;
                     }
                     leaf node-spring-srgb-block-range {
                       type uint32;
                     }
                     leaf node-spring-srgb-block-flags {
                       type string;
                     }
                   }
                 }
                 container node-msd-types {
                   list node-msd-entry {
                     key "node-msd-type";
                     leaf node-msd-type {
                       type uint32;
                     }
                     leaf node-msd-value {
                       type uint32;
                     }
                   }
                 }
                 container node-srv6-capability {
                   leaf node-srv6-capability-flag {
                     type uint32;
                   }
                 }
                 container node-spring-algorithms {
                   list node-spring-algorithm {
                     key "node-spring-algorithm-type";
                     leaf node-spring-algorithm-type {
                       type uint32;
                     }
                   }
                 }
                 container node-spring-falgo-defs {
                   list node-spring-falgo-def {
                     key "node-spring-falgo-def-algo";
                     leaf node-spring-falgo-def-algo {
                       type uint32;
                     }
                     leaf node-spring-falgo-def-metric-type {
                       type uint32;
                     }
                     leaf node-spring-falgo-def-calculation-type {
                       type uint32;
                     }
                     leaf node-spring-falgo-def-priority {
                       type uint32;
                     }
                     leaf node-spring-falgo-def-flags {
                       type string;
                     }
                     leaf node-spring-falgo-def-include-any {
                       type string;
                     }
                     leaf node-spring-falgo-def-exclude {
                       type string;
                     }
                     leaf node-spring-falgo-def-include-all {
                       type string;
                     }
                   }
                 }
               }
               container link-state-te-policy-cp {
                 leaf link-state-te-policy-cp-name {
                   type string;
                 }
                 leaf link-state-te-policy-cp-flags {
                   type string;
                 }
                 leaf link-state-te-policy-cp-preference {
                   type uint32;
                 }
                 leaf link-state-te-policy-cp-priority {
                   type uint32;
                 }
                 leaf link-state-te-policy-cp-constraint-header {
                   type empty;
                 }
                 leaf link-state-te-policy-cp-constraint-flags {
                   type string;
                 }
                 leaf link-state-te-policy-cp-mtid {
                   type uint32;
                 }
                 leaf link-state-te-policy-cp-algo {
                   type uint32;
                 }
                 leaf link-state-te-policy-cp-exclude-any {
                   type string;
                 }
                 leaf link-state-te-policy-cp-include-any {
                   type string;
                 }
                 leaf link-state-te-policy-cp-include-all {
                   type string;
                 }
                 leaf link-state-te-policy-cp-bandwidth {
                   type uint32;
                 }
                 leaf link-state-te-policy-cp-bsid-flags {
                   type string;
                 }
                 leaf link-state-te-policy-cp-mpls-bsid {
                   type uint32;
                 }
                 leaf link-state-te-policy-cp-mpls-spec-bsid {
                   type uint32;
                 }
                 leaf link-state-te-policy-cp-segment-list-count {
                   type int32;
                 }
                 container link-state-te-policy-cp-srv6-bsid-info {
                   leaf link-state-te-policy-cp-srv6-bsid-flags {
                     type string;
                     description
                       "SRv6 BSID flags";
                   }
                   leaf link-state-te-policy-cp-srv6-bsid {
                     type jt:ipv6addr;
                     description
                       "SRv6 BSID";
                   }
                   leaf link-state-te-policy-cp-srv6-spec-bsid {
                     type jt:ipv6addr;
                     description
                       "Specified SRv6 BSID";
                   }
                   leaf link-state-te-policy-cp-srv6-bsid-ep-bhv {
                     type uint32;
                     description
                       "SRv6 BSID endpoint behavior";
                   }
                   leaf link-state-te-policy-cp-srv6-bsid-ep-bhv-flags {
                     type string;
                     description
                       "SRv6 BSID endpoint behavior flags";
                   }
                   leaf link-state-te-policy-cp-srv6-bsid-ep-bhv-algo {
                     type uint32;
                     description
                       "SRv6 BSID endpoint behavior algo";
                   }
                   leaf link-state-te-policy-cp-srv6-bsid-sstlv {
                     type string;
                     description
                       "SRv6 BSID endpoint behavior SSTLV";
                   }
                 }
                 list link-state-te-policy-cp-segment-list {
                   key "link-state-te-policy-cp-segment-list-index";
                   leaf link-state-te-policy-cp-segment-list-index {
                     type int32;
                   }
                   leaf link-state-te-policy-cp-segment-list-flags {
                     type string;
                   }
                   leaf link-state-te-policy-cp-segment-list-mtid {
                     type uint32;
                   }
                   leaf link-state-te-policy-cp-segment-list-weight {
                     type uint32;
                   }
                   leaf link-state-te-policy-cp-segment-list-algo {
                     type uint32;
                   }
                   leaf link-state-te-policy-cp-segment-list-metric-type {
                     type string;
                   }
                   leaf link-state-te-policy-cp-segment-list-metric-value {
                     type uint32;
                   }
                   leaf link-state-te-policy-cp-segment-count {
                     type int32;
                   }
                   leaf link-state-te-policy-cp-segment-header {
                     type empty;
                   }
                   list link-state-te-policy-cp-segment {
                   }
                 }
               }
               container link-state-prefix {
                 leaf link-state-prefix-attr-flags {
                   type string;
                 }
                 leaf link-state-prefix-metric {
                   type uint32;
                 }
                 list link-state-prefix-sid {
                   key "link-state-prefix-sid-index link-state-prefix-sid-flags link-state-prefix-sid-algo";
                   leaf link-state-prefix-sid-index {
                     type uint32;
                   }
                   leaf link-state-prefix-sid-flags {
                     type string;
                   }
                   leaf link-state-prefix-sid-algo {
                     type string;
                   }
                 }
                 container link-state-prefix-srv6-locator {
                   leaf link-state-prefix-srv6-locator-flags {
                     type string;
                   }
                   leaf link-state-prefix-srv6-locator-algo {
                     type string;
                   }
                   leaf link-state-prefix-srv6-locator-metric {
                     type string;
                   }
                 }
                 list link-state-prefix-fapm {
                   key "link-state-prefix-fapm-algo";
                   leaf link-state-prefix-fapm-algo {
                     type uint32;
                   }
                   leaf link-state-prefix-fapm-metric {
                     type uint32;
                   }
                 }
               }
               container link-state-srv6-endsid {
                 container link-state-srv6-endsid-info {
                   leaf link-state-srv6-endsid-epb {
                     type string;
                   }
                   leaf link-state-srv6-endsid-flags {
                     type string;
                   }
                   leaf link-state-srv6-endsid-algo {
                     type string;
                   }
                   container link-state-srv6-endsid-sstlv {
                     leaf link-state-srv6-endsid-sstlv-header {
                       type empty;
                     }
                     leaf link-state-srv6-endsid-sstlv-blen {
                       type uint32;
                     }
                     leaf link-state-srv6-endsid-sstlv-nlen {
                       type uint32;
                     }
                     leaf link-state-srv6-endsid-sstlv-flen {
                       type uint32;
                     }
                     leaf link-state-srv6-endsid-sstlv-alen {
                       type uint32;
                     }
                   }
                 }
               }
               container link-state-unknown-tlvs {
                 list link-state-unknown-tlv {
                   key "unknown-type";
                   leaf unknown-type {
                     type uint32;
                   }
                   leaf unknown-length {
                     type uint32;
                   }
                   leaf unknown-bytes {
                     type string;
                   }
                 }
               }
             }
             container aggregate {
               leaf aggregate-truncate {
                 type string;
               }
               container aggregate-as-path {
                 container bgp-path-attributes {
                   container attr-as-path {
                     description
                       "AS Path Attribute";
                     leaf attr-length {
                       type string;
                     }
                     leaf flags {
                       type string;
                       description
                         "Enabled trace flags";
                     }
                   }
                   container attr-as4-path {
                     description
                       "4-byte AS Path Attribute";
                     leaf attr-length {
                       type string;
                     }
                   }
                   container attr-as-path-effective {
                     description
                       "Effective AS-Path Attribute";
                     leaf attr-length {
                       type string;
                     }
                   }
                   container attr-aggregator {
                     description
                       "Aggregator Attribute";
                     leaf attr-length {
                       type string;
                     }
                   }
                   container attr-aggregator4 {
                     description
                       "Aggregator4 Attribute";
                     leaf attr-length {
                       type string;
                     }
                   }
                   container attr-cluster-list {
                     description
                       "Cluster List Attribute";
                     leaf attr-length {
                       type string;
                     }
                   }
                   container attr-originator-id {
                     description
                       "Originator Attribute";
                     leaf attr-length {
                       type string;
                     }
                   }
                 }
                 leaf as-path {
                   type string;
                   description
                     "Name of AS path regular expression (BGP only)";
                 }
                 leaf reference-count {
                   type int32;
                   description
                     "Reference count";
                 }
                 leaf as-path-length {
                   type int32;
                 }
                 leaf aggregate-truncate {
                   type string;
                 }
               }
               leaf aggregate-flags {
                 type string;
                 description
                   "Flags on this aggregate route entry";
               }
               leaf aggregate-depth {
                 type int32;
                 description
                   "Depth of this aggregate";
               }
               leaf aggregate-active {
                 type empty;
                 description
                   "Present if this aggregate is active";
               }
               leaf aggregate-algo {
                 type uint32;
                 description
                   "Algorithm number";
               }
               leaf contributing-route-count {
                 type int32;
                 description
                   "Number of contributing routes in this aggregate";
               }
               leaf aggregate-policy-name {
                 type string;
               }
               list aggregated-route {
                 key "destination-prefix";
                 leaf destination-prefix {
                   type string;
                   description
                     "Destination prefix and mask";
                 }
                 leaf protocol-name {
                   type string;
                 }
               }
             }
             list nh {
               description
                 "Next-hop gateway information";
               leaf selected-next-hop {
                 type empty;
                 description
                   "Present if this next hop is selected";
               }
               leaf to {
                 type string;
                 description
                   "Neighbor address to which to send (next-hop address)";
               }
               leaf nh-indirect-fnh-type {
                 type string;
                 description
                   "Indirect pointing to a well-known nexthop";
               }
               leaf via {
                 type string;
                 description
                   "Reachable via a local interface";
               }
               container vxlan-header-rewrite {
                 description
                   "VXLAN tunnel rewrite information";
                 leaf vxlan-header-rewrite-mtu {
                   type int32;
                   description
                     "VXLAN tunnel MTU";
                 }
                 leaf vxlan-header-rewrite-flags {
                   type int32;
                   description
                     "VXLAN tunnel flags";
                 }
                 leaf vxlan-header-rewrite-encap-rtb-id {
                   type int32;
                   description
                     "VXLAN tunnel encapsulation table ID";
                 }
                 leaf vxlan-header-rewrite-decap-rtb-id {
                   type int32;
                   description
                     "VXLAN tunnel decapsulation table ID";
                 }
                 leaf vxlan-header-rewrite-encap-vnid {
                   type int32;
                   description
                     "VXLAN tunnel encapsulation VNI";
                 }
                 leaf vxlan-header-rewrite-decap-vnid {
                   type int32;
                   description
                     "VXLAN tunnel decapsulation VNI";
                 }
                 leaf vxlan-header-rewrite-svtep {
                   type jt:ipaddr;
                   description
                     "Source VTEP address";
                 }
                 leaf vxlan-header-rewrite-dvtep {
                   type jt:ipaddr;
                   description
                     "Destination VTEP address";
                 }
                 leaf vxlan-header-rewrite-smac {
                   type string;
                   description
                     "Source MAC address";
                 }
                 leaf vxlan-header-rewrite-dmac {
                   type string;
                   description
                     "Destination MAC address";
                 }
               }
               container srv6-info {
                 leaf srv6-info-srh-sid-mode {
                   type string;
                   description
                     "Reduced/non-reduced mode for SRH";
                 }
                 leaf srv6-info-packet-mode {
                   type string;
                   description
                     "Packet mode for SRV6-Tunnel";
                 }
                 leaf srv6-info-srh-last-sid {
                   type string;
                   description
                     "Remove last sid for ACX";
                 }
                 leaf srv6-info-dyn-tunnel {
                   type string;
                   description
                     "SRv6 tunnel created dynamically";
                 }
                 leaf srv6-cos-propagation {
                   type string;
                   description
                     "SRv6 CoS propagation";
                 }
                 leaf srv6-ttl-propagation {
                   type string;
                   description
                     "SRv6 TTL propagation";
                 }
                 leaf srv6-source {
                   type jt:ipaddr;
                   description
                     "Source IPv6 address";
                 }
                 leaf srv6-destination {
                   type jt:ipaddr;
                   description
                     "Destination IPv6 address";
                 }
                 list srv6-segment-list {
                   key "srv6-segment-list-index";
                   description
                     "SRH Segment list";
                   leaf srv6-segment-list-index {
                     type uint32;
                     description
                       "SRH segment list index";
                   }
                   leaf srv6-segment-list-addr {
                     type jt:ipaddr;
                     description
                       "SRH segment address";
                   }
                 }
               }
               leaf nh-string {
                 type string;
               }
               leaf nh-table-receive {
                 type string;
                 description
                   "Destination is a local address";
               }
               leaf nh-table {
                 type string;
                 description
                   "Indirect pointing to another table";
               }
               leaf nh-table-localized {
                 type string;
                 description
                   "Indirect pointing to a localized table";
               }
               leaf nh-localized-ifl {
                 type string;
                 description
                   "Indirect pointing to a localized ifl";
               }
               leaf lsp-name {
                 type string;
                 description
                   "Tunneled into an RSVP LSP";
               }
               leaf mpls-label {
                 type string;
                 description
                   "Label of MPLS packet";
               }
               leaf nh-local-interface {
                 type string;
                 description
                   "Destination is a local interface";
               }
               leaf nh-service {
                 type string;
                 description
                   "Next-hop service";
               }
               leaf nh-private-comp {
                 type string;
                 description
                   "Private Composite Next-hop";
               }
               leaf srv6-prefix-sid {
                 type jt:ipaddr;
                 description
                   "SRv6 prefixe sid value";
               }
               leaf srv6-encap-brief {
                 type string;
                 description
                   "IPV6 SR-header encapsulation";
               }
               leaf elnh-address {
                 type string;
                 description
                   "Address of Element Next-hop";
               }
               leaf localized-table {
                 type string;
                 description
                   "Name of localized table";
               }
               leaf ae-member-interface {
                 type string;
                 description
                   "AE Member interface";
               }
               leaf weight {
                 type int32;
                 description
                   "Next-hop weight";
               }
               leaf balance {
                 type int32;
                 description
                   "Next-hop balance";
               }
               leaf uflags {
                 type string;
                 description
                   "Next-hop uflags";
               }
               leaf filter {
                 type string;
                 description
                   "Next-hop firewall filter";
               }
               leaf session {
                 type string;
                 description
                   "Session ID Associated with this NH";
               }
               leaf statistics-id-group-terse {
                 type string;
                 description
                   "Statistics ID Group Associated with this NH";
               }
               leaf app-specific-opaque {
                 type string;
                 description
                   "Application specific opaque data dump";
               }
               leaf gw-opaque {
                 type string;
                 description
                   "Nexthops gateway opaque data handle";
               }
               leaf statistics-pkts-count {
                 type int32;
                 description
                   "Statistics packet count Associated with this NH";
               }
               leaf statistics-bytes-count {
                 type int32;
                 description
                   "Statistics bytes count Associated with this NH";
               }
               leaf ext-int-type {
                 type string;
                 description
                   "Next-hop type of equal-external-internal multipath";
               }
               leaf fc {
                 type int32;
                 description
                   "Forwarding-class";
               }
               leaf label-ttl-action {
                 type string;
                 description
                   "TTL action associated with labels";
               }
               leaf load-balance-label {
                 type string;
                 description
                   "Load balance action associated with labels";
               }
               leaf label-element {
                 type string;
                 description
                   "Pointer to the tag label element";
               }
               leaf label-element-parent {
                 type string;
                 description
                   "Pointer to the tag label element parent";
               }
               leaf label-element-refcount {
                 type string;
                 description
                   "Number of references to the tag label element";
               }
               leaf label-element-childcount {
                 type string;
                 description
                   "Number of child references to the tag label element";
               }
               leaf label-element-lspid {
                 type string;
                 description
                   "LSP ID of the tag label element";
               }
               leaf nh-service-pkt-dist {
                 type string;
                 description
                   "Multi services packet distribution type";
               }
               leaf nh-service-app-data {
                 type string;
                 description
                   "Multi services application specific data";
               }
               leaf nh-index {
                 type uint32;
                 description
                   "Next-hop index";
               }
               leaf nh-reference-count {
                 type int32;
                 description
                   "Number of references to this next hop";
               }
               leaf tunnel-composite-attr-type {
                 type string;
                 description
                   "Tunnel-Type for tunnel-composite-nexthop";
               }
               leaf tunnel-composite-attr-subtype {
                 type string;
                 description
                   "Tunnel-Subtype for tunnel-composite-nexthop";
               }
               leaf tunnel-composite-attr-reference-count {
                 type int32;
                 description
                   "Tunnel-reference-count for tunnel-composite-nexthop";
               }
               leaf tunnel-composite-attr-nh-id {
                 type int32;
                 description
                   "Tunnel-NextHop-Id for tunnel-composite-nexthop";
               }
               leaf tunnel-composite-attr-dest {
                 type jt:ipaddr;
                 description
                   "Tunnel-Destination for tunnel-composite-nexthop";
               }
               leaf tunnel-composite-attr-src {
                 type jt:ipaddr;
                 description
                   "Tunnel-Source for tunnel-composite-nexthop";
               }
               leaf tunnel-composite-attr-tunnel-endpoint {
                 type jt:ipaddr;
                 description
                   "Tunnel-Endpoint for tunnel-composite-nexthop";
               }
               leaf tunnel-composite-anchor-pfe {
                 type string;
                 description
                   "Anchor PFE name, if tunnel nexthop is localized";
               }
               leaf tunnel-composite-encap-rtb-id {
                 type int32;
                 description
                   "Tunnel encap routing table index";
               }
               leaf tunnel-composite-decap-rtb-id {
                 type int32;
                 description
                   "Tunnel decap routing table index";
               }
               leaf tunnel-composite-attr-ttl {
                 type int32;
                 description
                   "Tunnel-TTL for tunnel-composite-nexthop";
               }
               leaf tunnel-composite-attr-tid {
                 type int32;
                 description
                   "Tunnel-Id for tunnel-composite-nexthop";
               }
               leaf tunnel-composite-attr-label {
                 type string;
                 description
                   "Tunnel-VPN-Label for tunnel-composite-nexthop";
               }
               leaf tunnel-composite-attr-label-ttl {
                 type string;
                 description
                   "Tunnel-VPN-Label-TTL for tunnel-composite-nexthop";
               }
               leaf tunnel-composite-attr-gre-key {
                 type int32;
                 description
                   "GRE key for tunnel-composite-nexthop";
               }
               leaf-list tunnel-composite-attr-segment-addr {
                 type jt:ipaddr;
                 description
                   "IPv6 segment-address";
               }
               leaf-list tunnel-composite-attr-sid {
                 type int32;
                 description
                   "IPv6 segment-sid";
               }
               leaf tunnel-composite-attr-vni {
                 type int32;
                 description
                   "Tunnel-VNI for tunnel-composite-nexthop in VxLAN";
               }
               leaf translate-composite-attr-type {
                 type string;
                 description
                   "Translation type for translate-composite-nexthop";
               }
               leaf translate-composite-attr-flags {
                 type string;
                 description
                   "Flags for translate-composite-nexthop";
               }
               leaf translate-composite-attr-reference-count {
                 type int32;
                 description
                   "Reference count for translate-composite-nexthop";
               }
               leaf translate-composite-attr-nh-id {
                 type int32;
                 description
                   "NextHop id for translate-composite-nexthop";
               }
               leaf translate-composite-attr-dest {
                 type jt:ipaddr;
                 description
                   "Translation destination for translate-composite-nexthop";
               }
               leaf translate-composite-attr-dest-plen {
                 type int32;
                 description
                   "Translation destination prefix length for 
                   translate-composite-nexthop";
               }
               leaf translate-composite-attr-src {
                 type jt:ipaddr;
                 description
                   "Translation source for translate-composite-nexthop";
               }
               leaf translate-composite-attr-src-plen {
                 type int32;
                 description
                   "Translation source prefix length for 
                   translate-composite-nexthop";
               }
               leaf translate-composite-attr-dest-alg-type {
                 type string;
                 description
                   "Destination algorithm type for 
                   translate-composite-nexthop";
               }
               leaf translate-composite-attr-src-alg-type {
                 type string;
                 description
                   "Source algorithm type for translate-composite-nexthop";
               }
               leaf translate-composite-attr-dest-vrf-id {
                 type int32;
                 description
                   "Destination vrf id for translate-composite-nexthop";
               }
               leaf translate-composite-attr-src-vrf-id {
                 type int32;
                 description
                   "Source vrf id for translate-composite-nexthop";
               }
               leaf translate-composite-attr-hoplimit {
                 type int32;
                 description
                   "Hoplimit for translate-composite-nexthop";
               }
               leaf translate-composite-attr-traffic-class {
                 type int32;
                 description
                   "Traffic class for translate-composite-nexthop";
               }
               leaf translate-composite-attr-ttl {
                 type int32;
                 description
                   "Ttl for translate-composite-nexthop";
               }
               leaf translate-composite-attr-tos {
                 type int32;
                 description
                   "Tos for translate-composite-nexthop";
               }
             }
             container srte-policy-state {
               leaf sr-source {
                 type string;
               }
               leaf sr-origin {
                 type string;
               }
               leaf sr-preference {
                 type uint32;
               }
               leaf sr-preference-override {
                 type uint32;
               }
               leaf sr-route-distinguisher {
                 type uint32;
               }
             }
             container srte-policy-information {
               container srte-policy {
                 leaf srte-path-preference {
                   type uint32;
                 }
                 leaf srte-binding-sid {
                   type string;
                 }
                 leaf srte-adv-policy-name {
                   type string;
                 }
                 leaf srte-priority {
                   type uint32;
                 }
                 leaf srte-enlp {
                   type uint32;
                 }
                 leaf srte-tlv-recv-flags {
                   type string;
                 }
                 leaf srte-binding-sid-label-encoding {
                   type string;
                 }
               }
             }
             container bgp-prefix-sid-attr {
               description
                 "BGP Prefix SID Attribute";
               container bgp-prefix-sid-attr-label-idx-tlv {
                 leaf bgp-prefix-sid-label-idx-index {
                   type int32;
                 }
                 leaf bgp-prefix-sid-attr-status {
                   type string;
                 }
               }
               container bgp-prefix-sid-attr-srgb-tlv {
                 list bgp-prefix-sid-srgb-block {
                   key "bgp-prefix-sid-srgb-block-start-label";
                   leaf bgp-prefix-sid-srgb-block-start-label {
                     type int32;
                   }
                   leaf bgp-prefix-sid-srgb-block-range {
                     type int32;
                   }
                 }
               }
               container bgp-prefix-sid-attr-service-tlv {
                 leaf bgp-prefix-sid-srv6-sid-value {
                   type jt:ipaddr;
                 }
                 leaf bgp-prefix-sid-attr-service-tlv-type {
                   type uint32;
                 }
                 leaf bgp-prefix-sid-attr-tlv-type {
                   type uint32;
                 }
                 leaf bgp-prefix-sid-srv6-sid-bh {
                   type uint32;
                 }
                 leaf bgp-prefix-sid-srv6-sid-bl {
                   type uint32;
                 }
                 leaf bgp-prefix-sid-srv6-sid-nl {
                   type uint32;
                 }
                 leaf bgp-prefix-sid-srv6-sid-fl {
                   type uint32;
                 }
                 leaf bgp-prefix-sid-srv6-sid-al {
                   type uint32;
                 }
                 leaf bgp-prefix-sid-srv6-sid-tl {
                   type uint32;
                 }
                 leaf bgp-prefix-sid-srv6-sid-to {
                   type uint32;
                 }
               }
               container bgp-prefix-sid-attr-unknown-tlvs {
                 list bgp-prefix-sid-attr-unknown-tlv {
                   key "bgp-prefix-sid-unknown-tlv-type";
                   leaf bgp-prefix-sid-unknown-tlv-type {
                     type uint32;
                   }
                   leaf bgp-prefix-sid-unknown-tlv-len {
                     type uint32;
                   }
                 }
               }
             }
             leaf preference2 {
               type int32;
             }
             leaf age {
               type string;
             }
             leaf med {
               type int32;
               description
                 "Multiple exit discriminator";
             }
             leaf local-preference {
               type int32;
             }
             leaf rt-tag {
               type int32;
             }
             leaf rt-tag2 {
               type int32;
             }
             leaf learned-from {
               type jt:ipaddr;
               description
                 "Peer address from which this route was learned";
             }
             leaf peer-as {
               type int32;
               description
                 "Peer AS number";
             }
             leaf evpn-remote-mes {
               type jt:ipaddr;
               description
                 "Remote PE";
             }
             leaf evpn-routing-instance-name {
               type string;
               description
                 "Routing Instance";
             }
             leaf evpn-tag-rt-type {
               type string;
               description
                 "Route Type";
             }
             leaf evpn-vlan-id {
               type int32;
               description
                 "VLAN-ID";
             }
             leaf evpn-vpws-service-id {
               type int32;
               description
                 "VPWS Service-Id";
             }
             leaf rt-evpn-esi {
               type string;
               description
                 "ESI";
             }
             leaf evpn-isid {
               type int32;
               description
                 "ISID";
             }
             leaf rt-evpn-bmac {
               type string;
               description
                 "BMAC";
             }
             leaf bgp-rtarget-type {
               type string;
               description
                 "BGP RT-Constrain route type";
             }
             leaf bgp-rtarget-generation {
               type uint32;
               description
                 "BGP RT-Constrain generation";
             }
             leaf bgp-rtarget-for {
               type string;
               description
                 "BGP RT-Constrain member";
             }
             leaf nh-index {
               type uint32;
               description
                 "Next-hop index";
             }
             leaf transport-class {
               type string;
               description
                 "Transport class name";
             }
             leaf ext-int-intf-index {
               type int32;
               description
                 "Interface index of equal-external-internal multipath";
             }
             leaf nh-session-id {
               type uint32;
               description
                 "Nexthop session id";
             }
             leaf nh-key-opaque {
               type string;
               description
                 "Nexthop key opaque handle";
             }
             leaf nh-non-key-opaque {
               type string;
               description
                 "Nexthop non-key opaque handle";
             }
             leaf nh-key-opaque-dump {
               type string;
               description
                 "Nexthop key opaque app dump";
             }
             leaf nh-non-key-opaque-dump {
               type string;
               description
                 "Nexthop non-key opaque app dump";
             }
             leaf nh-flood-overflow {
               type empty;
               description
                 "Flood nexthop exceeds maximum branches";
             }
             leaf nh-kernel-id {
               type int32;
               description
                 "Table Id for this next hop";
             }
             leaf client-data {
               type string;
               description
                 "Route server client details";
             }
             leaf route-distinguisher {
               type string;
               description
                 "Name of the route-distinguisher";
             }
             leaf reason-for-invalid {
               type string;
             }
             leaf thread-name {
               type string;
             }
             leaf pmsi {
               type string;
               description
                 "P-multicast service interface";
             }
             leaf connector {
               type string;
             }
             leaf color {
               type int32;
             }
             leaf color2 {
               type int32;
             }
             leaf prefix-segment-index {
               type int32;
             }
             leaf rt-isis-level {
               type int32;
             }
             leaf rt-isis-downbit {
               type int32;
             }
             leaf rt-entry-state {
               type string;
               description
                 "State of this route entry";
             }
             leaf rt-fib-install-priority {
               type string;
               description
                 "Route FIB installation priority";
             }
             leaf rt-ack-state {
               type string;
               description
                 "Route acknowledgement state";
             }
             leaf rt-ack-ll-flag {
               type string;
               description
                 "Status of route ACK flags";
             }
             leaf rt-ack-req-ts {
               type string;
               description
                 "Time when ack request is sent";
             }
             leaf rt-ack-res-time {
               type uint32;
               description
                 "Ack route response time";
             }
             leaf rt-ack-re-flash-time {
               type string;
               description
                 "Time when ack is re flashed to protocols";
             }
             leaf rt-ack-re-flash-status {
               type string;
               description
                 "Status of ACK re-flash to protocols";
             }
             leaf rt-ack-guid {
               type uint64;
               description
                 "Ack route global identifier";
             }
             leaf rt-ack-olc {
               type uint64;
               description
                 "Ack route global version";
             }
             leaf rt-ack-local-ver {
               type uint32;
               description
                 "Ack route global version";
             }
             leaf rt-ack-and-err-flag {
               type uint32;
               description
                 "Route ack and error flag";
             }
             leaf rt-ack-history {
               type uint32;
               description
                 "Route ack history";
             }
             leaf pfe-err-state {
               type string;
               description
                 "Route error state from PFE";
             }
             leaf pfe-err-time {
               type uint32;
               description
                 "Route error receive time";
             }
             leaf rt-ver-id {
               type uint32;
               description
                 "Route version ID";
             }
             leaf rt-entry-pim-state {
               type string;
               description
                 "PIM state of this route entry";
             }
             leaf inactive-reason {
               type string;
               description
                 "HFRR profile Inactive reason (if any)";
             }
             leaf local-as {
               type int32;
               description
                 "Local AS number";
             }
             leaf med-plus-igp {
               type int32;
             }
             leaf rt-aigp {
               type uint64;
             }
             leaf rt-effective-aigp {
               type uint64;
               description
                 "Effective AIGP value used by route selection";
             }
             leaf rt-effective-aigp-reason {
               type string;
               description
                 "Reason why the effective AIGP value was selected";
             }
             leaf rt-resolving-aigp {
               type uint64;
             }
             leaf rt-effective-metric {
               type uint64;
               description
                 "Effective metric value used by route selection";
             }
             leaf rt-effective-metric-reason {
               type string;
               description
                 "Reason why the effective metric value was selected";
             }
             leaf rt-orr {
               type uint32;
             }
             leaf rt-actual-igp-metric {
               type uint32;
             }
             leaf rt-ospf-area {
               type string;
             }
             leaf task-name {
               type string;
               description
                 "Name of this task";
             }
             leaf announce-bits {
               type int32;
             }
             leaf announce-tasks {
               type string;
             }
             leaf flow-id {
               type int32;
             }
             leaf bgp-rt-flag {
               type string;
               description
                 "BGP route flag";
             }
             leaf label-base {
               type int32;
               description
                 "Label base for l2vpn";
             }
             leaf label-range {
               type int32;
               description
                 "Label range for l2vpn";
             }
             leaf l2vpn-status-vector {
               type string;
             }
             leaf label-offset {
               type int32;
               description
                 "Label offset for l2vpn";
             }
             leaf remote-site {
               type int32;
               description
                 "Remote site id";
             }
             leaf l2vpn-mesh-group {
               type string;
             }
             leaf vc-label {
               type int32;
               description
                 "VC label";
             }
             leaf context-id {
               type jt:ipaddr;
               description
                 "Context Identifier";
             }
             leaf route-control-word {
               type string;
               description
                 "Control Word";
             }
             leaf mtu {
               type int32;
               description
                 "MTU along an interface";
             }
             leaf cell-bundle-size {
               type int32;
               description
                 "Cell bundle size";
             }
             leaf vlan-id {
               type int32;
             }
             leaf flow-label-transmit {
               type int32;
             }
             leaf flow-label-receive {
               type int32;
             }
             leaf tdm-payload-size {
               type int32;
             }
             leaf tdm-bitrate {
               type int32;
             }
             leaf pw-status-code {
               type int32;
             }
             leaf vpn-label {
               type int32;
               description
                 "VPN label";
             }
             leaf route-label {
               type int32;
               description
                 "Route label";
             }
             leaf route-labels {
               type string;
               description
                 "Route label";
             }
             leaf mac-route-esi {
               type string;
               description
                 "ESI";
             }
             leaf evpn-igmp-flags {
               type int32;
               description
                 "IGMP flags";
             }
             leaf evpn-mld-flags {
               type int32;
               description
                 "MLD flags";
             }
             leaf evpn-leave-reserved {
               type int32;
               description
                 "IGMP Leave Reserved Field";
             }
             leaf evpn-leave-mrt {
               type int32;
               description
                 "IGMP Leave Max Response Time";
             }
             leaf overlay-gateway-address {
               type jt:ipaddr;
               description
                 "Overlay gateway address";
             }
             leaf reroute-address {
               type jt:ipaddr;
               description
                 "Reroute address";
             }
             leaf bgp-otc {
               type int32;
             }
             leaf peer-id {
               type jt:ipaddr;
             }
             leaf rt-entry-ext-pfx-attr-flags {
               type string;
               description
                 "Route entry extended prefix attribute flags";
             }
             leaf rt-entry-ext-pfx-source-rtrid {
               type string;
               description
                 "Route entry extended prefix source rtr id";
             }
             leaf path-id {
               type string;
             }
             leaf gateway {
               type string;
               description
                 "Sourcing gateway";
             }
             leaf rtrib-primary {
               type string;
               description
                 "Primary routing table";
             }
             leaf rib-export-rtrib-primary {
               type string;
               description
                 "RIB export primary routing table";
             }
             leaf rtrib-secondary {
               type string;
               description
                 "Secondary routing table";
             }
             leaf indirect-nh-count {
               type int32;
               description
                 "Number of indirect next hops";
             }
             leaf composite-nh-count {
               type int32;
               description
                 "Number of composite next hops";
             }
             leaf helper-refcount {
               type int32;
               description
                 "Reference count of those needing helper route";
             }
             leaf backup-pe-group-name {
               type string;
               description
                 "Name of the backup PE group";
             }
             leaf designated-forwarder {
               type string;
               description
                 "Indicates if we are the designated forwarder for this 
                 route";
             }
             leaf rt-entry-opaque-data {
               type string;
               description
                 "Opaque data associated with the route entry";
             }
             leaf rt-stats-id-grp-single-line {
               type string;
               description
                 "Stats-id-group associated with the route entry";
             }
             leaf rt-entry-ext-pfx-sid-data {
               type string;
               description
                 "Route entry extended prefix sid data";
             }
             leaf hidden-reason {
               type string;
               description
                 "Protocol's reason for hiding the route";
             }
             leaf bgp-bmp-send-flag-start {
               type string;
             }
             leaf bgp-bmp-send-flag-pre {
               type string;
             }
             leaf bgp-bmp-send-flag-post {
               type string;
             }
             leaf bgp-bmp-send-flag-station {
               type string;
             }
             leaf bgp-nnh-nodes {
               type string;
               description
                 "Next-next-hop nodes";
             }
             leaf bgp-nh-nnh-map {
               type string;
               description
                 "Next-hop to next-next-hop map";
             }
             leaf bgp-profile-creation-failure-reason {
               type string;
               description
                 "Reason for failing to create profile for next-next-hop map";
             }
             leaf bgp-nh-nnh-entry {
               type string;
               description
                 "Next-hop to next-next-hop entry";
             }
             leaf glb-profile {
               type string;
               description
                 "GLB Profile";
             }
             leaf glb-profile-id {
               type uint32;
               description
                 "GLB Profile ID";
             }
             leaf rt-entry-stats {
               type string;
               description
                 "Route entry statistics data";
             }
             container connection-bandwidth {
               description
                 "Bandwidth of a layer 2 connection";
               leaf bandwidth {
                 type string;
               }
               leaf class-type {
                 type int32;
               }
               leaf class-bandwidth {
                 type int32;
               }
             }
             container route-flap-damping {
               leaf last-merit {
                 type int32;
                 description
                   "Last merit value";
               }
               leaf merit {
                 type int32;
                 description
                   "Current merit value";
               }
               leaf damping-parameters {
                 type string;
               }
               leaf default-damping-parameters {
                 type empty;
                 description
                   "Default damping parameters used";
               }
               leaf last-update {
                 type string;
               }
               leaf first-update {
                 type string;
               }
               leaf route-flap-count {
                 type int32;
                 description
                   "Number of times this route has flapped";
               }
               leaf suppressed {
                 type empty;
                 description
                   "This route is suppressed";
               }
               leaf reuse-time {
                 type string;
                 description
                   "Time until this route is reusable";
               }
               leaf reuse-preference {
                 type int32;
                 description
                   "Preference to use when this route is reused";
               }
               leaf expire-time {
                 type string;
                 description
                   "Time when this damping entry expires";
               }
             }
             container nhh {
               leaf nh-type {
                 type string;
                 description
                   "Special next hop: Reject, Blackhole, Receive, Multicast,
                   Local, or Unused";
               }
               leaf nh-index {
                 type uint32;
                 description
                   "Next-hop index";
               }
               leaf transport-class {
                 type string;
                 description
                   "Transport class name";
               }
               leaf nh-address {
                 type string;
                 description
                   "Address of next hop";
               }
               leaf nh-reference-count {
                 type int32;
                 description
                   "Number of references to this next hop";
               }
               leaf ext-int-intf-index {
                 type int32;
                 description
                   "Interface index of equal-external-internal multipath";
               }
               leaf nh-session-id {
                 type uint32;
                 description
                   "Nexthop session id";
               }
               leaf nh-key-opaque {
                 type string;
                 description
                   "Nexthop key opaque handle";
               }
               leaf nh-non-key-opaque {
                 type string;
                 description
                   "Nexthop non-key opaque handle";
               }
               leaf nh-key-opaque-dump {
                 type string;
                 description
                   "Nexthop key opaque app dump";
               }
               leaf nh-non-key-opaque-dump {
                 type string;
                 description
                   "Nexthop non-key opaque app dump";
               }
               leaf nh-flood-overflow {
                 type empty;
                 description
                   "Flood nexthop exceeds maximum branches";
               }
               leaf nh-kernel-id {
                 type int32;
                 description
                   "Table Id for this next hop";
               }
             }
             list nh-expand {
               key "nhe-name nhe-handle";
               description
                 "Next-hop gateway information";
               leaf nhe-name {
                 type string;
                 description
                   "Name of next-hop";
               }
               leaf nhe-handle {
                 type string;
                 description
                   "Nexthop pointer";
               }
               leaf nhe-index {
                 type int32;
                 description
                   "Next-hop index";
               }
               leaf nhe-to {
                 type string;
                 description
                   "Nexthop address";
               }
               leaf nhe-mpls-label {
                 type string;
                 description
                   "Label of MPLS packet";
               }
             }
             list rt-session-id {
               key "rt-session-id-value";
               description
                 "Session-IDs associated with route";
               leaf rt-session-id-value {
                 type int32;
                 description
                   "Value of session-id";
               }
               leaf rt-session-id-version {
                 type int32;
                 description
                   "Version of session-id";
               }
             }
             container flex-rt-statistics {
               description
                 "Statistics associated with route";
               leaf flex-rt-statistics-pkts-count {
                 type int32;
                 description
                   "Packet count";
               }
               leaf flex-rt-statistics-pps {
                 type int32;
                 description
                   "Pps";
               }
               leaf flex-rt-statistics-bytes-count {
                 type int32;
                 description
                   "Byte count";
               }
               leaf flex-rt-statistics-bps {
                 type int32;
                 description
                   "Bps";
               }
             }
             leaf bgp-group-name {
               type string;
             }
             leaf bgp-no-label-reason {
               type string;
             }
             leaf sr-policy-distinguisher {
               type uint32;
             }
             leaf sr-policy-color {
               type uint32;
             }
             leaf sr-policy-endpoint {
               type jt:ipaddr;
             }
             leaf bgp-metric-flags {
               type string;
               description
                 "BGP metrics flags";
             }
             leaf bgp-output-queue-class {
               type string;
               description
                 "BGP output queue class";
             }
             leaf cluster-id {
               type string;
             }
             leaf originator {
               type string;
             }
             leaf bgp-aigp {
               type string;
               description
                 "Accumulated IGP Metric";
             }
             leaf bgp-elc {
               type empty;
               description
                 "Entropy label capable";
             }
             leaf bgp-elc-v2 {
               type empty;
               description
                 "Entropy label capable version 2";
             }
             leaf bgp-elc-v3 {
               type empty;
               description
                 "Entropy label capable version 3";
             }
             leaf bgp-nhc-unknown-characteristics-len {
               type uint32;
               description
                 "Total length of NHC unknown characteristics";
             }
             leaf bgp-nhc-nh-valid {
               type string;
               description
                 "Whether next hop field matches route next hop";
             }
             leaf bgp-nhc-characteristic-code {
               type uint32;
               description
                 "NHC characteristic code";
             }
             leaf bgp-nhc-characteristic-len {
               type uint32;
               description
                 "NHC characteristic length";
             }
             leaf bgp-nhc-characteristic-val {
               type string;
               description
                 "NHC characteristic value";
             }
           }
           list kern-nhexpand {
             key "kern-nhe-name kern-nhe-handle";
             description
               "Next-hop gateway information";
             container srv6-info {
               leaf srv6-info-srh-sid-mode {
                 type string;
                 description
                   "Reduced/non-reduced mode for SRH";
               }
               leaf srv6-info-packet-mode {
                 type string;
                 description
                   "Packet mode for SRV6-Tunnel";
               }
               leaf srv6-info-srh-last-sid {
                 type string;
                 description
                   "Remove last sid for ACX";
               }
               leaf srv6-info-dyn-tunnel {
                 type string;
                 description
                   "SRv6 tunnel created dynamically";
               }
               leaf srv6-cos-propagation {
                 type string;
                 description
                   "SRv6 CoS propagation";
               }
               leaf srv6-ttl-propagation {
                 type string;
                 description
                   "SRv6 TTL propagation";
               }
               leaf srv6-source {
                 type jt:ipaddr;
                 description
                   "Source IPv6 address";
               }
               leaf srv6-destination {
                 type jt:ipaddr;
                 description
                   "Destination IPv6 address";
               }
               list srv6-segment-list {
                 key "srv6-segment-list-index";
                 description
                   "SRH Segment list";
                 leaf srv6-segment-list-index {
                   type uint32;
                   description
                     "SRH segment list index";
                 }
                 leaf srv6-segment-list-addr {
                   type jt:ipaddr;
                   description
                     "SRH segment address";
                 }
               }
             }
             leaf kern-nhe-platform-layer-input {
               type empty;
               description
                 "Platform layer input nexthop";
             }
             leaf kern-nhe-platform-layer-output {
               type empty;
               description
                 "Platform layer output nexthop";
             }
             leaf kern-nhe-in-kernel {
               type empty;
               description
                 "Nexthop install in kernel";
             }
             leaf kern-nhe-fib-channel {
               type string;
               description
                 "Fib channel in which route is installed";
             }
             leaf kern-nhe-name {
               type string;
               description
                 "Name of next-hop";
             }
             leaf kern-nhe-subtype {
               type string;
               description
                 "Nexthop Subtype";
             }
             leaf kern-nhe-handle {
               type string;
               description
                 "Nexthop pointer";
             }
             leaf kern-nhe-index {
               type int32;
               description
                 "Next-hop index";
             }
             leaf kern-gw-flags {
               type string;
               description
                 "Nexthop gateway flags";
             }
             leaf kern-gw-opaque {
               type string;
               description
                 "Nexthop gateway opaque data handle";
             }
             leaf kern-key-opaque {
               type string;
               description
                 "Nexthop key opaque data handle";
             }
             leaf kern-nhe-to {
               type string;
               description
                 "Nexthop address";
             }
             leaf kern-nhe-mpls-label {
               type string;
               description
                 "Label of MPLS packet";
             }
             leaf kern-nhe-pnh {
               type string;
               description
                 "Protocol Nexthop address";
             }
             leaf kern-nhe-fib-nh-str {
               type string;
               description
                 "FIB inh or cnh identifier";
             }
             leaf kern-nhe-sessionid {
               type int32;
               description
                 "Session ID";
             }
             leaf kern-nhe-tunnel-type {
               type string;
               description
                 "Tunnel type";
             }
             leaf kern-nhe-tunnel-src {
               type string;
               description
                 "Tunnel Source address";
             }
             leaf kern-nhe-tunnel-dest {
               type string;
               description
                 "Tunnel Destination address";
             }
             leaf kern-nhe-tunnel-ep {
               type string;
               description
                 "Tunnel Endpoint address";
             }
             leaf kern-nhe-tunnel-vxlan-encap-vni {
               type int32;
               description
                 "VxLAN tunnel encap vni";
             }
             leaf kern-nhe-tunnel-vxlan-decap-vni {
               type int32;
               description
                 "VxLAN tunnel decap vni";
             }
             leaf kern-nhe-translate-type {
               type string;
               description
                 "Translation type";
             }
             leaf kern-nhe-translate-src {
               type string;
               description
                 "Translation Source address";
             }
             leaf kern-nhe-translate-src-plen {
               type int32;
               description
                 "Translation Source address prefix length";
             }
             leaf kern-nhe-translate-dest {
               type string;
               description
                 "Translation Destination address";
             }
             leaf kern-nhe-translate-dest-plen {
               type int32;
               description
                 "Translation Destination address prefix length";
             }
             leaf kern-nhe-tunnel-encap-rtb-id {
               type int32;
               description
                 "Tunnel encap routing table id";
             }
             leaf kern-nhe-tunnel-decap-rtb-id {
               type int32;
               description
                 "Tunnel decap routing table id";
             }
             leaf kern-nhe-interface {
               type string;
               description
                 "Interface";
             }
             leaf kern-nhe-slice-gencfg-id {
               type int32;
               description
                 "Slice-Gencfg ID";
             }
             leaf kern-nhe-sliceid {
               type int32;
               description
                 "Slice ID";
             }
             leaf kern-nhe-fwf {
               type string;
               description
                 "Filter Name";
             }
             leaf kern-nhe-flex-tunnel-info {
               type string;
               description
                 "Flex-tunnel information of nexthop";
             }
             leaf kern-nhe-flags {
               type string;
               description
                 "Nexthop flags";
             }
             leaf kern-nhe-stats-id-group {
               type string;
               description
                 "Statistics ID Group associated with nexthop";
             }
             leaf kern-nhe-reference-count {
               type int32;
               description
                 "Nexthop reference count";
             }
             leaf kern-elnh-address {
               type string;
               description
                 "Address of Element Next-hop";
             }
           }
           leaf rt-entry-count {
             type int32;
             description
               "Number of route entries in this route";
           }
           leaf rt-announced-count {
             type int32;
             description
               "Number of announced route entries";
           }
           leaf rt-state {
             type string;
             description
               "State of this route";
           }
           leaf-list tsi {
             type string;
             description
               "Task-specific information";
           }
           list bgp-tunnel-attribute {
             key "tunnel-attribute-type";
             description
               "Tunne encap attribute information";
             leaf tunnel-attribute-type {
               type string;
             }
             leaf tunnel-attribute-rpf {
               type empty;
             }
             leaf tunnel-attribute-color {
               type uint32;
             }
             leaf tunnel-attribute-destination {
               type jt:ipaddr;
             }
           }
         }
       }
       list rt-martians {
         key "rt-martian-table-name";
         leaf rt-martian-table-name {
           type string;
           description
             "Name of the martian table, for example, inet.0";
         }
         list route-filter {
           description
             "Entries in martian table";
           leaf flags {
             type string;
             description
               "Enabled trace flags";
           }
           leaf extended-information {
             type string;
           }
           leaf match-count {
             type uint64;
           }
         }
       }
       list rt-ribexport {
         key "rt-ribexport-name";
         leaf rt-ribexport-name {
           type string;
           description
             "RIB export name";
         }
         leaf rt-ribexport-address {
           type string;
           description
             "RIB export address";
         }
         leaf rt-ribexport-flags {
           type string;
           description
             "RIB export flags";
         }
         leaf rt-ribexport-refcount {
           type uint32;
           description
             "RIB export refcount";
         }
         leaf rt-ribexport-address-family {
           type string;
           description
             "RIB export group address family";
         }
         leaf rt-ribexport-policy-name {
           type string;
           description
             "Policy name";
         }
         leaf-list rt-ribexport-import-name {
           type string;
           description
             "Import RIB name";
         }
         leaf rt-ribexport-trace-address {
           type string;
           description
             "RIB export group trace pointer";
         }
         leaf rt-ribexport-deleted {
           type empty;
           description
             "Ribexport deleted. Display of ribexport will end here.";
         }
       }
       list rt-ribgroup {
         key "rt-ribgroup-name rt-ribgroup-address";
         leaf rt-ribgroup-name {
           type string;
           description
             "Rib-group name";
         }
         leaf rt-ribgroup-address {
           type string;
           description
             "Rib-group address";
         }
         leaf rt-ribgroup-address-family {
           type string;
           description
             "Rib-group address family";
         }
         leaf rt-ribgroup-flags {
           type string;
           description
             "Rib-group flags";
         }
         leaf rt-ribgroup-refcount {
           type uint32;
           description
             "Rib-group refcount";
         }
         leaf rt-ribgroup-export-name {
           type string;
           description
             "Export RIB name";
         }
         leaf rt-ribgroup-import-name {
           type string;
           description
             "Import RIB name";
         }
         leaf rt-ribgroup-import-policy-name {
           type string;
           description
             "Import policy name";
         }
         leaf-list rt-ribgroup-import-secondary-name {
           type string;
           description
             "Import secondary RIB name";
         }
         leaf rt-ribgroup-union-head-name {
           type string;
           description
             "Rib-group union head name";
         }
         leaf rt-ribgroup-union-child-name {
           type string;
           description
             "Rib-group union child name";
         }
         leaf rt-ribgroup-deleted {
           type empty;
           description
             "Ribgroup deleted. Display of ribgroups will end here.";
         }
       }
     }
   }
   augment "/jgs:genstate" {
     description
       "Adds route-information container to top-level genstate container";
     uses route-information-top;
   }
 }
