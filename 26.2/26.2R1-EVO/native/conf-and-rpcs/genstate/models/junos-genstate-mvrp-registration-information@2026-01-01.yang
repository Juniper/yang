module junos-genstate-mvrp-registration-information {
   yang-version 1;
   namespace "http://yang.juniper.net/junos/genstate/mvrp-registration-information";
   prefix jgmri;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for mvrp-registration-information.

      Copyright (c) 2026 Juniper Networks, Inc.
      All rights reserved.";

   revision 2026-01-01 {
     description "Junos: 26.2R1.7-EVO";
   }

   grouping mvrp-registration-information-top {
     description
       "Top-level grouping";
     container mvrp-registration-information {
       description
         "Information about multicast MAC Registration state";
       list mvrp-registration-instance {
         key "mvrp-routing-instance-name";
         leaf mvrp-routing-instance-name {
           type string;
           description
             "Name of routing instance";
         }
         list mvrp-registration-vlan-entry {
           key "mvrp-vlan-id";
           description
             "Registration state information";
           leaf mvrp-vlan-id {
             type int32;
             description
               "VLAN ID";
           }
           list mvrp-registration-interface-entry {
             key "mvrp-interface-name";
             leaf mvrp-interface-name {
               type string;
               description
                 "Name of interface";
             }
             leaf mvrp-registration-state {
               type string;
               description
                 "Registration state";
             }
             leaf mvrp-registration-forced-state {
               type string;
               description
                 "Forced state";
             }
             leaf mvrp-registration-manage-state {
               type string;
               description
                 "Management state";
             }
             leaf mvrp-registration-stp-state {
               type string;
               description
                 "STP state";
             }
           }
         }
       }
     }
   }
   augment "/jgs:genstate" {
     description
       "Adds mvrp-registration-information container to top-level genstate 
       container";
     uses mvrp-registration-information-top;
   }
 }
