module junos-genstate-policy-information {
   yang-version 1;
   namespace "http://yang.juniper.net/junos/genstate/policy-information";
   prefix jgpi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for policy-information.

      Copyright (c) 2026 Juniper Networks, Inc.
      All rights reserved.";

   revision 2026-01-01 {
     description "Junos: 26.2R1.7-EVO";
   }

   grouping policy-information-top {
     description
       "Top-level grouping";
     container policy-information {
       description
         "Top-level container";
       list policy {
         key "policy-name";
         leaf policy-name {
           type string;
           description
             "Name of the policy";
         }
         container policy-defaults {
           leaf route-filter-walk-up {
             type empty;
             description
               "Route filter walk up";
           }
           leaf route-filter-no-walk-up {
             type empty;
             description
               "Route filter no walk up";
           }
         }
         list term {
           key "name";
           leaf term-stat {
             type uint32;
           }
           leaf name {
             type string;
           }
           container from {
             leaf aggregate-contributor-stat {
               type string;
               description
                 "Aggregate contributor statistics";
             }
             leaf aggregate-contributor {
               type empty;
               description
                 "Match more specifics of an aggregate";
             }
             leaf area-stat {
               type string;
               description
                 "Area statistics";
             }
             leaf area {
               type uint32;
               description
                 "OSPF area identifier";
             }
             leaf as-path-stat {
               type string;
               description
                 "AS path statistics";
             }
             leaf as-path {
               type string;
               description
                 "Name of AS path regular expression (BGP only)";
             }
             leaf as-path-group-stat {
               type string;
               description
                 "AS path group statistics";
             }
             leaf as-path-group {
               type string;
               description
                 "Name of AS path group (BGP only)";
             }
             leaf bgp-srte-discriminator-stat {
               type string;
               description
                 "BGP SRTE discriminator statistics";
             }
             leaf bgp-srte-discriminator {
               type uint32;
               description
                 "SRTE discriminator";
             }
             leaf bridge-domain-id-stat {
               type string;
               description
                 "Bridge domain id statistics";
             }
             leaf bridge-domain-id {
               type uint32;
               description
                 "Bridge Domain ID";
             }
             leaf color-stat {
               type string;
               description
                 "Color statistics";
             }
             leaf color1 {
               type uint32;
               description
                 "Color1";
             }
             leaf color2-stat {
               type string;
               description
                 "Color2 statistics";
             }
             leaf color2 {
               type int32;
             }
             leaf community-stat {
               type string;
               description
                 "Community statistics";
             }
             leaf-list community {
               type string;
               description
                 "Basic community";
             }
             leaf condition-stat {
               type string;
               description
                 "Condition statistics";
             }
             leaf condition {
               type string;
               description
                 "Condition to match on";
             }
             leaf evpn-mac-route-stat {
               type string;
               description
                 "EVPN mac route statistics";
             }
             leaf evpn-mac-route {
               type uint32;
               description
                 "EVPN Mac Route type";
             }
             leaf evpn-tag-stat {
               type string;
               description
                 "EVPN tag statistics";
             }
             leaf evpn-tag {
               type uint32;
               description
                 "Tag in EVPN Route";
             }
             leaf family-stat {
               type string;
             }
             leaf family {
               type string;
             }
             leaf igp-instance-stat {
               type string;
               description
                 "IGP instance statistics";
             }
             leaf igp-instance {
               type string;
               description
                 "IGP instance";
             }
             leaf igp-instance-regex-stat {
               type string;
               description
                 "IGP instance regex statistics";
             }
             leaf igp-instance-regex {
               type string;
               description
                 "IGP instance regex";
             }
             leaf instance-stat {
               type string;
               description
                 "Instance statistics";
             }
             leaf-list instance {
               type string;
               description
                 "Routing protocol instance";
             }
             leaf instance-any-stat {
               type string;
               description
                 "Instance any statistics";
             }
             leaf instance-any {
               type empty;
               description
                 "Any routing protocol instance";
             }
             leaf instance-list-stat {
               type string;
               description
                 "Instance list statistics";
             }
             leaf instance-list {
               type string;
               description
                 "A list of routing protocol instances";
             }
             leaf interface-stat {
               type string;
               description
                 "Interface statistics";
             }
             leaf-list interface {
               type string;
               description
                 "Interface name or address";
             }
             leaf policy-level-stat {
               type string;
               description
                 "Level statistics";
             }
             leaf policy-level {
               type uint32;
             }
             leaf policy-local-preference-stat {
               type string;
               description
                 "Local preference statistics";
             }
             leaf policy-local-preference {
               type uint32;
               description
                 "Local preference associated with a route";
             }
             leaf lsp-stat {
               type string;
               description
                 "LSP statistics";
             }
             leaf lsp {
               type string;
               description
                 "Label switched path name";
             }
             leaf lsp-regex-stat {
               type string;
               description
                 "LSP regex statistics";
             }
             leaf lsp-regex {
               type string;
               description
                 "Label switched path name regular expression";
             }
             leaf metric-stat {
               type string;
               description
                 "Metric statistics";
             }
             leaf metric1 {
               type uint32;
               description
                 "Metric value";
             }
             leaf metric2-stat {
               type string;
               description
                 "Metric2 statistics";
             }
             leaf metric-2 {
               type uint32;
               description
                 "Metric value 2";
             }
             leaf metric3-stat {
               type string;
               description
                 "Metric3 statistics";
             }
             leaf metric3 {
               type uint32;
               description
                 "Metric value 3";
             }
             leaf metric4-stat {
               type string;
               description
                 "Metric4 statistics";
             }
             leaf metric4 {
               type uint32;
               description
                 "Metric value 4";
             }
             leaf policy-neighbor-stat {
               type string;
               description
                 "Policy neighbor statistics";
             }
             leaf policy-neighbor {
               type string;
               description
                 "Neighboring router";
             }
             leaf next-hop-stat {
               type string;
               description
                 "Nexthop statistics";
             }
             leaf next-hop {
               type jt:ipaddr;
               description
                 "Next-hop address";
             }
             leaf next-hop-type-stat {
               type string;
               description
                 "Nexthop type statistics";
             }
             leaf next-hop-type {
               type string;
               description
                 "Next-hop type";
             }
             leaf nlri-route-type-stat {
               type string;
               description
                 "NLRI route type statistics";
             }
             leaf nlri-route-type {
               type uint32;
               description
                 "Route type from NLRI (1..10)";
             }
             leaf origin-stat {
               type string;
               description
                 "Origin statistics";
             }
             leaf origin {
               type string;
               description
                 "BGP origin attribute";
             }
             leaf policy-name-stat {
               type string;
               description
                 "Policy statistics";
             }
             leaf policy-name {
               type string;
               description
                 "Name of the policy";
             }
             leaf preference-stat {
               type string;
               description
                 "Preference statistics";
             }
             leaf preference1 {
               type uint32;
             }
             leaf preference2-stat {
               type string;
               description
                 "Preference2 statistics";
             }
             leaf preference-2 {
               type uint32;
               description
                 "Preference value 2";
             }
             leaf prefix-list-stat {
               type string;
               description
                 "Prefix list statistics";
             }
             leaf-list prefix-list {
               type string;
               description
                 "List of prefix-lists of routes to match";
             }
             leaf programmed-stat {
               type string;
               description
                 "Programmed statistics";
             }
             leaf programmed {
               type empty;
               description
                 "API-programmed route";
             }
             leaf protocol-stat {
               type string;
               description
                 "Protocol statistics";
             }
             leaf protocol {
               type string;
               description
                 "Protocol from which route was learned";
             }
             leaf rib-stat {
               type string;
               description
                 "RIB statistics";
             }
             leaf rib {
               type string;
               description
                 "Routing table";
             }
             leaf rib-list-stat {
               type string;
               description
                 "RIB list statistics";
             }
             leaf-list rib-list {
               type string;
               description
                 "RIB list";
             }
             leaf route-distinguisher-stat {
               type string;
               description
                 "Route distinguisher statistics";
             }
             leaf-list route-distinguisher {
               type string;
               description
                 "Name of the route-distinguisher";
             }
             leaf route-type-stat {
               type string;
               description
                 "Route type statistics";
             }
             leaf route-type {
               type string;
               description
                 "Route type";
             }
             leaf-list rtf-prefix-list-stat {
               type string;
               description
                 "RTF prefix list statistics";
             }
             leaf-list rtf-prefix-list {
               type string;
               description
                 "List of rtf-prefix-lists of routes to match";
             }
             leaf source-address-filter-list-stat {
               type string;
               description
                 "Source address filter list statistics";
             }
             leaf-list source-address-filter-list {
               type string;
               description
                 "List of source-address-filter-lists of routes to match";
             }
             leaf srte-color-stat {
               type string;
               description
                 "SRTE color statistics";
             }
             leaf srte-color {
               type uint32;
               description
                 "SRTE color";
             }
             leaf state-stat {
               type string;
               description
                 "State statistics";
             }
             leaf state {
               type string;
               description
                 "HFRR profile Current state";
             }
             leaf tag-stat {
               type string;
               description
                 "Policy tag statistics";
             }
             leaf policy-tag {
               type uint32;
               description
                 "Tag string";
             }
             leaf tag2-stat {
               type string;
               description
                 "Policy tag2 statistics";
             }
             leaf policy-tag2 {
               type uint32;
               description
                 "Tag string 2";
             }
             leaf tunnel-type-stat {
               type string;
               description
                 "Tunnel type statistics";
             }
             leaf tunnel-type {
               type string;
               description
                 "Tunnel type";
             }
             leaf validation-state-stat {
               type string;
               description
                 "Validation database statistics";
             }
             leaf validation-database {
               type string;
               description
                 "Name to identify a validation-state";
             }
             leaf mac-filter-list-stat {
               type string;
               description
                 "MAC filter list statistics";
             }
             leaf-list mac-filter-list {
               type string;
               description
                 "List of mac-filter-list macs to match";
             }
             leaf mac-filter {
               type string;
               description
                 "Information on mac filter";
             }
             leaf traffic-engineering-stat {
               type string;
               description
                 "Traffic engineering statistics";
             }
             list as-path-calc-length {
               key "as-path-calc-length-value";
               description
                 "Number of BGP ASes excluding confederations";
               leaf as-path-calc-length-stat {
                 type string;
                 description
                   "AS path calculation length statistics";
               }
               leaf equal {
                 type empty;
               }
               leaf orhigher {
                 type empty;
               }
               leaf orlower {
                 type empty;
               }
               leaf as-path-calc-length-value {
                 type uint32;
               }
             }
             container as-path-neighbors {
               leaf as-path-neighbors-stat {
                 type string;
                 description
                   "AS path neighbors statistics";
               }
               leaf as-list {
                 type string;
                 description
                   "AS list name";
               }
               leaf as-list-group {
                 type string;
                 description
                   "AS list group name";
               }
             }
             container as-path-origins {
               leaf as-path-origins-stat {
                 type string;
                 description
                   "AS path origins statistics";
               }
               leaf as-list {
                 type string;
                 description
                   "AS list name";
               }
               leaf as-list-group {
                 type string;
                 description
                   "AS list group name";
               }
             }
             container as-path-transits {
               leaf as-path-transits-stat {
                 type string;
                 description
                   "AS path transits statistics";
               }
               leaf as-list {
                 type string;
                 description
                   "AS list name";
               }
               leaf as-list-group {
                 type string;
                 description
                   "AS list group name";
               }
             }
             list as-path-unique-count {
               key "policy-value";
               description
                 "Number of unique BGP ASes excluding confederations";
               leaf as-path-unique-count-stat {
                 type string;
                 description
                   "AS path unique count statistics";
               }
               leaf equal {
                 type empty;
               }
               leaf orhigher {
                 type empty;
               }
               leaf orlower {
                 type empty;
               }
               leaf policy-value {
                 type uint32;
               }
             }
             container external {
               description
                 "External route";
               leaf external-stat {
                 type string;
                 description
                   "External statistics";
               }
               leaf external-type {
                 type uint32;
               }
               leaf nssa-only {
                 type empty;
               }
             }
             list flowspec-attribute {
               key "flowspec-attribute-list-name";
               leaf flowspec-attribute-stat {
                 type string;
                 description
                   "Flowspec attribute statistics";
               }
               leaf flowspec-attribute-list-name {
                 type string;
                 description
                   "Policy flowspec attributes";
               }
               container match {
                 leaf dscp {
                   type string;
                 }
                 leaf dscp-any-val {
                   type empty;
                 }
                 leaf icmp-code {
                   type string;
                 }
                 leaf icmp-code-any-val {
                   type empty;
                 }
                 leaf icmp-type {
                   type string;
                 }
                 leaf icmp-type-any-val {
                   type empty;
                 }
                 leaf icmp6-code {
                   type string;
                 }
                 leaf icmp6-code-any-val {
                   type empty;
                 }
                 leaf icmp6-type {
                   type string;
                 }
                 leaf icmp6-type-any-val {
                   type empty;
                 }
                 leaf proto {
                   type string;
                 }
                 leaf proto-any-val {
                   type empty;
                 }
                 leaf packet-length {
                   type string;
                 }
                 leaf packet-length-any-val {
                   type empty;
                 }
                 leaf flow-label {
                   type string;
                 }
                 leaf flow-label-any-val {
                   type empty;
                 }
                 leaf fragment-any-val {
                   type empty;
                 }
                 leaf fragment {
                   type string;
                 }
                 leaf tcp-flags-any-val {
                   type empty;
                 }
                 leaf tcp-flags {
                   type string;
                 }
                 leaf destination-v6-offset {
                   type empty;
                 }
                 leaf source-v6-offset {
                   type empty;
                 }
                 leaf destination {
                   type empty;
                 }
                 leaf source-match {
                   type empty;
                 }
                 leaf port-any-value {
                   type empty;
                 }
                 leaf port-value {
                   type string;
                 }
                 leaf port-range {
                   type string;
                 }
                 leaf port-count {
                   type uint32;
                 }
                 leaf port-count-flag {
                   type string;
                 }
                 leaf range-count {
                   type uint32;
                 }
                 leaf range-count-flag {
                   type string;
                 }
                 leaf cumulative-count {
                   type uint32;
                 }
                 leaf cumulative-count-flag {
                   type string;
                 }
                 leaf destination-port-any-value {
                   type empty;
                 }
                 leaf destination-port-value {
                   type string;
                 }
                 leaf destination-port-range {
                   type string;
                 }
                 leaf destination-port-count {
                   type uint32;
                 }
                 leaf destination-port-count-flag {
                   type string;
                 }
                 leaf destination-port-range-count {
                   type uint32;
                 }
                 leaf destination-port-range-count-flag {
                   type string;
                 }
                 leaf destination-port-cumulative-count {
                   type uint32;
                 }
                 leaf destination-port-cumulative-count-flag {
                   type string;
                 }
                 leaf source-port-any-value {
                   type empty;
                 }
                 leaf source-port-value {
                   type string;
                 }
                 leaf source-port-range {
                   type string;
                 }
                 leaf source-port-count {
                   type uint32;
                 }
                 leaf source-port-count-flag {
                   type string;
                 }
                 leaf source-port-range-count {
                   type uint32;
                 }
                 leaf source-port-range-count-flag {
                   type string;
                 }
                 leaf source-port-cumulative-count {
                   type uint32;
                 }
                 leaf source-port-cumulative-count-flag {
                   type string;
                 }
               }
               container flow-action {
                 leaf rate-limit {
                   type empty;
                 }
                 leaf mark {
                   type empty;
                 }
                 leaf redirect {
                   type empty;
                 }
                 leaf ri {
                   type empty;
                 }
                 leaf sample {
                   type empty;
                 }
               }
               container invert-match {
                 leaf invert-dscp {
                   type string;
                 }
                 leaf invert-dscp-any-val {
                   type empty;
                 }
                 leaf invert-icmp-code {
                   type string;
                 }
                 leaf invert-icmp-code-any-val {
                   type empty;
                 }
                 leaf invert-icmp-type {
                   type string;
                 }
                 leaf invert-icmp-type-any-val {
                   type empty;
                 }
                 leaf invert-icmp6-code {
                   type string;
                 }
                 leaf invert-icmp6-code-any-val {
                   type empty;
                 }
                 leaf invert-icmp6-type {
                   type string;
                 }
                 leaf invert-icmp6-type-any-val {
                   type empty;
                 }
                 leaf invert-proto {
                   type string;
                 }
                 leaf invert-proto-any-val {
                   type empty;
                 }
                 leaf invert-packet-length {
                   type string;
                 }
                 leaf invert-packet-length-any-val {
                   type empty;
                 }
                 leaf invert-flow-label {
                   type string;
                 }
                 leaf invert-flow-label-any-val {
                   type empty;
                 }
                 leaf invert-fragment-any-val {
                   type empty;
                 }
                 leaf invert-fragment {
                   type string;
                 }
                 leaf invert-tcp-flags-any-val {
                   type empty;
                 }
                 leaf invert-tcp-flags {
                   type string;
                 }
                 leaf invert-destination-v6-offset {
                   type empty;
                 }
                 leaf invert-source-v6-offset {
                   type empty;
                 }
                 leaf invert-destination {
                   type empty;
                 }
                 leaf invert-source {
                   type empty;
                 }
                 leaf invert-port-any-value {
                   type empty;
                 }
                 leaf invert-port-value {
                   type string;
                 }
                 leaf invert-port-range {
                   type string;
                 }
                 leaf invert-destination-port-any-value {
                   type empty;
                 }
                 leaf invert-destination-port-value {
                   type string;
                 }
                 leaf invert-destination-port-range {
                   type string;
                 }
                 leaf invert-source-port-any-value {
                   type empty;
                 }
                 leaf invert-source-port-value {
                   type string;
                 }
                 leaf invert-source-port-range {
                   type string;
                 }
               }
             }
             container multicast-scope {
               description
                 "Multicast scope to match";
               leaf multicast-scope-stat {
                 type string;
                 description
                   "Multicast scope statistics";
               }
               leaf orlower {
                 type empty;
               }
               leaf orhigher {
                 type empty;
               }
               leaf equal {
                 type empty;
               }
               leaf multicast-scope-value {
                 type uint32;
                 description
                   "Multicast scope value";
               }
               leaf link-local {
                 type empty;
               }
               leaf node-local {
                 type empty;
               }
               leaf organization-local {
                 type empty;
               }
               leaf site-local {
                 type empty;
               }
               leaf global {
                 type empty;
               }
             }
             container prefix-list-filter-information {
               leaf prefix-list-filter-stat {
                 type string;
                 description
                   "Prefix list filter statistics";
               }
               list prefix-list-filter {
                 key "prefix-list-filter-name";
                 leaf prefix-list-filter-name {
                   type string;
                 }
               }
             }
             container prefix-segment {
               description
                 "The prefix segment attributes";
               leaf prefix-segment-stat {
                 type string;
                 description
                   "Prefix segment statistics";
               }
               leaf psid-extended-data {
                 type int32;
                 description
                   "Prefix segment extendend information";
               }
               leaf prefix-segment-index-value {
                 type uint32;
               }
               leaf node-segment {
                 type empty;
               }
               leaf redistribute {
                 type empty;
               }
               container algorithm {
                 leaf prefix-segment-index-value {
                   type uint32;
                 }
                 leaf algorithm-name {
                   type uint32;
                 }
                 leaf node-segment {
                   type empty;
                 }
               }
             }
             container protocol-instance-information {
               description
                 "Protocol instance";
               leaf protocol-instance-stat {
                 type string;
                 description
                   "Protocol instance statistics";
               }
               list protocol-instance {
                 key "protocol";
                 leaf protocol {
                   type string;
                   description
                     "Protocol from which route was learned";
                 }
                 leaf protocol-instance-name {
                   type string;
                 }
               }
             }
             container route-filter-information {
               leaf route-filter-stat {
                 type string;
                 description
                   "Route filter statistics";
               }
               list route-filter {
                 description
                   "Entries in martian table";
                 leaf flags {
                   type string;
                   description
                     "Enabled trace flags";
                 }
                 leaf match-count {
                   type uint64;
                 }
               }
             }
             container source-address-filter-information {
               leaf source-address-filter-stat {
                 type string;
                 description
                   "Source address filter statistics";
               }
               list source-address-filter {
                 leaf flags {
                   type string;
                   description
                     "Enabled trace flags";
                 }
               }
             }
             container traffic-engineering {
               description
                 "Traffic-Engineering related parameters";
               leaf traffic-engineering-stat {
                 type string;
                 description
                   "Traffic engineering statistics";
               }
               leaf te-identifier {
                 type uint64;
                 description
                   "BGP-TE identifier";
               }
               leaf te-protocol {
                 type string;
               }
               container link {
                 container te-from {
                   leaf as {
                     type uint32;
                   }
                   leaf router-id {
                     type jt:ipaddr;
                   }
                   leaf sys-id {
                     type string;
                   }
                   leaf node-type {
                     type string;
                   }
                   leaf any {
                     type empty;
                   }
                   leaf link-address {
                     type string;
                   }
                 }
                 container te-to {
                   leaf as {
                     type uint32;
                   }
                   leaf router-id {
                     type jt:ipaddr;
                   }
                   leaf sys-id {
                     type string;
                   }
                   leaf node-type {
                     type string;
                   }
                   leaf any {
                     type empty;
                   }
                   leaf link-address {
                     type string;
                   }
                 }
               }
               container ipv4-prefix {
                 leaf as {
                   type uint32;
                 }
                 leaf router-id {
                   type jt:ipaddr;
                 }
                 leaf prefix {
                   type jt:ipaddr;
                 }
                 leaf sys-id {
                   type string;
                 }
                 leaf any {
                   type empty;
                 }
               }
               container ipv6-prefix {
                 leaf as {
                   type uint32;
                 }
                 leaf router-id {
                   type jt:ipaddr;
                 }
                 leaf prefix {
                   type jt:ipaddr;
                 }
                 leaf sys-id {
                   type string;
                 }
                 leaf any {
                   type empty;
                 }
               }
               container srv6-sid {
                 leaf as {
                   type uint32;
                 }
                 leaf router-id {
                   type jt:ipaddr;
                 }
                 leaf end-sid {
                   type string;
                   description
                     "SRv6 end sid";
                 }
                 leaf sys-id {
                   type string;
                 }
                 leaf any {
                   type empty;
                 }
               }
               container te-node {
                 leaf as {
                   type uint32;
                 }
                 leaf router-id {
                   type jt:ipaddr;
                 }
                 leaf sys-id {
                   type string;
                 }
                 leaf node-type {
                   type string;
                 }
                 leaf any {
                   type empty;
                 }
               }
               container te-springte {
                 leaf as {
                   type uint32;
                 }
                 leaf router-id {
                   type jt:ipaddr;
                 }
                 leaf color1 {
                   type uint32;
                   description
                     "Color1";
                 }
                 leaf discriminator {
                   type uint32;
                   description
                     "Spring-te discriminator";
                 }
                 leaf endpoint {
                   type string;
                   description
                     "Spring-te endpoint";
                 }
                 leaf proto-origin {
                   type string;
                   description
                     "Spring-te proto-origin";
                 }
                 leaf origin-as {
                   type uint32;
                 }
                 leaf origin-addr {
                   type string;
                   description
                     "Spring-te origin address";
                 }
               }
             }
             container route-distinguisher-info {
               leaf rd-filter-flag {
                 type string;
                 description
                   "Route distinguisher filter flag";
               }
               leaf-list rd-details {
                 type string;
                 description
                   "Route distingusher details";
               }
             }
             container route-target-prefix-count {
               description
                 "Number of BGP prefixes with a 'Route Target' set";
               leaf route-target-prefix-count-stat {
                 type string;
                 description
                   "'Route Target' extended community prefix count 
                   statistics";
               }
               leaf orhigher {
                 type empty;
               }
               leaf policy-value {
                 type uint32;
               }
             }
             list community-count {
               key "policy-value";
               description
                 "Number of BGP communities";
               leaf community-count-stat {
                 type string;
                 description
                   "Community count statistics";
               }
               leaf equal {
                 type empty;
               }
               leaf orhigher {
                 type empty;
               }
               leaf orlower {
                 type empty;
               }
               leaf policy-value {
                 type uint32;
               }
             }
             list large-community-count {
               key "policy-value";
               description
                 "Large community count";
               leaf large-community-count-stat {
                 type string;
                 description
                   "Large community count statistics";
               }
               leaf equal {
                 type empty;
               }
               leaf orhigher {
                 type empty;
               }
               leaf orlower {
                 type empty;
               }
               leaf policy-value {
                 type uint32;
               }
             }
             container next-hop-weight {
               description
                 "Nexthop weight";
               leaf next-hop-weight-stat {
                 type string;
                 description
                   "Nexthop weight statistics";
               }
               leaf equal-to {
                 type uint32;
               }
               leaf greater-than {
                 type uint32;
               }
               leaf greater-than-equal {
                 type uint32;
               }
               leaf less-than {
                 type uint32;
               }
               leaf less-than-equal {
                 type uint32;
               }
               leaf all-nexthop {
                 type empty;
               }
             }
             container next-hop-ecmp {
               description
                 "Nexthop ecmp";
               leaf next-hop-ecmp-stat {
                 type string;
                 description
                   "Nexthop ecmp statistics";
               }
               leaf equal-to {
                 type uint32;
               }
               leaf greater-than {
                 type uint32;
               }
               leaf greater-than-equal {
                 type uint32;
               }
               leaf less-than {
                 type uint32;
               }
               leaf less-than-equal {
                 type uint32;
               }
             }
             container source-routing-path {
               leaf source-routing-path-stat {
                 type string;
                 description
                   "Source routing path statistics";
               }
               leaf color-value {
                 type uint32;
                 description
                   "Color";
               }
               leaf dest {
                 type string;
                 description
                   "Spring-te lsp IPV4/IPV6 destination without color";
               }
               leaf name-regex {
                 type string;
                 description
                   "Spring-te lsp name regex";
               }
               leaf origin-value {
                 type string;
                 description
                   "Origin";
               }
               leaf route-distinguisher-value {
                 type uint32;
                 description
                   "Route distinguisher";
               }
               leaf tunnel-source {
                 type string;
                 description
                   "Source protocol";
               }
             }
             container validation-database-instance {
               description
                 "Validation database instance";
               leaf validation-database-instance-stat {
                 type string;
                 description
                   "Validation database instance statistics";
               }
               leaf validation-database-instance-database-name {
                 type string;
                 description
                   "Name of the validation database";
               }
               leaf validation-database-instance-state-invalid {
                 type empty;
                 description
                   "Invalid validation database instance state";
               }
               leaf validation-database-instance-state-unknown {
                 type empty;
                 description
                   "Unknown validation database instance state";
               }
               leaf validation-database-instance-state-valid {
                 type empty;
                 description
                   "Valid validation database instance state";
               }
             }
             container route-filter-list-information {
               leaf route-filter-list-stat {
                 type string;
                 description
                   "Route filter list statistics";
               }
               list route-filter-list {
                 key "route-filter-list-name";
                 leaf route-filter-list-name {
                   type string;
                   description
                     "List of route-filter-lists of routes to match";
                 }
               }
             }
           }
           container policy-to {
             leaf family-stat {
               type string;
             }
             leaf family {
               type string;
             }
             leaf area-stat {
               type string;
               description
                 "Area statistics";
             }
             leaf area {
               type uint32;
               description
                 "OSPF area identifier";
             }
             leaf as-path-stat {
               type string;
               description
                 "AS path statistics";
             }
             leaf as-path {
               type string;
               description
                 "Name of AS path regular expression (BGP only)";
             }
             leaf as-path-group-stat {
               type string;
               description
                 "AS path group statistics";
             }
             leaf as-path-group {
               type string;
               description
                 "Name of AS path group (BGP only)";
             }
             leaf color-stat {
               type string;
               description
                 "Color statistics";
             }
             leaf color1 {
               type uint32;
               description
                 "Color1";
             }
             leaf color2-stat {
               type string;
               description
                 "Color2 statistics";
             }
             leaf color2 {
               type int32;
             }
             leaf community-stat {
               type string;
               description
                 "Community statistics";
             }
             leaf-list community {
               type string;
               description
                 "Basic community";
             }
             leaf instance-stat {
               type string;
               description
                 "Instance statistics";
             }
             leaf-list instance {
               type string;
               description
                 "Routing protocol instance";
             }
             leaf instance-any-stat {
               type string;
               description
                 "Instance any statistics";
             }
             leaf instance-any {
               type empty;
               description
                 "Any routing protocol instance";
             }
             leaf instance-list-stat {
               type string;
               description
                 "Instance list statistics";
             }
             leaf instance-list {
               type string;
               description
                 "A list of routing protocol instances";
             }
             leaf interface-stat {
               type string;
               description
                 "Interface statistics";
             }
             leaf-list interface {
               type string;
               description
                 "Interface name or address";
             }
             leaf policy-level-stat {
               type string;
               description
                 "Level statistics";
             }
             leaf policy-level {
               type uint32;
             }
             leaf policy-local-preference-stat {
               type string;
               description
                 "Local preference statistics";
             }
             leaf policy-local-preference {
               type uint32;
               description
                 "Local preference associated with a route";
             }
             leaf metric-stat {
               type string;
               description
                 "Metric statistics";
             }
             leaf metric1 {
               type uint32;
               description
                 "Metric value";
             }
             leaf metric2-stat {
               type string;
               description
                 "Metric2 statistics";
             }
             leaf metric-2 {
               type uint32;
               description
                 "Metric value 2";
             }
             leaf metric3-stat {
               type string;
               description
                 "Metric3 statistics";
             }
             leaf metric3 {
               type uint32;
               description
                 "Metric value 3";
             }
             leaf metric4-stat {
               type string;
               description
                 "Metric4 statistics";
             }
             leaf metric4 {
               type uint32;
               description
                 "Metric value 4";
             }
             leaf policy-neighbor-stat {
               type string;
               description
                 "Policy neighbor statistics";
             }
             leaf policy-neighbor {
               type string;
               description
                 "Neighboring router";
             }
             leaf next-hop-stat {
               type string;
               description
                 "Nexthop statistics";
             }
             leaf next-hop {
               type jt:ipaddr;
               description
                 "Next-hop address";
             }
             leaf origin-stat {
               type string;
               description
                 "Origin statistics";
             }
             leaf origin {
               type string;
               description
                 "BGP origin attribute";
             }
             leaf preference-stat {
               type string;
               description
                 "Preference statistics";
             }
             leaf preference1 {
               type uint32;
             }
             leaf preference2-stat {
               type string;
               description
                 "Preference2 statistics";
             }
             leaf preference-2 {
               type uint32;
               description
                 "Preference value 2";
             }
             leaf programmed-stat {
               type string;
               description
                 "Programmed statistics";
             }
             leaf programmed {
               type empty;
               description
                 "API-programmed route";
             }
             leaf protocol-stat {
               type string;
               description
                 "Protocol statistics";
             }
             leaf protocol {
               type string;
               description
                 "Protocol from which route was learned";
             }
             leaf rib-stat {
               type string;
               description
                 "RIB statistics";
             }
             leaf rib {
               type string;
               description
                 "Routing table";
             }
             leaf tag-stat {
               type string;
               description
                 "Policy tag statistics";
             }
             leaf policy-tag {
               type uint32;
               description
                 "Tag string";
             }
             leaf tag2-stat {
               type string;
               description
                 "Policy tag2 statistics";
             }
             leaf policy-tag2 {
               type uint32;
               description
                 "Tag string 2";
             }
             container external {
               description
                 "External route";
               leaf external-stat {
                 type string;
                 description
                   "External statistics";
               }
               leaf external-type {
                 type uint32;
               }
               leaf nssa-only {
                 type empty;
               }
             }
           }
           container then {
             leaf accept-stat {
               type string;
             }
             leaf accept {
               type empty;
               description
                 "Accept a route";
             }
             leaf advertise-locator-stat {
               type string;
               description
                 "Advertise locator statistics";
             }
             leaf advertise-locator {
               type empty;
               description
                 "Advertise SRv6 locator";
             }
             leaf advertise-locator-internal {
               type empty;
               description
                 "Advertise SRv6 locator internal";
             }
             leaf aggregate-bandwidth-stat {
               type string;
               description
                 "Aggregate bandwidth statistics";
             }
             leaf aggregate-bandwidth {
               type int32;
               description
                 "Aggregate bandwidth";
             }
             leaf aggregate-weight-multiplier-stat {
               type string;
               description
                 "Aggregate weight statistics";
             }
             leaf aggregate-weight-multiplier {
               type int32;
               description
                 "Aggregate weight multiplier";
             }
             leaf auto-link-bandwidth-stat {
               type string;
               description
                 "Auto link bandwidth statistics";
             }
             leaf auto-link-bandwidth {
               type empty;
               description
                 "Auto link bandwidth";
             }
             leaf push-label-stat {
               type string;
               description
                 "Push label statistics";
             }
             leaf push-label {
               type empty;
               description
                 "Push label";
             }
             leaf analyze-stat {
               type string;
               description
                 "Analyze statistics";
             }
             leaf analyze {
               type empty;
               description
                 "Send to registered controllers for analysis";
             }
             leaf as-path-prepend-stat {
               type string;
               description
                 "AS path prepend statistics";
             }
             leaf as-path-prepend {
               type uint32;
               description
                 "Prepend AS numbers to an AS path (BGP only)";
             }
             leaf as-path-replace-stat {
               type string;
               description
                 "AS path replace statistics";
             }
             leaf as-path-replace {
               type string;
               description
                 "Replace AS numbers, or 'private' for an AS path (BGP only)";
             }
             leaf class-stat {
               type string;
               description
                 "Class statistics";
             }
             leaf-list class {
               type string;
               description
                 "An instance of BGP output queue statistics";
             }
             leaf cos-next-hop-map-stat {
               type string;
               description
                 "COS next hop map statistics";
             }
             leaf cos-next-hop-map {
               type string;
               description
                 "The CoS-based next-hop map in forwarding table";
             }
             leaf damping-stat {
               type string;
               description
                 "Damping statistics";
             }
             leaf damping {
               type string;
               description
                 "Define BGP route flap damping parameters";
             }
             leaf default-action-stat {
               type string;
               description
                 "Default action statistics";
             }
             leaf default-action {
               type string;
               description
                 "The default policy action";
             }
             leaf destination-class-stat {
               type string;
               description
                 "Destination class statistics";
             }
             leaf destination-class {
               type string;
               description
                 "The destination class in forwarding table";
             }
             leaf dynamic-tunnel-attributes-stat {
               type string;
               description
                 "Dynamic tunnel attribute statistics";
             }
             leaf dynamic-tunnel-attributes {
               type string;
               description
                 "The dynamic tunnel attributes used for forwarding";
             }
             leaf fib-install-priority-stat {
               type string;
               description
                 "FIB install priority statistics";
             }
             leaf fib-install-priority {
               type string;
               description
                 "FIB install priority";
             }
             leaf filter-stat {
               type string;
               description
                 "Filter statistics";
             }
             leaf filter {
               type string;
               description
                 "Next-hop firewall filter";
             }
             leaf flow-route-accounting-stat {
               type string;
             }
             leaf flow-route-accounting {
               type empty;
               description
                 "Flow route accounting";
             }
             leaf get-route-range {
               type empty;
               description
                 "Get route range";
             }
             leaf ignore-service-label-stat {
               type string;
               description
                 "Ignore service label statistics";
             }
             leaf ignore-service-label {
               type string;
               description
                 "Ignore service labels";
             }
             leaf install-to-fib-stat {
               type string;
               description
                 "Install to FIB statistics";
             }
             leaf install-to-fib {
               type string;
               description
                 "Install to FIB";
             }
             leaf ipv4-source-router-id-stat {
               type string;
               description
                 "IPV4 source router id statistics";
             }
             leaf ipv4-source-router-id {
               type empty;
             }
             leaf ipv4-source-router-id-address {
               type string;
               description
                 "IPV4 source router id address";
             }
             leaf ipv6-source-router-id-stat {
               type string;
               description
                 "IPV6 source router id statistics";
             }
             leaf ipv6-source-router-id {
               type empty;
             }
             leaf ipv6-source-router-id-address {
               type string;
               description
                 "IPV6 source router id address";
             }
             leaf label-allocation-stat {
               type string;
               description
                 "Label allocation statistics";
             }
             leaf label-allocation {
               type string;
               description
                 "Label allocation mode";
             }
             leaf label-allocation-fallback-reject-stat {
               type string;
               description
                 "Label allocation fallback reject statistics";
             }
             leaf label-allocation-fallback-reject {
               type string;
               description
                 "Suppress prefix export when label allocation fails";
             }
             leaf limit-bandwidth-stat {
               type string;
               description
                 "Limit bandwidth statistics";
             }
             leaf limit-bandwidth {
               type uint64;
               description
                 "Limit advertised aggregate outbound link bandwidth";
             }
             leaf load-balance-stat {
               type string;
               description
                 "Load balance statistics";
             }
             leaf load-balance {
               type string;
               description
                 "Load-balancing algorithm chosen";
             }
             leaf mhop-bfd-port-stat {
               type string;
               description
                 "Mhop bfd port statistics";
             }
             leaf mhop-bfd-port {
               type uint32;
               description
                 "Use port number 4784 for MPLS-BFD as per RFC5884";
             }
             leaf multipath-resolve-stat {
               type string;
               description
                 "Multipath resolve statistics";
             }
             leaf multipath-resolve {
               type string;
               description
                 "Use all paths for resolution over this prefix";
             }
             leaf next-stat {
               type string;
               description
                 "Next policy statistics";
             }
             leaf next {
               type string;
               description
                 "Skip to next policy or term";
             }
             leaf no-backup-stat {
               type string;
               description
                 "No backup statistics";
             }
             leaf no-backup {
               type empty;
               description
                 "This prefix should not have backup";
             }
             leaf no-entropy-label-capability-stat {
               type string;
               description
                 "No entropy label capability statistics";
             }
             leaf no-entropy-label-capability {
               type empty;
               description
                 "Don't advertise entropy label capability";
             }
             leaf origin-stat {
               type string;
               description
                 "Origin statistics";
             }
             leaf origin {
               type string;
               description
                 "BGP origin attribute";
             }
             leaf p2mp-lsp-root-stat {
               type string;
               description
                 "P2mp lsp root statistics";
             }
             leaf p2mp-lsp-root {
               type jt:ipaddr;
               description
                 "P2mp lsp root address";
             }
             leaf policy-priority-stat {
               type string;
               description
                 "Policy priority statistics";
             }
             leaf policy-priority {
               type string;
             }
             leaf reject-stat {
               type string;
               description
                 "Reject statistics";
             }
             leaf reject {
               type empty;
               description
                 "Reject a route";
             }
             leaf request-long-lived-ack-stat {
               type string;
               description
                 "Request long lived ack statistics";
             }
             leaf request-long-lived-ack {
               type empty;
               description
                 "Advertise route after forwarding is programmed";
             }
             leaf resolution-map-stat {
               type string;
               description
                 "Resolution map stat";
             }
             leaf resolution-map {
               type string;
               description
                 "Resolution map";
             }
             leaf resolution-map-mode {
               type string;
               description
                 "Resolution map modes";
             }
             leaf selected-mldp-egress-stat {
               type string;
               description
                 "Selected mldp egress statistics";
             }
             leaf selected-mldp-egress {
               type string;
               description
                 "This node should act as egress node for MLDP inband 
                 signalling";
             }
             leaf send-withdrawal-on-route-change-stat {
               type string;
               description
                 "Send withdrawal on route change statistics";
             }
             leaf send-withdrawal-on-route-change {
               type empty;
               description
                 "Withdrawn route as change is not ack'd from forwarding";
             }
             leaf set-down-bit-stat {
               type string;
               description
                 "Set down bit statistics";
             }
             leaf set-down-bit {
               type empty;
               description
                 "Set down bit";
             }
             leaf slice-stat {
               type string;
               description
                 "Slice statistics";
             }
             leaf slice {
               type string;
               description
                 "Slice name";
             }
             leaf source-class-stat {
               type string;
               description
                 "Source class statistics";
             }
             leaf source-class {
               type string;
               description
                 "The source class in forwarding table";
             }
             leaf sr-te-template-stat {
               type string;
               description
                 "SRTE template statistics";
             }
             leaf sr-te-template {
               type string;
               description
                 "SR TE template to apply";
             }
             leaf ssm-source-stat {
               type string;
               description
                 "SSM source statistics";
             }
             leaf ssm-source {
               type jt:ipaddr;
               description
                 "List of Sources for SSM mapping";
             }
             leaf strip-as-path-stat {
               type string;
               description
                 "Strip Aspath statistics";
             }
             leaf strip-as-path {
               type empty;
               description
                 "Atrip As path";
             }
             leaf trace-stat {
               type string;
               description
                 "Tunnel statistics";
             }
             leaf trace {
               type empty;
               description
                 "Log matches to a trace file";
             }
             leaf tunnel-end-point-address-stat {
               type string;
               description
                 "Tunnel end point address statistics";
             }
             leaf tunnel-end-point-address {
               type string;
               description
                 "Set tunnel end-point address of tunnel";
             }
             leaf tunnel-termination-profile-stat {
               type string;
               description
                 "Tunnel termination profile statistics";
             }
             leaf tunnel-termination-profile {
               type string;
               description
                 "Tunnel termination profile name";
             }
             leaf validation-state-stat {
               type string;
               description
                 "Validation database statistics";
             }
             leaf validation-state {
               type string;
               description
                 "Validation-state of a route";
             }
             leaf otc-local-role {
               type string;
               description
                 "Overridden OTC local role";
             }
             container external {
               description
                 "External route";
               leaf external-stat {
                 type string;
                 description
                   "External statistics";
               }
               leaf external-type {
                 type uint32;
               }
               leaf nssa-only {
                 type empty;
               }
             }
             container install-nexthop {
               description
                 "The next hop to be used for forwarding";
               container except {
                 leaf lsp {
                   type string;
                   description
                     "Label switched path name";
                 }
                 leaf lsp-regex {
                   type string;
                   description
                     "Label switched path name regular expression";
                 }
                 leaf non-labelled-nexthop {
                   type empty;
                 }
                 leaf non-lsp-nexthop {
                   type empty;
                 }
                 leaf static-lsp {
                   type string;
                 }
                 leaf static-lsp-regex {
                   type string;
                 }
                 leaf overlay-vxlan-interfaces {
                   type empty;
                 }
                 leaf macsec-interfaces {
                   type empty;
                 }
               }
               container fallback {
                 leaf lsp {
                   type string;
                   description
                     "Label switched path name";
                 }
                 leaf lsp-regex {
                   type string;
                   description
                     "Label switched path name regular expression";
                 }
                 leaf non-labelled-nexthop {
                   type empty;
                 }
                 leaf non-lsp-nexthop {
                   type empty;
                 }
                 leaf static-lsp {
                   type string;
                 }
                 leaf static-lsp-regex {
                   type string;
                 }
                 leaf overlay-vxlan-interfaces {
                   type empty;
                 }
                 leaf macsec-interfaces {
                   type empty;
                 }
               }
               leaf install-nexthop-stat {
                 type string;
                 description
                   "Install nexthop statistics";
               }
               leaf lsp {
                 type string;
                 description
                   "Label switched path name";
               }
               leaf lsp-regex {
                 type string;
                 description
                   "Label switched path name regular expression";
               }
               leaf non-labelled-nexthop {
                 type empty;
               }
               leaf non-lsp-nexthop {
                 type empty;
               }
               leaf static-lsp {
                 type string;
               }
               leaf static-lsp-regex {
                 type string;
               }
               leaf strict {
                 type empty;
               }
               leaf strict-named-lsp {
                 type empty;
               }
               leaf overlay-vxlan-interfaces {
                 type empty;
               }
               leaf macsec-interfaces {
                 type empty;
               }
               leaf nh-select {
                 type string;
               }
               leaf hash {
                 type uint32;
               }
             }
             container map-to-interface {
               description
                 "Set output logical interface";
               list interface {
                 description
                   "Interface name or address";
               }
               leaf map-to-interface-stat {
                 type string;
                 description
                   "Map to interface statistics";
               }
               leaf self {
                 type empty;
               }
             }
             container then-metric {
               leaf metric-stat {
                 type string;
                 description
                   "Metric statistics";
               }
               leaf metric1 {
                 type uint32;
                 description
                   "Metric value";
               }
               leaf add-metric {
                 type uint32;
               }
               leaf subtract-metric {
                 type uint32;
               }
               leaf aigp-metric {
                 type empty;
               }
               container effective-aigp {
                 leaf metric-offset {
                   type uint32;
                 }
               }
               container igp {
                 leaf metric-offset {
                   type uint32;
                 }
               }
               container minimum-effective-aigp {
                 leaf metric-offset {
                   type uint32;
                 }
               }
               container minimum-igp {
                 leaf metric-offset {
                   type uint32;
                 }
               }
             }
             container prefix-segment {
               description
                 "The prefix segment attributes";
               leaf prefix-segment-stat {
                 type string;
                 description
                   "Prefix segment statistics";
               }
               leaf psid-extended-data {
                 type int32;
                 description
                   "Prefix segment extendend information";
               }
               leaf prefix-segment-index-value {
                 type uint32;
               }
               leaf node-segment {
                 type empty;
               }
               leaf redistribute {
                 type empty;
               }
               container algorithm {
                 leaf prefix-segment-index-value {
                   type uint32;
                 }
                 leaf algorithm-name {
                   type uint32;
                 }
                 leaf node-segment {
                   type empty;
                 }
               }
             }
             list tunnel-attribute {
               key "tunnel-attribute-name";
               description
                 "Tunnel attribute information";
               leaf tunnel-attribute-stat {
                 type string;
                 description
                   "Tunnel attribute statistics";
               }
               leaf set {
                 type empty;
                 description
                   "Set BGP tunnel attribute in the route";
               }
               leaf remove {
                 type empty;
                 description
                   "Remove BGP tunnel attribute from the route";
               }
               leaf tunnel-attribute-name {
                 type string;
                 description
                   "Name of a tunnel attribute , or 'all'";
               }
             }
             container add-path {
               description
                 "BGP add-path attributes";
               leaf add-path-stat {
                 type string;
               }
               leaf sendcount {
                 type uint32;
                 description
                   "Number of add-paths sent";
               }
             }
             container aigp-adjust {
               description
                 "Adjust a BGP AIGP attribute";
               leaf aigp-adjust-stat {
                 type string;
                 description
                   "AIGP adjust statistics";
               }
               leaf distance-to-protocol-nexthop {
                 type empty;
               }
               leaf add {
                 type empty;
               }
               leaf divide {
                 type empty;
               }
               leaf multiply {
                 type empty;
               }
               leaf subtract {
                 type empty;
               }
               leaf user-value {
                 type uint64;
               }
             }
             container aigp-originate {
               description
                 "Originate a BGP AIGP attribute";
               leaf aigp-originate-stat {
                 type string;
                 description
                   "AIGP originate statistics";
               }
               leaf distance {
                 type uint32;
                 description
                   "AIGP distance";
               }
             }
             container as-path-expand {
               description
                 "Prepend AS numbers prior to adding local-as (BGP only)";
               leaf as-path-expand-stat {
                 type string;
                 description
                   "AS path expand statistics";
               }
               leaf as-path-sequence {
                 type string;
               }
               leaf last-as {
                 type empty;
               }
               leaf last-as-count {
                 type uint32;
               }
               leaf aspath-expand-local-as {
                 type empty;
               }
               leaf aspath-expand-local-as-count {
                 type uint32;
               }
               leaf as-value {
                 type uint32;
               }
               leaf asn-count {
                 type uint32;
               }
             }
             container assisted-replication {
               leaf assisted-replication-stat {
                 type string;
                 description
                   "Assisted replication";
               }
               leaf replicator-ip {
                 type string;
               }
               leaf strict-mode {
                 type string;
               }
               leaf fallback-replicator-ip {
                 type string;
               }
             }
             container bgp-output-queue-priority {
               description
                 "The BGP Update output queue priority";
               leaf bgp-output-queue-priority-stat {
                 type string;
                 description
                   "BGP output queue priority statistics";
               }
               leaf expedited {
                 type empty;
               }
               leaf queue-priority {
                 type uint32;
               }
             }
             container then-color {
               leaf color-stat {
                 type string;
                 description
                   "Color statistics";
               }
               leaf add-metric {
                 type uint32;
               }
               leaf subtract-metric {
                 type uint32;
               }
               leaf metric1 {
                 type uint32;
                 description
                   "Metric value";
               }
             }
             container then-color2 {
               leaf color2-stat {
                 type string;
                 description
                   "Color2 statistics";
               }
               leaf add-metric {
                 type uint32;
               }
               leaf subtract-metric {
                 type uint32;
               }
               leaf metric1 {
                 type uint32;
                 description
                   "Metric value";
               }
             }
             container then-community {
               leaf community-stat {
                 type string;
                 description
                   "Community statistics";
               }
               leaf add {
                 type empty;
               }
               leaf set {
                 type empty;
                 description
                   "Set BGP tunnel attribute in the route";
               }
               leaf community-delete {
                 type empty;
               }
               leaf community-name {
                 type string;
               }
             }
             container credibility {
               leaf credibility-stat {
                 type string;
                 description
                   "Credibility statistics";
               }
               leaf add-metric {
                 type uint32;
               }
               leaf subtract-metric {
                 type uint32;
               }
               leaf metric1 {
                 type uint32;
                 description
                   "Metric value";
               }
             }
             container localpreference {
               leaf policy-local-preference-stat {
                 type string;
                 description
                   "Local preference statistics";
               }
               leaf add-metric {
                 type uint32;
               }
               leaf subtract-metric {
                 type uint32;
               }
               leaf metric1 {
                 type uint32;
                 description
                   "Metric value";
               }
             }
             container then-metric2 {
               leaf metric2-stat {
                 type string;
                 description
                   "Metric2 statistics";
               }
               leaf metric1 {
                 type uint32;
                 description
                   "Metric value";
               }
               leaf add-metric {
                 type uint32;
               }
               leaf subtract-metric {
                 type uint32;
               }
             }
             container then-metric3 {
               leaf metric3-stat {
                 type string;
                 description
                   "Metric3 statistics";
               }
               leaf metric1 {
                 type uint32;
                 description
                   "Metric value";
               }
               leaf add-metric {
                 type uint32;
               }
               leaf subtract-metric {
                 type uint32;
               }
             }
             container then-metric4 {
               leaf metric4-stat {
                 type string;
                 description
                   "Metric4 statistics";
               }
               leaf metric1 {
                 type uint32;
                 description
                   "Metric value";
               }
               leaf add-metric {
                 type uint32;
               }
               leaf subtract-metric {
                 type uint32;
               }
             }
             container then-nexthop {
               leaf next-hop-stat {
                 type string;
                 description
                   "Nexthop statistics";
               }
               leaf reject {
                 type empty;
                 description
                   "Reject a route";
               }
               leaf discard {
                 type empty;
               }
               leaf self {
                 type empty;
               }
               leaf no-resolution {
                 type empty;
               }
               leaf nexthop-peer-address {
                 type empty;
               }
               leaf next-table {
                 type string;
               }
             }
             container then-preference {
               leaf preference-stat {
                 type string;
                 description
                   "Preference statistics";
               }
               leaf metric1 {
                 type uint32;
                 description
                   "Metric value";
               }
               leaf add-metric {
                 type uint32;
               }
               leaf subtract-metric {
                 type uint32;
               }
             }
             container then-preference2 {
               leaf preference2-stat {
                 type string;
                 description
                   "Preference2 statistics";
               }
               leaf metric1 {
                 type uint32;
                 description
                   "Metric value";
               }
               leaf add-metric {
                 type uint32;
               }
               leaf subtract-metric {
                 type uint32;
               }
             }
             container prefix-attribute-flags {
               leaf prefix-attribute-flags-stat {
                 type string;
                 description
                   "Prefix attribute flag statistics";
               }
               leaf node-segment-flag {
                 type empty;
                 description
                   "Node segment flag";
               }
               leaf external-prefix-flag {
                 type empty;
                 description
                   "External prefix flag";
               }
               leaf entropy-label-capability-flag {
                 type empty;
                 description
                   "Entropy label capability flag";
               }
               leaf anycast-flag {
                 type empty;
                 description
                   "Anycast flag";
               }
             }
             container request-ack {
               description
                 "Request acknowledgements";
               leaf request-ack-stat {
                 type string;
                 description
                   "Request acknowledgements statistics";
               }
               leaf route-ack {
                 type empty;
                 description
                   "Route acknowledgements";
               }
               leaf nexthop-ack {
                 type empty;
                 description
                   "Nexthop acknowledgements";
               }
             }
             container rib-export-strip {
               description
                 "RIB export strip attributes";
               leaf rib-export-strip-stat {
                 type string;
                 description
                   "RIB export stripped attributes statistics";
               }
               leaf cluster-list {
                 type empty;
                 description
                   "Strip cluster-list attribute";
               }
             }
             container srv6 {
               leaf srv6-stat {
                 type string;
                 description
                   "SRv6 SID";
               }
               leaf sid {
                 type string;
               }
               leaf locator {
                 type string;
                 description
                   "SRv6 locator";
               }
               leaf micro-dt4-sid {
                 type empty;
               }
               leaf micro-dt6-sid {
                 type empty;
               }
               leaf micro-dt46-sid {
                 type empty;
               }
               leaf end-dtm-sid {
                 type empty;
               }
             }
             container then-tag {
               leaf tag-stat {
                 type string;
                 description
                   "Policy tag statistics";
               }
               leaf metric1 {
                 type uint32;
                 description
                   "Metric value";
               }
               leaf add-metric {
                 type uint32;
               }
               leaf subtract-metric {
                 type uint32;
               }
             }
             container then-tag2 {
               leaf tag2-stat {
                 type string;
                 description
                   "Policy tag2 statistics";
               }
               leaf metric1 {
                 type uint32;
                 description
                   "Metric value";
               }
               leaf add-metric {
                 type uint32;
               }
               leaf subtract-metric {
                 type uint32;
               }
             }
           }
         }
         leaf policy-flags {
           type string;
           description
             "Policy flags";
         }
       }
     }
   }
   augment "/jgs:genstate" {
     description
       "Adds policy-information container to top-level genstate container";
     uses policy-information-top;
   }
 }
