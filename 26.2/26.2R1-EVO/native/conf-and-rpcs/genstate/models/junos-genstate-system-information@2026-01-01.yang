module junos-genstate-system-information {
   yang-version 1;
   namespace "http://yang.juniper.net/junos/genstate/system-information";
   prefix jgsi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for system-information.

      Copyright (c) 2026 Juniper Networks, Inc.
      All rights reserved.";

   revision 2026-01-01 {
     description "Junos: 26.2R1.7-EVO";
   }

   grouping system-information-top {
     description
       "Top-level grouping";
     container system-information {
       description
         "Top-level container";
       leaf host-name {
         type string;
         description
           "Hostname of router";
       }
       leaf hardware-model {
         type string;
         description
           "Platform";
       }
       leaf os-name {
         type string;
         description
           "Operating System Name";
       }
       leaf os-version {
         type string;
         description
           "Operating System Version";
       }
       leaf serial-number {
         type string;
         description
           "Chassis Serial Number";
       }
       list package-information {
         key "name";
         leaf name {
           type string;
           description
             "Syslog message tag name";
         }
         leaf package-name {
           type string;
           description
             "Name of software package";
         }
       }
     }
   }
   augment "/jgs:genstate" {
     description
       "Adds system-information container to top-level genstate container";
     uses system-information-top;
   }
 }
