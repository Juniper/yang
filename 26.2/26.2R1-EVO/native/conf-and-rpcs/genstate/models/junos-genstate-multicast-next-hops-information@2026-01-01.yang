module junos-genstate-multicast-next-hops-information {
   yang-version 1;
   namespace "http://yang.juniper.net/junos/genstate/multicast-next-hops-information";
   prefix jgmnhi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for multicast-next-hops-information.

      Copyright (c) 2026 Juniper Networks, Inc.
      All rights reserved.";

   revision 2026-01-01 {
     description "Junos: 26.2R1.7-EVO";
   }

   grouping multicast-next-hops-information-top {
     description
       "Top-level grouping";
     container multicast-next-hops-information {
       description
         "Top-level container";
       list next-hops-family {
         key "address-family";
         leaf address-family {
           type string;
         }
         list iflist-next-hop {
           key "next-hop-id";
           leaf next-hop-id {
             type uint32;
           }
           leaf next-hop-ref-count {
             type uint32;
           }
           leaf next-hop-kernel-ref-count {
             type uint32;
           }
           list next-hop-downstream-interface {
             key "interface-name";
             leaf interface-name {
               type string;
               description
                 "Name of interface";
             }
           }
           leaf next-hop-downstream-interface-count {
             type uint32;
           }
         }
       }
     }
   }
   augment "/jgs:genstate" {
     description
       "Adds multicast-next-hops-information container to top-level genstate
       container";
     uses multicast-next-hops-information-top;
   }
 }
