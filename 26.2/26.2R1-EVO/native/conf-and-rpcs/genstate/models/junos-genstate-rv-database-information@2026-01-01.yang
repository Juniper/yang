module junos-genstate-rv-database-information {
   yang-version 1;
   namespace "http://yang.juniper.net/junos/genstate/rv-database-information";
   prefix jgrdi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for rv-database-information.

      Copyright (c) 2026 Juniper Networks, Inc.
      All rights reserved.";

   revision 2026-01-01 {
     description "Junos: 26.2R1.7-EVO";
   }

   grouping rv-database-information-top {
     description
       "Top-level grouping";
     container rv-database-information {
       description
         "RV database information";
       container rv-database {
         leaf database-name {
           type string;
         }
         leaf ip-prefix-count {
           type uint32;
         }
         leaf ip6-prefix-count {
           type uint32;
         }
         list rv-database-entry {
           key "ip-prefix maximum-length origin-as";
           leaf ip-prefix {
             type jt:ipprefix;
           }
           leaf maximum-length {
             type uint32;
           }
           leaf origin-as {
             type uint32;
           }
           leaf ip-address {
             type jt:ipaddr;
           }
           leaf validation-state {
             type string;
             description
               "Validation-state of a route";
           }
           leaf validation-mismatch {
             type string;
           }
         }
       }
     }
   }
   augment "/jgs:genstate" {
     description
       "Adds rv-database-information container to top-level genstate 
       container";
     uses rv-database-information-top;
   }
 }
