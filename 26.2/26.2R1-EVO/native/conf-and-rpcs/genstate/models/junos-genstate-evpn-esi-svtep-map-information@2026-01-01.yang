module junos-genstate-evpn-esi-svtep-map-information {
   yang-version 1;
   namespace "http://yang.juniper.net/junos/genstate/evpn-esi-svtep-map-information";
   prefix jgeesmi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for evpn-esi-svtep-map-information.

      Copyright (c) 2026 Juniper Networks, Inc.
      All rights reserved.";

   revision 2026-01-01 {
     description "Junos: 26.2R1.7-EVO";
   }

   grouping evpn-esi-svtep-map-information-top {
     description
       "Top-level grouping";
     container evpn-esi-svtep-map-information {
       description
         "EVPN ESI-SVTEP map";
       list evpn-esi-svtep-map-entry {
         key "evpn-esi-svtep-map-entry-esi";
         description
           "One <ESI, SVTEP> map entry";
         leaf evpn-esi-svtep-map-entry-esi {
           type string;
         }
         leaf evpn-esi-svtep-map-entry-svtep-address {
           type jt:ipaddr;
         }
       }
     }
   }
   augment "/jgs:genstate" {
     description
       "Adds evpn-esi-svtep-map-information container to top-level genstate 
       container";
     uses evpn-esi-svtep-map-information-top;
   }
 }
