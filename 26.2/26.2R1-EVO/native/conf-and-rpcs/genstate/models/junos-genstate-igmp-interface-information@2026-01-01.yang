module junos-genstate-igmp-interface-information {
   yang-version 1;
   namespace "http://yang.juniper.net/junos/genstate/igmp-interface-information";
   prefix jgiii;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for igmp-interface-information.

      Copyright (c) 2026 Juniper Networks, Inc.
      All rights reserved.";

   revision 2026-01-01 {
     description "Junos: 26.2R1.7-EVO";
   }

   grouping igmp-interface-information-top {
     description
       "Top-level grouping";
     container igmp-interface-information {
       description
         "Top-level container";
       list mgm-interface {
         key "interface-name";
         leaf interface-name {
           type string;
           description
             "Name of interface";
         }
         leaf querier-address {
           type jt:ipaddr;
         }
         leaf mgm-interface-state {
           type string;
         }
         leaf querier-timeout {
           type int32;
         }
         leaf mgm-interface-version {
           type int32;
         }
         leaf mgm-group-count {
           type int32;
         }
         leaf mgm-group-limit {
           type uint32;
           description
             "Maximum number of (source,group) per interface";
         }
         leaf mgm-group-threshold {
           type uint32;
           description
             "Percentage of maximum at which to start generating warnings";
         }
         leaf mgm-group-log-interval {
           type uint32;
           description
             "Percentage of maximum at which to start generating warnings";
         }
         leaf mgm-ssm-map {
           type string;
           description
             "Name of source-specific multicast map";
         }
         leaf mgm-ssm-map-policy {
           type string;
           description
             "Name of source-specific multicast map policy";
         }
         leaf mgm-immediate-leave {
           type string;
           description
             "Groups are removed immediately without sending last membership
             queries";
         }
         leaf mgm-promiscuous-mode {
           type string;
           description
             "IGMP messages coming from different subnet are accepted";
         }
         leaf mgm-passive {
           type string;
           description
             "Do not send or receive control messages";
         }
         leaf mgm-passive-allow-receive {
           type empty;
           description
             "Allow receiving control messages";
         }
         leaf mgm-passive-send-general-query {
           type empty;
           description
             "Send general query messages";
         }
         leaf mgm-passive-send-group-query {
           type empty;
           description
             "Send group query messages";
         }
         leaf mgm-group-policy {
           type string;
           description
             "Group filter applied to incoming Report messages";
         }
         leaf mgm-oif-map {
           type string;
           description
             "Output interface mapping policy";
         }
         leaf mgm-distributed {
           type string;
           description
             "Distributed IGMP";
         }
       }
       container mgm-configured-parameters {
         leaf query-interval {
           type string;
         }
         leaf query-response-interval {
           type string;
         }
         leaf last-member-query-interval {
           type string;
         }
         leaf robustness-count {
           type int32;
         }
       }
       container mgm-derived-parameters {
         leaf membership-timeout {
           type string;
         }
         leaf query-other-timeout {
           type string;
         }
       }
       container mgm-amt-configured-parameters {
         leaf query-interval {
           type string;
         }
         leaf query-response-interval {
           type string;
         }
         leaf last-member-query-interval {
           type string;
         }
         leaf robustness-count {
           type int32;
         }
       }
       container mgm-amt-derived-parameters {
         leaf membership-timeout {
           type string;
         }
         leaf query-other-timeout {
           type string;
         }
       }
     }
   }
   augment "/jgs:genstate" {
     description
       "Adds igmp-interface-information container to top-level genstate 
       container";
     uses igmp-interface-information-top;
   }
 }
