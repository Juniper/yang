module junos-genstate-ldp-interface-information {
   yang-version 1;
   namespace "http://yang.juniper.net/junos/genstate/ldp-interface-information";
   prefix jglii;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for ldp-interface-information.

      Copyright (c) 2026 Juniper Networks, Inc.
      All rights reserved.";

   revision 2026-01-01 {
     description "Junos: 26.2R1.7-EVO";
   }

   grouping ldp-interface-information-top {
     description
       "Top-level grouping";
     container ldp-interface-information {
       description
         "Top-level container";
       list ldp-interface {
         key "interface-name";
         leaf interface-name {
           type string;
           description
             "Name of interface";
         }
         leaf ldp-interface-local-address {
           type jt:ipaddr;
         }
         leaf ldp-label-space-id {
           type string;
         }
         leaf ldp-neighbor-count {
           type int32;
         }
         leaf ldp-next-hello {
           type int32;
         }
         leaf ldp-hello-interval {
           type int32;
         }
         leaf ldp-holdtime {
           type int32;
         }
         leaf ldp-transport-address {
           type jt:ipaddr;
         }
         leaf ldp-local-hello-interval {
           type int32;
           description
             "The locally configured hello interval";
         }
         leaf ldp-interface-index {
           type uint32;
         }
         leaf ldp-block-time {
           type int32;
         }
         leaf ldp-hello-sent {
           type uint32;
           description
             "Number of hellos sent on this interface";
         }
         leaf ldp-hello-received {
           type uint32;
           description
             "Number of hellos received on this interface";
         }
         container ldp-if-link-protection {
           description
             "If link protection";
           leaf ldp-link-protection {
             type string;
             description
               "Link Protection";
           }
         }
       }
     }
   }
   augment "/jgs:genstate" {
     description
       "Adds ldp-interface-information container to top-level genstate 
       container";
     uses ldp-interface-information-top;
   }
 }
