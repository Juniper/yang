module junos-genstate-multicast-pim-to-mld-proxy-information {
   yang-version 1;
   namespace "http://yang.juniper.net/junos/genstate/multicast-pim-to-mld-proxy-information";
   prefix jgmptmpi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for multicast-pim-to-mld-proxy-information.

      Copyright (c) 2026 Juniper Networks, Inc.
      All rights reserved.";

   revision 2026-01-01 {
     description "Junos: 26.2R1.7-EVO";
   }

   grouping multicast-pim-to-mld-proxy-information-top {
     description
       "Top-level grouping";
     container multicast-pim-to-mld-proxy-information {
       description
         "Top-level container";
       container multicast-pim-to-mld-proxy {
         description
           "Pim-to-mld-proxy state";
         leaf instance-name {
           type string;
         }
         leaf proxy-state {
           type string;
         }
       }
       list proxy-upstream-interface {
         key "interface-name";
         leaf interface-name {
           type string;
           description
             "Name of interface";
         }
       }
     }
   }
   augment "/jgs:genstate" {
     description
       "Adds multicast-pim-to-mld-proxy-information container to top-level 
       genstate container";
     uses multicast-pim-to-mld-proxy-information-top;
   }
 }
