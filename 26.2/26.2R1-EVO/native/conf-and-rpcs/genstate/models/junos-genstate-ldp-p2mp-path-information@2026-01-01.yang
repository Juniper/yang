module junos-genstate-ldp-p2mp-path-information {
   yang-version 1;
   namespace "http://yang.juniper.net/junos/genstate/ldp-p2mp-path-information";
   prefix jglppi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for ldp-p2mp-path-information.

      Copyright (c) 2026 Juniper Networks, Inc.
      All rights reserved.";

   revision 2026-01-01 {
     description "Junos: 26.2R1.7-EVO";
   }

   grouping ldp-p2mp-path-information-top {
     description
       "Top-level grouping";
     container ldp-p2mp-path-information {
       description
         "Top-level container";
       list ldp-p2mp-path {
         key "ldp-p2mp-path-type";
         leaf ldp-p2mp-path-type {
           type string;
           description
             "Type of p2mp path";
         }
         leaf ldp-p2mp-outlib-session {
           type string;
           description
             "Output session";
         }
         leaf ldp-p2mp-outlib-label {
           type int32;
           description
             "Label advertised on output session";
         }
         leaf ldp-p2mp-label-primary {
           type string;
           description
             "Indicates if p2mp label is primary for this fec";
         }
         leaf ldp-p2mp-egress-label {
           type int32;
           description
             "Application specified label";
         }
         leaf ldp-p2mp-path-address {
           type int32;
           description
             "Address of the p2mp path object";
         }
         leaf ldp-reference-count {
           type int32;
         }
         leaf ldp-p2mp-path-transit-route {
           type empty;
           description
             "Indicates if transit route is installed";
         }
         list ldp-p2mp-inlib-label {
           key "ldp-label-session";
           leaf ldp-label-session {
             type string;
             description
               "Input session";
           }
           leaf ldp-label {
             type int32;
           }
         }
         list ldp-egress-nh {
           key "interface-name";
           leaf ldp-egress-nh-type {
             type string;
             description
               "Type of egress nexthop";
           }
           leaf interface-name {
             type string;
             description
               "Name of interface";
           }
         }
         list ldp-rpf-nh {
           key "interface-name";
           leaf ldp-rpf-nh-type {
             type string;
             description
               "Type of RPF nexthop";
           }
           leaf interface-name {
             type string;
             description
               "Name of interface";
           }
           leaf ldp-rpf-nexthop-address {
             type jt:ipaddr;
           }
           leaf ldp-label {
             type int32;
           }
           leaf ldp-rpf-weight {
             type int32;
           }
         }
         list ldp-p2mp-path-fec {
           key "ldp-prefix";
           leaf ldp-prefix {
             type string;
           }
           leaf next-root {
             type string;
           }
           leaf ldp-prefix-active {
             type string;
             description
               "Indicates if p2mp path is active for this fec";
           }
           leaf ldp-prefix-mbb-timer {
             type int32;
             description
               "Make before break timer";
           }
           leaf ldp-prefix-mbb-timer-type {
             type string;
             description
               "Make before break timer type";
           }
           leaf ldp-p2mp-fec-mofrr {
             type string;
             description
               "Indicates if MoFRR enabled for this fec";
           }
         }
       }
     }
   }
   augment "/jgs:genstate" {
     description
       "Adds ldp-p2mp-path-information container to top-level genstate 
       container";
     uses ldp-p2mp-path-information-top;
   }
 }
