module junos-genstate-l2circuit-connection-information {
   yang-version 1;
   namespace "http://yang.juniper.net/junos/genstate/l2circuit-connection-information";
   prefix jglci;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for l2circuit-connection-information.

      Copyright (c) 2026 Juniper Networks, Inc.
      All rights reserved.";

   revision 2026-01-01 {
     description "Junos: 26.2R1.7-EVO";
   }

   grouping l2circuit-connection-information-top {
     description
       "Top-level grouping";
     container l2circuit-connection-information {
       description
         "Top-level container";
       list l2circuit-neighbor {
         key "neighbor-address";
         leaf neighbor-address {
           type jt:ipaddr;
           description
             "IP address of this neighbor";
         }
         leaf lsw-interface-name {
           type string;
         }
         list connection {
           key "connection-id";
           leaf connection-id {
             type string;
           }
           leaf connection-type {
             type string;
           }
           leaf connection-status {
             type string;
           }
           leaf last-change {
             type string;
           }
           leaf up-transitions {
             type int32;
           }
           leaf remote-pe {
             type jt:ipaddr;
           }
           leaf control-word {
             type string;
           }
           leaf control-word-type {
             type string;
           }
           leaf inbound-label {
             type string;
           }
           leaf outbound-label {
             type string;
           }
           leaf pw-status-tlv {
             type string;
           }
           leaf local-pw-status-code {
             type string;
           }
           leaf remote-pw-status-code {
             type string;
           }
           leaf connection-protection {
             type string;
           }
           leaf vc-flow-label-transmit {
             type string;
           }
           leaf vc-flow-label-receive {
             type string;
           }
           list local-interface {
             key "interface-name";
             leaf interface-name {
               type string;
               description
                 "Name of interface";
             }
             leaf interface-status {
               type string;
             }
             leaf interface-encapsulation {
               type string;
             }
             leaf working-status {
               type string;
             }
             leaf interface-description {
               type string;
             }
           }
           container connection-bandwidth {
             description
               "Bandwidth of a layer 2 connection";
             leaf bandwidth {
               type string;
             }
           }
           container history {
             list history-element {
               key "log-time-stamp log-event";
               leaf log-time-stamp {
                 type string;
               }
               leaf log-event {
                 type string;
               }
               leaf changed-entity {
                 type string;
               }
             }
           }
           container egress-protection-protector {
             leaf protector-state {
               type string;
             }
             leaf protector-interface {
               type string;
             }
             leaf interface-status {
               type string;
             }
             leaf protector-pe {
               type jt:ipaddr;
             }
             leaf protector-pe-status {
               type string;
             }
             leaf protection-context {
               type jt:ipaddr;
             }
             leaf context-status {
               type string;
             }
           }
           container egress-protection-protected-l2ckt {
             leaf protected-l2ckt-state {
               type string;
             }
             leaf protected-l2ckt-ingress {
               type jt:ipaddr;
             }
             leaf protected-l2ckt-egress {
               type jt:ipaddr;
             }
             leaf protected-l2ckt-vcid {
               type string;
             }
           }
         }
       }
     }
   }
   augment "/jgs:genstate" {
     description
       "Adds l2circuit-connection-information container to top-level 
       genstate container";
     uses l2circuit-connection-information-top;
   }
 }
