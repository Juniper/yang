module junos-genstate-bmp-peer-statistics-information {
   yang-version 1;
   namespace "http://yang.juniper.net/junos/genstate/bmp-peer-statistics-information";
   prefix jgbpsi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for bmp-peer-statistics-information.

      Copyright (c) 2026 Juniper Networks, Inc.
      All rights reserved.";

   revision 2026-01-01 {
     description "Junos: 26.2R1.7-EVO";
   }

   grouping bmp-peer-statistics-information-top {
     description
       "Top-level grouping";
     container bmp-peer-statistics-information {
       description
         "BMP peer up/down statistics information";
       leaf bmp-peer-statistics-header {
         type string;
       }
       list bmp-peer {
         key "bmp-station-name";
         leaf bmp-station-name {
           type string;
         }
         container bmp-peer-up-statistics {
           leaf peer-statistics-count {
             type int32;
             description
               "Total peer up/down count";
           }
           leaf peer-last-sent-time-stamp {
             type string;
             description
               "Time when last peer sent";
           }
         }
         container bmp-peer-down-statistics {
           leaf peer-statistics-count {
             type int32;
             description
               "Total peer up/down count";
           }
           leaf peer-last-sent-time-stamp {
             type string;
             description
               "Time when last peer sent";
           }
         }
       }
     }
   }
   augment "/jgs:genstate" {
     description
       "Adds bmp-peer-statistics-information container to top-level genstate
       container";
     uses bmp-peer-statistics-information-top;
   }
 }
