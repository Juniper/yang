/*
 * Copyright (c) 2026 Juniper Networks, Inc.
 * All rights reserved.
 */
 module junos-rpc-system {
   namespace "http://yang.juniper.net/junos/rpc/system";

   prefix system;

   import junos-common-types {
     prefix jt;
     revision-date 2026-01-01;
   }

   organization "Juniper Networks, Inc.";

   contact "yang-support@juniper.net";

   description "Junos RPC YANG module for system command(s)";

   revision 2026-01-01 {
     description "Junos: 26.2R1.7-EVO";
   }

   rpc get-system-dual-phase-bootup-status {
     description "To check the current dual-phase-bootup status";
     output {
       choice output-tags {
         case actual-tag {
           container system-dual-phase-bootup-status {
             uses system-dual-phase-bootup-status-block;
           }
         }
         case multichassis-tag {
           container multi-routing-engine-results {
             list multi-routing-engine-item {
               leaf re-name {
                 type string;
               }
               choice output-tags {
                 case actual-tag {
                   container system-dual-phase-bootup-status {
                     uses system-dual-phase-bootup-status-block;
                   }
                 }
               }
             }
           }
         }
       }
     }
   }
   rpc get-genstate-path-cli-command-mapping {
     description "Show mapped CLI command for a given genstate path";
     input {
       leaf genstate-path {
         description "Input genstate path";
         type string;
         mandatory true;
       }
     }
     output {
       choice output-tags {
         case actual-tag {
           container genstate-path-cli-command-mapping-information {
             uses genstate-path-cli-command-mapping-information-block;
           }
         }
         case multichassis-tag {
           container multi-routing-engine-results {
             list multi-routing-engine-item {
               leaf re-name {
                 type string;
               }
               choice output-tags {
                 case actual-tag {
                   container genstate-path-cli-command-mapping-information {
                     uses genstate-path-cli-command-mapping-information-block;
                   }
                 }
               }
             }
           }
         }
       }
     }
   }
   rpc get-commit-information {
     description "Show pending commit requests (if any) and commit history";
     input {
       leaf include-configuration-revision {
         description "Display configuration revision information against each commit record";
         type empty;
       }
     }
     output {
       choice output-tags {
         case actual-tag {
           container commit-information {
             uses commit-information-block;
           }
         }
         case multichassis-tag {
           container multi-routing-engine-results {
             list multi-routing-engine-item {
               leaf re-name {
                 type string;
               }
               choice output-tags {
                 case actual-tag {
                   container commit-information {
                     uses commit-information-block;
                   }
                 }
               }
             }
           }
         }
       }
     }
   }
   rpc get-commit-revision-information {
     description "Show latest commit revision number for shared database";
     input {
       leaf level {
         default "brief";
         type enumeration {
           enum "brief" {
             description "Display brief output";
           }
           enum "detail" {
             description "Display detailed output";
           }
         }
       }
       leaf config-namespace {
         description "Display config-namespace commit revision";
         type enumeration {
           enum "dynamic" {
             description "Display dynamic namespace commit revision";
           }
           enum "boot" {
             description "Display boot namespace commit revision";
           }
           enum "security" {
             description "Display security namespace commit revision";
           }
         }
       }
     }
     output {
       choice output-tags {
         case actual-tag {
           container commit-revision-information {
             uses commit-revision-information-block;
           }
         }
         case multichassis-tag {
           container multi-routing-engine-results {
             list multi-routing-engine-item {
               leaf re-name {
                 type string;
               }
               choice output-tags {
                 case actual-tag {
                   container commit-revision-information {
                     uses commit-revision-information-block;
                   }
                 }
               }
             }
           }
         }
       }
     }
   }
   rpc get-pending-commit-sync-jobs {
     description "Show pending commit synchronize jobs";
     output {
       choice output-tags {
         case actual-tag {
           container commit-synchronize-server {
             uses commit-synchronize-server-block;
           }
         }
         case multichassis-tag {
           container multi-routing-engine-results {
             list multi-routing-engine-item {
               leaf re-name {
                 type string;
               }
               choice output-tags {
                 case actual-tag {
                   container commit-synchronize-server {
                     uses commit-synchronize-server-block;
                   }
                 }
               }
             }
           }
         }
       }
     }
   }
   rpc get-commit-server-information {
     description "Show commit server detail";
     input {
       leaf status {
         description "Display commit server status";
         type empty;
       }
     }
     output {
       choice output-tags {
         case actual-tag {
           container commit-server-information {
             uses commit-server-information-block;
           }
         }
         case multichassis-tag {
           container multi-routing-engine-results {
             list multi-routing-engine-item {
               leaf re-name {
                 type string;
               }
               choice output-tags {
                 case actual-tag {
                   container commit-server-information {
                     uses commit-server-information-block;
                   }
                 }
               }
             }
           }
         }
       }
     }
   }
   rpc get-commit-server-queue-information {
     description "Show transaction ids in the commit queue";
     input {
       choice job-status-or-id {
         case id {
           leaf id {
             description "Show commit queue id";
             type union {
               type uint32;
               type string {
                 pattern "<.*>|$.*";
               }
             }
           }
         }
         case job-status {
           leaf job-status {
             description "Restrict display by job status";
             default "all";
             type enumeration {
               enum "all" {
                 description "Display all jobs";
               }
               enum "error" {
                 description "Display jobs that had errors";
               }
               enum "success" {
                 description "Display jobs that succeeded";
               }
               enum "pending" {
                 description "Display jobs that are pending";
               }
             }
           }
         }
       }
       leaf patch {
         description "Display commit queue patch";
         type empty;
       }
     }
     output {
       choice output-tags {
         case actual-tag {
           container commit-server-queue-information {
             uses commit-server-queue-information-block;
           }
         }
         case multichassis-tag {
           container multi-routing-engine-results {
             list multi-routing-engine-item {
               leaf re-name {
                 type string;
               }
               choice output-tags {
                 case actual-tag {
                   container commit-server-queue-information {
                     uses commit-server-queue-information-block;
                   }
                 }
               }
             }
           }
         }
       }
     }
   }
   rpc get-rescue-information {
     description "Show rescue configuration";
     input {
       leaf format {
         description "Output format of configuration (XML or text or JSON)";
         type enumeration {
           enum "text" {
             description "Output text configuration";
           }
           enum "xml" {
             description "Output XML configuration";
           }
           enum "json" {
             description "Output JSON configuration";
           }
         }
       }
     }
     output {
       choice output-tags {
         case output-tag {
           leaf output {
             type string;
           }
         }
         case actual-tag {
           anyxml rescue-information;
         }
         case multichassis-tag {
           anyxml multi-routing-engine-results;
         }
       }
     }
   }
   rpc get-configuration-by-revision {
     description "Show configuration for the specified configuration revision";
     input {
       leaf revision-string {
         description "Configuration revision string";
         type string;
         mandatory true;
       }
       choice configuration-revision-choice {
         case rollback-number {
           leaf rollback-number {
             description "Show corresponding rollback number for the given configuration revision";
             type empty;
           }
         }
         case compare {
           leaf compare {
             description "Configuration revision to compare";
             type string;
           }
         }
       }
       leaf format {
         description "Output format of configuration (XML or text or JSON)";
         type enumeration {
           enum "text" {
             description "Output text configuration";
           }
           enum "xml" {
             description "Output XML configuration";
           }
           enum "json" {
             description "Output JSON configuration";
           }
         }
       }
     }
     output {
       choice output-tags {
         case actual-tag {
           container configuration-revision-information {
             uses configuration-revision-information-block;
           }
         }
         case multichassis-tag {
           container multi-routing-engine-results {
             list multi-routing-engine-item {
               leaf re-name {
                 type string;
               }
               choice output-tags {
                 case actual-tag {
                   container configuration-revision-information {
                     uses configuration-revision-information-block;
                   }
                 }
               }
             }
           }
         }
       }
     }
   }
   rpc get-database-usage {
     description "Show configuration database usage";
     input {
       leaf ephemeral-instance {
         description "Ephemeral instance name";
         type string;
       }
       leaf merge {
         description "Show all databases usage together";
         type empty;
       }
     }
     output {
       choice output-tags {
         case actual-tag {
           container database-usage {
             uses database-usage-block;
           }
         }
         case multichassis-tag {
           container multi-routing-engine-results {
             list multi-routing-engine-item {
               leaf re-name {
                 type string;
               }
               choice output-tags {
                 case actual-tag {
                   container database-usage {
                     uses database-usage-block;
                   }
                 }
               }
             }
           }
         }
       }
     }
   }
   rpc get-configuration-database-status {
     description "Show users currently editing configuration";
     output {
       choice output-tags {
         case actual-tag {
           container database-status-information {
             uses database-status-information-block;
           }
         }
         case multichassis-tag {
           container multi-routing-engine-results {
             list multi-routing-engine-item {
               leaf re-name {
                 type string;
               }
               choice output-tags {
                 case actual-tag {
                   container database-status-information {
                     uses database-status-information-block;
                   }
                 }
               }
             }
           }
         }
       }
     }
   }
   rpc get-system-archival {
     description "List files queued up for archive transfer";
     output {
       choice output-tags {
         case actual-tag {
           container directory-list {
             uses directory-list-block;
           }
         }
         case multichassis-tag {
           container multi-routing-engine-results {
             list multi-routing-engine-item {
               leaf re-name {
                 type string;
               }
               choice output-tags {
                 case actual-tag {
                   container directory-list {
                     uses directory-list-block;
                   }
                 }
               }
             }
           }
         }
       }
     }
   }
   rpc get-rollback-information {
     description "Show rolled back configuration";
     input {
       leaf rollback {
         description "Rollback number to display";
         type union {
           type string {
             pattern "<.*>|$.*";
           }
           type uint32 {
             range "0 .. 49";
           }
         }
         mandatory true;
       }
       leaf configuration-revision {
         description "Show corresponding configuration revision for this rollback number";
         type empty;
       }
       leaf compare {
         description "Rollback number to compare";
         type union {
           type string {
             pattern "<.*>|$.*";
           }
           type uint32 {
             range "0 .. 49";
           }
         }
       }
       leaf format {
         description "Output format of configuration (XML or text or JSON)";
         type enumeration {
           enum "text" {
             description "Output text configuration";
           }
           enum "xml" {
             description "Output XML configuration";
           }
           enum "json" {
             description "Output JSON configuration";
           }
         }
       }
     }
     output {
       choice output-tags {
         case output-tag {
           leaf output {
             type string;
           }
         }
         case actual-tag {
           anyxml rollback-information;
         }
         case multichassis-tag {
           anyxml multi-routing-engine-results;
         }
       }
     }
   }
   rpc get-system-login-password-expiry-information {
     description "Show password expiry information of users";
     input {
       leaf user {
         description "Username";
         type string;
       }
     }
     output {
       choice output-tags {
         case actual-tag {
           container system-login-password-expiry-information {
             uses system-login-password-expiry-information-block;
           }
         }
         case multichassis-tag {
           container multi-routing-engine-results {
             list multi-routing-engine-item {
               leaf re-name {
                 type string;
               }
               choice output-tags {
                 case actual-tag {
                   container system-login-password-expiry-information {
                     uses system-login-password-expiry-information-block;
                   }
                 }
               }
             }
           }
         }
       }
     }
   }
   rpc get-system-login-lockout-information {
     description "Show user accounts not permitted logins";
     input {
       leaf user {
         description "Name of user";
         type string {
         }
       }
     }
     output {
       choice output-tags {
         case actual-tag {
           container system-login-lockout-information {
             uses system-login-lockout-information-block;
           }
         }
         case multichassis-tag {
           container multi-routing-engine-results {
             list multi-routing-engine-item {
               leaf re-name {
                 type string;
               }
               choice output-tags {
                 case actual-tag {
                   container system-login-lockout-information {
                     uses system-login-lockout-information-block;
                   }
                 }
               }
             }
           }
         }
       }
     }
   }
   rpc get-system-alarm-information {
     description "Show system alarm status";
     input {
       uses command-forwarding;
     }
     output {
       choice output-tags {
         case actual-tag {
           container alarm-information {
             uses alarm-information-block;
           }
         }
         case multichassis-tag {
           container multi-routing-engine-results {
             list multi-routing-engine-item {
               leaf re-name {
                 type string;
               }
               choice output-tags {
                 case actual-tag {
                   container alarm-information {
                     uses alarm-information-block;
                   }
                 }
               }
             }
           }
         }
       }
     }
   }
   rpc get-system-alarm-reference-information {
     description "Show information about all alarms";
     input {
       leaf fru {
         description "FRU name like fpc, sib, psm";
         type string;
       }
       leaf slot {
         description "FRU slot";
         type union {
           type string {
             pattern "<.*>|$.*";
           }
           type uint32 {
             range "0 .. 63";
           }
         }
       }
     }
     output {
       choice output-tags {
         case actual-tag {
           container system-alarm-reference-information {
             uses system-alarm-reference-information-block;
           }
         }
         case multichassis-tag {
           container multi-routing-engine-results {
             list multi-routing-engine-item {
               leaf re-name {
                 type string;
               }
               choice output-tags {
                 case actual-tag {
                   container system-alarm-reference-information {
                     uses system-alarm-reference-information-block;
                   }
                 }
               }
             }
           }
         }
       }
     }
   }
   rpc get-system-alarm-reference-detail-information {
     description "Show information about all alarms with remedies";
     input {
       leaf fru {
         description "FRU name like fpc, sib, psm";
         type string;
       }
       leaf slot {
         description "FRU slot";
         type union {
           type string {
             pattern "<.*>|$.*";
           }
           type uint32 {
             range "0 .. 63";
           }
         }
       }
     }
     output {
       choice output-tags {
         case actual-tag {
           container system-alarm-reference-information {
             uses system-alarm-reference-information-block;
           }
         }
         case multichassis-tag {
           container multi-routing-engine-results {
             list multi-routing-engine-item {
               leaf re-name {
                 type string;
               }
               choice output-tags {
                 case actual-tag {
                   container system-alarm-reference-information {
                     uses system-alarm-reference-information-block;
                   }
                 }
               }
             }
           }
         }
       }
     }
   }
   rpc unified-services-chassis-mode-status {
     description "Current status of Unified-Services feature";
     output {
       choice output-tags {
         case actual-tag {
           container unified-services-status-information {
             uses unified-services-status-information-block;
           }
         }
         case multichassis-tag {
           container multi-routing-engine-results {
             list multi-routing-engine-item {
               leaf re-name {
                 type string;
               }
               choice output-tags {
                 case actual-tag {
                   container unified-services-status-information {
                     uses unified-services-status-information-block;
                   }
                 }
               }
             }
           }
         }
       }
     }
   }
   rpc get-system-uptime-information {
     description "Show time since system and processes started";
     input {
       uses command-forwarding;
       choice dcf-role {
         description "Device type";
         case interconnect-device {
         }
         case node-group {
         }
         case infrastructure {
         }
         case director-group {
         }
       }
     }
     output {
       choice output-tags {
         case actual-tag {
           container system-uptime-information {
             uses system-uptime-information-block;
           }
         }
         case multichassis-tag {
           container multi-routing-engine-results {
             list multi-routing-engine-item {
               leaf re-name {
                 type string;
               }
               choice output-tags {
                 case actual-tag {
                   container system-uptime-information {
                     uses system-uptime-information-block;
                   }
                 }
               }
             }
           }
         }
       }
     }
   }
   rpc get-macsec-license-information {
     description "Show macsec licenses information";
     output {
       choice output-tags {
         case actual-tag {
           container macsec-license-information {
             uses macsec-license-information-block;
           }
         }
         case multichassis-tag {
           container multi-routing-engine-results {
             list multi-routing-engine-item {
               leaf re-name {
                 type string;
               }
               choice output-tags {
                 case actual-tag {
                   container macsec-license-information {
                     uses macsec-license-information-block;
                   }
                 }
               }
             }
           }
         }
       }
     }
   }
   rpc get-license-summary-information {
     description "Show feature licenses information";
     input {
       leaf level {
         default "brief";
         type enumeration {
           enum "brief" {
             description "Display brief output (default)";
           }
           enum "detail" {
             description "Display detailed output";
           }
         }
       }
     }
     output {
       choice output-tags {
         case actual-tag {
           container license-summary-information {
             uses license-summary-information-block;
           }
         }
         case multichassis-tag {
           container multi-routing-engine-results {
             list multi-routing-engine-item {
               leaf re-name {
                 type string;
               }
               choice output-tags {
                 case actual-tag {
                   container license-summary-information {
                     uses license-summary-information-block;
                   }
                 }
               }
             }
           }
         }
       }
     }
   }
   rpc get-license-information {
     description "Show installed feature licenses";
     output {
       choice output-tags {
         case actual-tag {
           container license-information {
             uses license-information-block;
           }
         }
         case multichassis-tag {
           container multi-routing-engine-results {
             list multi-routing-engine-item {
               leaf re-name {
                 type string;
               }
               choice output-tags {
                 case actual-tag {
                   container license-information {
                     uses license-information-block;
                   }
                 }
               }
             }
           }
         }
       }
     }
   }
   rpc get-license-key-information {
     description "Show license keys";
     output {
       choice output-tags {
         case actual-tag {
           container license-key-information {
             uses license-key-information-block;
           }
         }
         case multichassis-tag {
           container multi-routing-engine-results {
             list multi-routing-engine-item {
               leaf re-name {
                 type string;
               }
               choice output-tags {
                 case actual-tag {
                   container license-key-information {
                     uses license-key-information-block;
                   }
                 }
               }
             }
           }
         }
       }
     }
   }
   rpc get-license-usage-summary {
     description "Show licensed features";
     output {
       choice output-tags {
         case actual-tag {
           container license-usage-summary {
             uses license-usage-summary-block;
           }
         }
         case multichassis-tag {
           container multi-routing-engine-results {
             list multi-routing-engine-item {
               leaf re-name {
                 type string;
               }
               choice output-tags {
                 case actual-tag {
                   container license-usage-summary {
                     uses license-usage-summary-block;
                   }
                 }
               }
             }
           }
         }
       }
     }
   }
   rpc get-license-feature-list {
     description "Show all applicable licensed features";
     output {
       choice output-tags {
         case actual-tag {
           container license-feature-list-information {
             uses license-feature-list-information-block;
           }
         }
         case multichassis-tag {
           container multi-routing-engine-results {
             list multi-routing-engine-item {
               leaf re-name {
                 type string;
               }
               choice output-tags {
                 case actual-tag {
                   container license-feature-list-information {
                     uses license-feature-list-information-block;
                   }
                 }
               }
             }
           }
         }
       }
     }
   }
   rpc get-license-fpc-information {
     description "Show license fpc information";
     output {
       choice output-tags {
         case actual-tag {
           container license-fpc-information {
             uses license-fpc-information-block;
           }
         }
         case multichassis-tag {
           container multi-routing-engine-results {
             list multi-routing-engine-item {
               leaf re-name {
                 type string;
               }
               choice output-tags {
                 case actual-tag {
                   container license-fpc-information {
                     uses license-fpc-information-block;
                   }
                 }
               }
             }
           }
         }
       }
     }
   }
   rpc get-license-bandwidth-summary-information {
     description "Show license bandwidth summary";
     output {
       choice output-tags {
         case actual-tag {
           container license-bandwidth-summary {
             uses license-bandwidth-summary-block;
           }
         }
         case multichassis-tag {
           container multi-routing-engine-results {
             list multi-routing-engine-item {
               leaf re-name {
                 type string;
               }
               choice output-tags {
                 case actual-tag {
                   container license-bandwidth-summary {
                     uses license-bandwidth-summary-block;
                   }
                 }
               }
             }
           }
         }
       }
     }
   }
   rpc get-license-fpc-bandwidth-information {
     description "Show license fpc bandwidth summary";
     input {
       leaf fpc-slot {
         description "FPC slot number";
         type union {
           type string {
             pattern "<.*>|$.*";
           }
           type uint32;
         }
         mandatory true;
       }
     }
     output {
       choice output-tags {
         case actual-tag {
           container license-bandwidth-summary {
             uses license-bandwidth-summary-block;
           }
         }
         case multichassis-tag {
           container multi-routing-engine-results {
             list multi-routing-engine-item {
               leaf re-name {
                 type string;
               }
               choice output-tags {
                 case actual-tag {
                   container license-bandwidth-summary {
                     uses license-bandwidth-summary-block;
                   }
                 }
               }
             }
           }
         }
       }
     }
   }
   rpc get-license-bandwidth-information {
     description "Show fpc port bandwidth details";
     input {
       leaf fpc-slot {
         description "FPC slot number";
         type union {
           type string {
             pattern "<.*>|$.*";
           }
           type uint32;
         }
         mandatory true;
       }
     }
     output {
       choice output-tags {
         case actual-tag {
           container license-bandwidth-information {
             uses license-bandwidth-information-block;
           }
         }
         case multichassis-tag {
           container multi-routing-engine-results {
             list multi-routing-engine-item {
               leaf re-name {
                 type string;
               }
               choice output-tags {
                 case actual-tag {
                   container license-bandwidth-information {
                     uses license-bandwidth-information-block;
                   }
                 }
               }
             }
           }
         }
       }
     }
   }
   rpc get-license-linecard-bandwidth-information {
     description "Show license flex-only bandwidth summary";
     output {
       choice output-tags {
         case actual-tag {
           container license-linecard-bandwidth {
             uses license-linecard-bandwidth-block;
           }
         }
         case multichassis-tag {
           container multi-routing-engine-results {
             list multi-routing-engine-item {
               leaf re-name {
                 type string;
               }
               choice output-tags {
                 case actual-tag {
                   container license-linecard-bandwidth {
                     uses license-linecard-bandwidth-block;
                   }
                 }
               }
             }
           }
         }
       }
     }
   }
   rpc get-system-information {
     description "Show system information";
     output {
       choice output-tags {
         case actual-tag {
           container system-information {
             uses system-information-block;
           }
         }
         case multichassis-tag {
           container multi-routing-engine-results {
             list multi-routing-engine-item {
               leaf re-name {
                 type string;
               }
               choice output-tags {
                 case actual-tag {
                   container system-information {
                     uses system-information-block;
                   }
                 }
               }
             }
           }
         }
       }
     }
   }
   rpc get-system-timex-information {
     description "Print timex structure information";
     input {
       leaf node {
         description "Node name";
         type string;
       }
     }
     output {
       choice output-tags {
         case actual-tag {
           container system-timex-information {
             uses system-timex-information-block;
           }
         }
         case multichassis-tag {
           container multi-routing-engine-results {
             list multi-routing-engine-item {
               leaf re-name {
                 type string;
               }
               choice output-tags {
                 case actual-tag {
                   container system-timex-information {
                     uses system-timex-information-block;
                   }
                 }
               }
             }
           }
         }
       }
     }
   }
   rpc get-yang-schema {
     description "Show system schema in various formats";
     input {
       leaf format {
         description "The data modeling language of the schema";
         default "yang";
         type enumeration {
           enum "yang" {
             description "YANG (default)";
           }
         }
       }
       leaf identifier {
         description "Module to be shown";
         type string;
         mandatory true;
       }
       leaf output-directory {
         description "Directory to save requested YANG modules";
         type string;
         mandatory true;
       }
       leaf version {
         description "Version of the schema requested";
         type string;
       }
     }
     output {
       choice output-tags {
         case output-tag {
           leaf output {
             type string;
           }
         }
         case multichassis-tag {
           anyxml multi-routing-engine-results;
         }
       }
     }
   }
   rpc get-system-yang-packages {
     description "Show YANG package(s) installed on system";
     input {
       leaf id {
         description "Show YANG package with ID";
         type string;
       }
       choice re-choice {
         case re0 {
           leaf re0 {
             description "Add/Delete YANG module(s) on RE0";
             type empty;
           }
         }
         case re1 {
           leaf re1 {
             description "Add/Delete YANG module(s) on RE1";
             type empty;
           }
         }
         case other-routing-engine {
           leaf other-routing-engine {
             description "Add/Delete YANG module(s) on other RE";
             type empty;
           }
         }
       }
     }
     output {
       choice output-tags {
         case actual-tag {
           container yang-package-information {
             uses yang-package-information-block;
           }
         }
         case multichassis-tag {
           container multi-routing-engine-results {
             list multi-routing-engine-item {
               leaf re-name {
                 type string;
               }
               choice output-tags {
                 case actual-tag {
                   container yang-package-information {
                     uses yang-package-information-block;
                   }
                 }
               }
             }
           }
         }
       }
     }
   }
   rpc get-subscriber-management-health-clients {
     description "Clients information";
     output {
       choice output-tags {
         case actual-tag {
           container clients {
             uses clients-block;
           }
         }
         case multichassis-tag {
           container multi-routing-engine-results {
             list multi-routing-engine-item {
               leaf re-name {
                 type string;
               }
               choice output-tags {
                 case actual-tag {
                   container clients {
                     uses clients-block;
                   }
                 }
               }
             }
           }
         }
       }
     }
   }
   rpc get-subscriber-management-health-endpoints {
     description "Endpoints information";
     output {
       choice output-tags {
         case actual-tag {
           container endpoints {
             uses endpoints-block;
           }
         }
         case multichassis-tag {
           container multi-routing-engine-results {
             list multi-routing-engine-item {
               leaf re-name {
                 type string;
               }
               choice output-tags {
                 case actual-tag {
                   container endpoints {
                     uses endpoints-block;
                   }
                 }
               }
             }
           }
         }
       }
     }
   }
   rpc get-subscriber-management-health-services {
     description "Services information";
     output {
       choice output-tags {
         case actual-tag {
           container services {
             uses services-block;
           }
         }
         case multichassis-tag {
           container multi-routing-engine-results {
             list multi-routing-engine-item {
               leaf re-name {
                 type string;
               }
               choice output-tags {
                 case actual-tag {
                   container services {
                     uses services-block;
                   }
                 }
               }
             }
           }
         }
       }
     }
   }
   rpc get-subscriber-management-health-service {
     description "Service information";
     input {
       leaf service-name {
         description "Name of the service";
         type enumeration {
           enum "all" {
             description "All services";
           }
           enum "authentication-service" {
             description "Authentication service";
           }
           enum "ipm-service" {
             description "Integrated plane manager service";
           }
           enum "ppp-service" {
             description "PPP service";
           }
           enum "l2tp-service" {
             description "L2TP service";
           }
           enum "replication-client-service" {
             description "Replication client service";
           }
           enum "replication-server-service" {
             description "Replication server service";
           }
           enum "smg-service" {
             description "Control plane subscriber-management management service";
           }
           enum "smg-service1" {
             description "Control plane subscriber management service";
           }
           enum "subscriber-statistics-service" {
             description "Subscriber statistics service";
           }
           enum "up-smg-service" {
             description "User plane subscriber management service";
           }
         }
         mandatory true;
       }
     }
     output {
       choice output-tags {
         case actual-tag {
           container service {
             uses service-block;
           }
         }
         case multichassis-tag {
           container multi-routing-engine-results {
             list multi-routing-engine-item {
               leaf re-name {
                 type string;
               }
               choice output-tags {
                 case actual-tag {
                   container service {
                     uses service-block;
                   }
                 }
               }
             }
           }
         }
       }
     }
   }
   rpc get-upm-summary-information {
     description "User-plane manager summary information";
     output {
       choice output-tags {
         case output-tag {
           leaf output {
             type string;
           }
         }
         case actual-tag {
           anyxml subscriber-management-user-plane-cpm;
         }
         case multichassis-tag {
           anyxml multi-routing-engine-results;
         }
       }
     }
   }
   rpc get-upm-association-information {
     description "User-plane manager association information";
     output {
       choice output-tags {
         case actual-tag {
           container subscriber-management-user-plane-associations {
             uses subscriber-management-user-plane-associations-block;
           }
         }
         case multichassis-tag {
           container multi-routing-engine-results {
             list multi-routing-engine-item {
               leaf re-name {
                 type string;
               }
               choice output-tags {
                 case actual-tag {
                   container subscriber-management-user-plane-associations {
                     uses subscriber-management-user-plane-associations-block;
                   }
                 }
               }
             }
           }
         }
       }
     }
   }
   rpc get-upm-client-information {
     description "User-plane manager client information";
     output {
       choice output-tags {
         case actual-tag {
           container subscriber-management-user-plane-clients {
             uses subscriber-management-user-plane-clients-block;
           }
         }
         case multichassis-tag {
           container multi-routing-engine-results {
             list multi-routing-engine-item {
               leaf re-name {
                 type string;
               }
               choice output-tags {
                 case actual-tag {
                   container subscriber-management-user-plane-clients {
                     uses subscriber-management-user-plane-clients-block;
                   }
                 }
               }
             }
           }
         }
       }
     }
   }
   rpc get-upm-services-information {
     description "User-plane services information";
     output {
       choice output-tags {
         case actual-tag {
           container subscriber-management-user-plane-services {
             uses subscriber-management-user-plane-services-block;
           }
         }
         case multichassis-tag {
           container multi-routing-engine-results {
             list multi-routing-engine-item {
               leaf re-name {
                 type string;
               }
               choice output-tags {
                 case actual-tag {
                   container subscriber-management-user-plane-services {
                     uses subscriber-management-user-plane-services-block;
                   }
                 }
               }
             }
           }
         }
       }
     }
   }
   rpc get-upm-service-information {
     description "User-plane service information";
     input {
       leaf service-name {
         description "Service name";
         type enumeration {
           enum "all" {
             description "All services";
           }
           enum "subscriber-helper-service" {
             description "Helperd service";
           }
           enum "gtp-proxy-service" {
             description "GTP proxy service";
           }
           enum "pfcp-proxy-service" {
             description "PFCP proxy service";
           }
           enum "subscriber-statistics-service" {
             description "Subscriber statistics service";
           }
           enum "upm-service" {
             description "User plane manager service";
           }
           enum "replication-client-service" {
             description "Replication client service";
           }
           enum "replication-server-service" {
             description "Replication server service";
           }
           enum "up-smg-service" {
             description "User plane subscriber management service";
           }
         }
         mandatory true;
       }
     }
     output {
       choice output-tags {
         case output-tag {
           leaf output {
             type string;
           }
         }
         case actual-tag {
           anyxml subscriber-management-user-plane-service;
         }
         case multichassis-tag {
           anyxml multi-routing-engine-results;
         }
       }
     }
   }
   rpc get-control-plane-information {
     description "Control-plane information";
     input {
       leaf control-plane-name {
         description "Control plane name";
         type string;
         mandatory true;
       }
       leaf endpoint {
         description "Name of the Endpoint";
         type enumeration {
           enum "all" {
             description "All endpoints";
           }
           enum "Sci" {
             description "Node association";
           }
           enum "Cpri" {
             description "Control Packet I/O";
           }
           enum "PfcpProxySmgIpc" {
             description "PFCP proxy endpoint of Ipc to Smg";
           }
           enum "SmgPfcpProxyIpc" {
             description "Smg endpoint of Ipc to PFCP proxyd";
           }
           enum "StatsPfcpProxyIpc" {
             description "Stats endpoint of Ipc to PFCP proxyd";
           }
           enum "PfcpProxyStatsIpc" {
             description "PFCP proxyd endpoint of Ipc to Stats";
           }
           enum "RepClientSS" {
             description "Rep client state sync";
           }
         }
       }
     }
     output {
       choice output-tags {
         case actual-tag {
           container subscriber-management-control-plane-detail {
             uses subscriber-management-control-plane-detail-block;
           }
         }
         case multichassis-tag {
           container multi-routing-engine-results {
             list multi-routing-engine-item {
               leaf re-name {
                 type string;
               }
               choice output-tags {
                 case actual-tag {
                   container subscriber-management-control-plane-detail {
                     uses subscriber-management-control-plane-detail-block;
                   }
                 }
               }
             }
           }
         }
       }
     }
   }
   rpc get-subscriber-management-summary-information {
     description "Show Subscriber management summary";
     output {
       choice output-tags {
         case output-tag {
           leaf output {
             type string;
           }
         }
         case actual-tag {
           anyxml subscriber-management-summary-information;
         }
         case multichassis-tag {
           anyxml multi-routing-engine-results;
         }
       }
     }
   }
   rpc get-subscriber-management-statistics {
     description "Show subscriber management statistics";
     input {
       leaf all {
         description "Display all statistics";
         type empty;
       }
       leaf dhcp {
         description "Display dhcp statistics";
         type empty;
       }
       leaf dvlan {
         description "Display dvlan statistics";
         type empty;
       }
       leaf ppp {
         description "Display ppp statistics";
         type empty;
       }
       leaf pppoe {
         description "Display pppoe statistics";
         type empty;
       }
       leaf l2tp {
         description "Display l2tp statistics";
         type empty;
       }
       leaf fixed-wireless-access {
         description "Display fixed-wireless-access statistics";
         type empty;
       }
       leaf agf {
         description "Display agf statistics";
         type empty;
       }
     }
     output {
       choice output-tags {
         case output-tag {
           leaf output {
             type string;
           }
         }
         case actual-tag {
           anyxml subscriber-management-statistics;
         }
         case multichassis-tag {
           anyxml multi-routing-engine-results;
         }
       }
     }
   }
   rpc get-sub-mgmt-internal-transit-statistics {
     description "Show subscriber management internal-transit statistics";
     input {
       leaf all {
         description "Display all statistics";
         type empty;
       }
       leaf dhcp {
         description "Display dhcp statistics";
         type empty;
       }
       leaf dvlan {
         description "Display dvlan statistics";
         type empty;
       }
       leaf ppp {
         description "Display ppp statistics";
         type empty;
       }
       leaf pppoe {
         description "Display pppoe statistics";
         type empty;
       }
       leaf l2tp {
         description "Display l2tp statistics";
         type empty;
       }
       leaf fixed-wireless-access {
         description "Display fixed-wireless-access statistics";
         type empty;
       }
       leaf agf {
         description "Display agf statistics";
         type empty;
       }
     }
     output {
       choice output-tags {
         case output-tag {
           leaf output {
             type string;
           }
         }
         case actual-tag {
           anyxml subscriber-management-statistics;
         }
         case multichassis-tag {
           anyxml multi-routing-engine-results;
         }
       }
     }
   }
   rpc get-subscriber-management-route-information {
     description "Show subscriber management route information";
     input {
       leaf family {
         description "Name of family";
         type enumeration {
           enum "inet" {
             description "IP version 4 (IPv4)";
           }
           enum "inet6" {
             description "IP version 6 (IPv6)";
           }
         }
       }
       leaf route-type {
         description "Type of route";
         type enumeration {
           enum "local" {
             description "Local route";
           }
           enum "access" {
             description "Access route";
           }
           enum "access-internal" {
             description "Access-internal route";
           }
           enum "kernel" {
             description "Kernel route";
           }
           enum "discard" {
             description "Discard route";
           }
         }
       }
       leaf routing-instance {
         description "Name of routing instance";
         type string;
       }
       leaf level {
         default "brief";
         type enumeration {
           enum "brief" {
             description "Display brief information";
           }
           enum "detail" {
             description "Display detailed information";
           }
         }
       }
       leaf incomplete {
         description "Display only incomplete routes";
         type empty;
       }
     }
     output {
       choice output-tags {
         case actual-tag {
           container subscriber-management-route-information {
             uses subscriber-management-route-information-block;
           }
         }
         case multichassis-tag {
           container multi-routing-engine-results {
             list multi-routing-engine-item {
               leaf re-name {
                 type string;
               }
               choice output-tags {
                 case actual-tag {
                   container subscriber-management-route-information {
                     uses subscriber-management-route-information-block;
                   }
                 }
               }
             }
           }
         }
       }
     }
   }
   rpc get-subscriber-management-route-summary {
     description "Show subscriber management route summary";
     output {
       choice output-tags {
         case output-tag {
           leaf output {
             type string;
           }
         }
         case actual-tag {
           anyxml subscriber-management-route-summary;
         }
         case multichassis-tag {
           anyxml multi-routing-engine-results;
         }
       }
     }
   }
   rpc get-subscriber-management-route-nh {
     description "Show subscriber management route next-hop information";
     input {
       leaf index {
         description "Next-hop index";
         type union {
           type string {
             pattern "<.*>|$.*";
           }
           type uint16 {
             range "1 .. 65535";
           }
         }
       }
     }
     output {
       choice output-tags {
         case output-tag {
           leaf output {
             type string;
           }
         }
         case actual-tag {
           anyxml subscriber-management-route-nh;
         }
         case multichassis-tag {
           anyxml multi-routing-engine-results;
         }
       }
     }
   }
   rpc get-subscriber-management-arp-information {
     description "Show subscriber management arp information";
     output {
       choice output-tags {
         case output-tag {
           leaf output {
             type string;
           }
         }
         case actual-tag {
           anyxml subscriber-management-arp-information;
         }
         case multichassis-tag {
           anyxml multi-routing-engine-results;
         }
       }
     }
   }
   rpc get-subscriber-management-arp-interface {
     description "Name of interface";
     input {
       leaf interface-name {
         description "Name of interface";
         type string;
         mandatory true;
       }
     }
     output {
       choice output-tags {
         case output-tag {
           leaf output {
             type string;
           }
         }
         case actual-tag {
           anyxml subscriber-management-arp-interface;
         }
         case multichassis-tag {
           anyxml multi-routing-engine-results;
         }
       }
     }
   }
   rpc get-subscriber-management-arp-address {
     description "Ipv4 address";
     input {
       leaf ip-address {
         description "Ipv4 address";
         type jt:ipv4addr;
         mandatory true;
       }
     }
     output {
       choice output-tags {
         case output-tag {
           leaf output {
             type string;
           }
         }
         case actual-tag {
           anyxml subscriber-management-arp-address;
         }
         case multichassis-tag {
           anyxml multi-routing-engine-results;
         }
       }
     }
   }
   rpc get-subscriber-management-ipv6-nbrs-information {
     description "Show subscriber management ipv6 neighbors information";
     output {
       choice output-tags {
         case output-tag {
           leaf output {
             type string;
           }
         }
         case actual-tag {
           anyxml subscriber-management-ipv6-neighbors-information;
         }
         case multichassis-tag {
           anyxml multi-routing-engine-results;
         }
       }
     }
   }
   rpc get-subscriber-management-ipv6-neighbor-interface {
     description "Name of interface";
     input {
       leaf interface-name {
         description "Name of interface";
         type string;
         mandatory true;
       }
     }
     output {
       choice output-tags {
         case output-tag {
           leaf output {
             type string;
           }
         }
         case actual-tag {
           anyxml subscriber-management-ipv6-neighbor-interface;
         }
         case multichassis-tag {
           anyxml multi-routing-engine-results;
         }
       }
     }
   }
   rpc get-subscriber-management-ipv6-neighbor-address {
     description "Ipv6 address";
     input {
       leaf interface-name {
         description "Ipv6 address";
         type jt:ipv6addr;
         mandatory true;
       }
     }
     output {
       choice output-tags {
         case output-tag {
           leaf output {
             type string;
           }
         }
         case actual-tag {
           anyxml subscriber-management-ipv6-neighbor-address;
         }
         case multichassis-tag {
           anyxml multi-routing-engine-results;
         }
       }
     }
   }
   rpc get-subscriber-management-ipv6-ra {
     description "Show subscriber management ipv6 router-advertisement information";
     output {
       choice output-tags {
         case actual-tag {
           container subscriber-management-ipv6-ra {
             uses subscriber-management-ipv6-ra-block;
           }
         }
         case multichassis-tag {
           container multi-routing-engine-results {
             list multi-routing-engine-item {
               leaf re-name {
                 type string;
               }
               choice output-tags {
                 case actual-tag {
                   container subscriber-management-ipv6-ra {
                     uses subscriber-management-ipv6-ra-block;
                   }
                 }
               }
             }
           }
         }
       }
     }
   }
   rpc get-subscriber-management-ipv6-ra-interface {
     description "Name of interface";
     input {
       leaf interface-name {
         description "Name of interface";
         type string;
         mandatory true;
       }
     }
     output {
       choice output-tags {
         case output-tag {
           leaf output {
             type string;
           }
         }
         case actual-tag {
           anyxml subscriber-management-ipv6-ra-interface;
         }
         case multichassis-tag {
           anyxml multi-routing-engine-results;
         }
       }
     }
   }
   rpc get-subscriber-management-ipv6-ra-prefix {
     description "Ipv6 prefix";
     input {
       leaf interface-prefix {
         description "Ipv6 prefix";
         type jt:ipv6addr;
         mandatory true;
       }
     }
     output {
       choice output-tags {
         case output-tag {
           leaf output {
             type string;
           }
         }
         case actual-tag {
           anyxml subscriber-management-ipv6-ra-prefix;
         }
         case multichassis-tag {
           anyxml multi-routing-engine-results;
         }
       }
     }
   }
   rpc get-subscriber-management-v4-liveness {
     description "Show subscriber management dhcpv4 liveness detection information";
     output {
       choice output-tags {
         case output-tag {
           leaf output {
             type string;
           }
         }
         case actual-tag {
           anyxml subscriber-management-v4-liveness;
         }
         case multichassis-tag {
           anyxml multi-routing-engine-results;
         }
       }
     }
   }
   rpc get-subscriber-management-v4-liveness-interface {
     description "Name of interface";
     input {
       leaf interface-name {
         description "Name of interface";
         type string;
         mandatory true;
       }
     }
     output {
       choice output-tags {
         case output-tag {
           leaf output {
             type string;
           }
         }
         case actual-tag {
           anyxml subscriber-management-v4-liveness-interface;
         }
         case multichassis-tag {
           anyxml multi-routing-engine-results;
         }
       }
     }
   }
   rpc get-subscriber-management-v4-liveness-address {
     description "Ipv4 address";
     input {
       leaf ip-address {
         description "Ipv4 address";
         type jt:ipv4addr;
         mandatory true;
       }
     }
     output {
       choice output-tags {
         case output-tag {
           leaf output {
             type string;
           }
         }
         case actual-tag {
           anyxml subscriber-management-v4-liveness-address;
         }
         case multichassis-tag {
           anyxml multi-routing-engine-results;
         }
       }
     }
   }
   rpc get-subscriber-management-v6-liveness {
     description "Show subscriber management dhcpv6 liveness detection information";
     output {
       choice output-tags {
         case output-tag {
           leaf output {
             type string;
           }
         }
         case actual-tag {
           anyxml subscriber-management-v6-liveness;
         }
         case multichassis-tag {
           anyxml multi-routing-engine-results;
         }
       }
     }
   }
   rpc get-subscriber-management-v6-liveness-interface {
     description "Name of interface";
     input {
       leaf interface-name {
         description "Name of interface";
         type string;
         mandatory true;
       }
     }
     output {
       choice output-tags {
         case output-tag {
           leaf output {
             type string;
           }
         }
         case actual-tag {
           anyxml subscriber-management-v6-liveness-interface;
         }
         case multichassis-tag {
           anyxml multi-routing-engine-results;
         }
       }
     }
   }
   rpc get-subscriber-management-v6-liveness-address {
     description "Ipv6 address";
     input {
       leaf interface-name {
         description "Ipv6 address";
         type jt:ipv6addr;
         mandatory true;
       }
     }
     output {
       choice output-tags {
         case output-tag {
           leaf output {
             type string;
           }
         }
         case actual-tag {
           anyxml subscriber-management-v6-liveness-address;
         }
         case multichassis-tag {
           anyxml multi-routing-engine-results;
         }
       }
     }
   }
   rpc get-subscriber-management-napt-pool-stats {
     description "Show inline-napt pool statistics information";
     output {
       choice output-tags {
         case actual-tag {
           container subscriber-management-napt-pool-stats {
             uses subscriber-management-napt-pool-stats-block;
           }
         }
         case multichassis-tag {
           container multi-routing-engine-results {
             list multi-routing-engine-item {
               leaf re-name {
                 type string;
               }
               choice output-tags {
                 case actual-tag {
                   container subscriber-management-napt-pool-stats {
                     uses subscriber-management-napt-pool-stats-block;
                   }
                 }
               }
             }
           }
         }
       }
     }
   }
   rpc get-subscriber-management-napt-pool-stats-name {
     description "Name of pool";
     input {
       leaf pool-name {
         description "Name of pool";
         type string;
         mandatory true;
       }
     }
     output {
       choice output-tags {
         case output-tag {
           leaf output {
             type string;
           }
         }
         case actual-tag {
           anyxml subscriber-management-napt-pool-stats-name;
         }
         case multichassis-tag {
           anyxml multi-routing-engine-results;
         }
       }
     }
   }
   rpc get-subscriber-management-resiliency-information {
     description "Show resiliency information";
     input {
       leaf level {
         default "summary";
         type enumeration {
           enum "summary" {
             description "Display summary information";
           }
           enum "detail" {
             description "Display detailed information";
           }
           enum "extensive" {
             description "Display extensive information";
           }
         }
       }
     }
     output {
       choice output-tags {
         case output-tag {
           leaf output {
             type string;
           }
         }
         case multichassis-tag {
           anyxml multi-routing-engine-results;
         }
       }
     }
   }
   rpc get-subscriber-mgmt-red-state {
     description "Show subscriber management redundancy state";
     output {
       choice output-tags {
         case output-tag {
           leaf output {
             type string;
           }
         }
         case actual-tag {
           anyxml subscriber-mgmt-red-state;
         }
         case multichassis-tag {
           anyxml multi-routing-engine-results;
         }
       }
     }
   }
   rpc get-subscriber-mgmt-red-state-dhcp {
     description "DHCP information";
     output {
       choice output-tags {
         case output-tag {
           leaf output {
             type string;
           }
         }
         case actual-tag {
           anyxml subscriber-mgmt-red-state-dhcp;
         }
         case multichassis-tag {
           anyxml multi-routing-engine-results;
         }
       }
     }
   }
   rpc get-subscriber-mgmt-red-state-dhcp-alq {
     description "Active-leasequery protocol";
     output {
       choice output-tags {
         case output-tag {
           leaf output {
             type string;
           }
         }
         case actual-tag {
           anyxml subscriber-mgmt-red-state-dhcp-alq;
         }
         case multichassis-tag {
           anyxml multi-routing-engine-results;
         }
       }
     }
   }
   rpc get-subscriber-mgmt-red-state-dhcp-alq-intf {
     description "Underlying interface name";
     input {
       leaf interface-name {
         description "Name of interface";
         type string;
         mandatory true;
       }
     }
     output {
       choice output-tags {
         case output-tag {
           leaf output {
             type string;
           }
         }
         case actual-tag {
           anyxml subscriber-mgmt-red-state-dhcp-alq-intf;
         }
         case multichassis-tag {
           anyxml multi-routing-engine-results;
         }
       }
     }
   }
   rpc get-subscriber-mgmt-red-state-intf {
     description "Underlying interface name";
     input {
       leaf interface-name {
         description "Name of interface";
         type string;
         mandatory true;
       }
     }
     output {
       choice output-tags {
         case output-tag {
           leaf output {
             type string;
           }
         }
         case actual-tag {
           anyxml subscriber-mgmt-red-state-intf;
         }
         case multichassis-tag {
           anyxml multi-routing-engine-results;
         }
       }
     }
   }
   rpc get-subscriber-management-subscriber-group {
     description "Show subscriber group information";
     input {
       leaf subscriber-group-name {
         description "Subscriber group name";
         type string;
       }
       leaf redundancy-service {
         description "Redundancy Service Id";
         type union {
           type uint32;
           type string {
             pattern "<.*>|$.*";
           }
         }
       }
     }
     output {
       choice output-tags {
         case output-tag {
           leaf output {
             type string;
           }
         }
         case actual-tag {
           anyxml subscriber-management-subscriber-group;
         }
         case multichassis-tag {
           anyxml multi-routing-engine-results;
         }
       }
     }
   }
   rpc get-subscriber-management-routing-instance {
     description "Show routing-instance information";
     input {
       leaf routing-instance-name {
         description "Routing instance name";
         type string;
       }
     }
     output {
       choice output-tags {
         case actual-tag {
           container subscriber-management-routing-instance {
             uses subscriber-management-routing-instance-block;
           }
         }
         case multichassis-tag {
           container multi-routing-engine-results {
             list multi-routing-engine-item {
               leaf re-name {
                 type string;
               }
               choice output-tags {
                 case actual-tag {
                   container subscriber-management-routing-instance {
                     uses subscriber-management-routing-instance-block;
                   }
                 }
               }
             }
           }
         }
       }
     }
   }
   rpc get-system-core-dumps {
     description "Show system core files";
     input {
       uses command-forwarding;
       leaf subsystem {
         description "Name of the subsystem";
         type string;
         mandatory true;
       }
     }
     output {
       choice output-tags {
         case actual-tag {
           container directory-list {
             uses directory-list-block;
           }
         }
         case multichassis-tag {
           container multi-routing-engine-results {
             list multi-routing-engine-item {
               leaf re-name {
                 type string;
               }
               choice output-tags {
                 case actual-tag {
                   container directory-list {
                     uses directory-list-block;
                   }
                 }
               }
             }
           }
         }
       }
     }
   }
   rpc get-core-file-satellite {
     description "Show core-files on satellite devices";
     input {
       leaf fpc-slot {
         description "Satellite slot number";
         type union {
           type string {
             pattern "<.*>|$.*";
           }
           type uint32 {
             range "65 .. 254";
           }
         }
       }
       leaf device-alias {
         description "Device alias";
         type string;
       }
     }
     output {
       choice output-tags {
         case output-tag {
           leaf output {
             type string;
           }
         }
         case multichassis-tag {
           anyxml multi-routing-engine-results;
         }
       }
     }
   }
   rpc get-boot-media-information {
     description "Display permanent boot media settings";
     output {
       choice output-tags {
         case output-tag {
           leaf output {
             type string;
           }
         }
         case actual-tag {
           anyxml system-boot-media-information;
         }
         case multichassis-tag {
           anyxml multi-routing-engine-results;
         }
       }
     }
   }
   rpc get-system-error-information {
     description "Show system error status";
     output {
       choice output-tags {
         case actual-tag {
           container system-error-information {
             uses system-error-information-block;
           }
         }
         case multichassis-tag {
           container multi-routing-engine-results {
             list multi-routing-engine-item {
               leaf re-name {
                 type string;
               }
               choice output-tags {
                 case actual-tag {
                   container system-error-information {
                     uses system-error-information-block;
                   }
                 }
               }
             }
           }
         }
       }
     }
   }
   rpc get-active-error-count-information {
     description "Show all errors";
     output {
       choice output-tags {
         case actual-tag {
           container active-error-count-information {
             uses active-error-count-information-block;
           }
         }
         case multichassis-tag {
           container multi-routing-engine-results {
             list multi-routing-engine-item {
               leaf re-name {
                 type string;
               }
               choice output-tags {
                 case actual-tag {
                   container active-error-count-information {
                     uses active-error-count-information-block;
                   }
                 }
               }
             }
           }
         }
       }
     }
   }
   rpc get-active-error-information {
     description "Show active errors";
     output {
       choice output-tags {
         case actual-tag {
           container active-error-information {
             uses active-error-information-block;
           }
         }
         case multichassis-tag {
           container multi-routing-engine-results {
             list multi-routing-engine-item {
               leaf re-name {
                 type string;
               }
               choice output-tags {
                 case actual-tag {
                   container active-error-information {
                     uses active-error-information-block;
                   }
                 }
               }
             }
           }
         }
       }
     }
   }
   rpc get-fpc-active-error-information {
     description "Show active errors for FPC";
     input {
       leaf slot {
         description "FPC slot number";
         type union {
           type string {
             pattern "<.*>|$.*";
           }
           type uint32;
         }
         mandatory true;
       }
     }
     output {
       choice output-tags {
         case actual-tag {
           container active-error-information {
             uses active-error-information-block;
           }
         }
         case multichassis-tag {
           container multi-routing-engine-results {
             list multi-routing-engine-item {
               leaf re-name {
                 type string;
               }
               choice output-tags {
                 case actual-tag {
                   container active-error-information {
                     uses active-error-information-block;
                   }
                 }
               }
             }
           }
         }
       }
     }
   }
   rpc get-sib-active-error-information {
     description "Show active errors for SIB";
     input {
       leaf slot {
         description "SIB slot number";
         type union {
           type string {
             pattern "<.*>|$.*";
           }
           type uint32;
         }
         mandatory true;
       }
     }
     output {
       choice output-tags {
         case actual-tag {
           container active-error-information {
             uses active-error-information-block;
           }
         }
         case multichassis-tag {
           container multi-routing-engine-results {
             list multi-routing-engine-item {
               leaf re-name {
                 type string;
               }
               choice output-tags {
                 case actual-tag {
                   container active-error-information {
                     uses active-error-information-block;
                   }
                 }
               }
             }
           }
         }
       }
     }
   }
   rpc get-feb-active-error-information {
     description "Show active errors for FEB";
     input {
       leaf slot {
         description "FEB slot number";
         type union {
           type string {
             pattern "<.*>|$.*";
           }
           type uint32 {
             range "0 .. 1";
           }
         }
         mandatory true;
       }
     }
     output {
       choice output-tags {
         case actual-tag {
           container active-error-information {
             uses active-error-information-block;
           }
         }
         case multichassis-tag {
           container multi-routing-engine-results {
             list multi-routing-engine-item {
               leaf re-name {
                 type string;
               }
               choice output-tags {
                 case actual-tag {
                   container active-error-information {
                     uses active-error-information-block;
                   }
                 }
               }
             }
           }
         }
       }
     }
   }
   rpc get-re-active-error-information {
     description "Show active errors for RE";
     input {
       leaf slot {
         description "RE slot number";
         type union {
           type string {
             pattern "<.*>|$.*";
           }
           type int32;
         }
         mandatory true;
       }
     }
     output {
       choice output-tags {
         case actual-tag {
           container active-error-information {
             uses active-error-information-block;
           }
         }
         case multichassis-tag {
           container multi-routing-engine-results {
             list multi-routing-engine-item {
               leaf re-name {
                 type string;
               }
               choice output-tags {
                 case actual-tag {
                   container active-error-information {
                     uses active-error-information-block;
                   }
                 }
               }
             }
           }
         }
       }
     }
   }
   rpc get-cb-active-error-information {
     description "Show active errors for CB";
     input {
       leaf slot {
         description "CB slot number";
         type union {
           type string {
             pattern "<.*>|$.*";
           }
           type uint32;
         }
         mandatory true;
       }
     }
     output {
       choice output-tags {
         case actual-tag {
           container active-error-information {
             uses active-error-information-block;
           }
         }
         case multichassis-tag {
           container multi-routing-engine-results {
             list multi-routing-engine-item {
               leaf re-name {
                 type string;
               }
               choice output-tags {
                 case actual-tag {
                   container active-error-information {
                     uses active-error-information-block;
                   }
                 }
               }
             }
           }
         }
       }
     }
   }
   rpc get-fan-active-error-information {
     description "Show active errors for FAN";
     input {
       leaf slot {
         description "FAN slot number";
         type union {
           type string {
             pattern "<.*>|$.*";
           }
           type uint32 {
             range "0 .. 6";
           }
         }
         mandatory true;
       }
     }
     output {
       choice output-tags {
         case actual-tag {
           container active-error-information {
             uses active-error-information-block;
           }
         }
         case multichassis-tag {
           container multi-routing-engine-results {
             list multi-routing-engine-item {
               leaf re-name {
                 type string;
               }
               choice output-tags {
                 case actual-tag {
                   container active-error-information {
                     uses active-error-information-block;
                   }
                 }
               }
             }
           }
         }
       }
     }
   }
   rpc get-psm-active-error-information {
     description "Show active errors for PSM";
     input {
       leaf slot {
         description "PSM slot number";
         type union {
           type string {
             pattern "<.*>|$.*";
           }
           type uint32;
         }
         mandatory true;
       }
     }
     output {
       choice output-tags {
         case actual-tag {
           container active-error-information {
             uses active-error-information-block;
           }
         }
         case multichassis-tag {
           container multi-routing-engine-results {
             list multi-routing-engine-item {
               leaf re-name {
                 type string;
               }
               choice output-tags {
                 case actual-tag {
                   container active-error-information {
                     uses active-error-information-block;
                   }
                 }
               }
             }
           }
         }
       }
     }
   }
   rpc get-fpm-active-error-information {
     description "Show active errors for FPM";
     input {
       leaf slot {
         description "FPM slot number";
         type union {
           type string {
             pattern "<.*>|$.*";
           }
           type uint32;
         }
         mandatory true;
       }
     }
     output {
       choice output-tags {
         case actual-tag {
           container active-error-information {
             uses active-error-information-block;
           }
         }
         case multichassis-tag {
           container multi-routing-engine-results {
             list multi-routing-engine-item {
               leaf re-name {
                 type string;
               }
               choice output-tags {
                 case actual-tag {
                   container active-error-information {
                     uses active-error-information-block;
                   }
                 }
               }
             }
           }
         }
       }
     }
   }
   rpc get-chassis-active-error-information {
     description "Show active errors for chassis";
     input {
       leaf slot {
         description "Chassis slot number";
         type union {
           type string {
             pattern "<.*>|$.*";
           }
           type uint32;
         }
         mandatory true;
       }
     }
     output {
       choice output-tags {
         case actual-tag {
           container active-error-information {
             uses active-error-information-block;
           }
         }
         case multichassis-tag {
           container multi-routing-engine-results {
             list multi-routing-engine-item {
               leaf re-name {
                 type string;
               }
               choice output-tags {
                 case actual-tag {
                   container active-error-information {
                     uses active-error-information-block;
                   }
                 }
               }
             }
           }
         }
       }
     }
   }
   rpc get-ftc-active-error-information {
     description "Show active errors for FTC";
     input {
       leaf slot {
         description "FTC slot number";
         type union {
           type string {
             pattern "<.*>|$.*";
           }
           type uint32;
         }
         mandatory true;
       }
     }
     output {
       choice output-tags {
         case actual-tag {
           container active-error-information {
             uses active-error-information-block;
           }
         }
         case multichassis-tag {
           container multi-routing-engine-results {
             list multi-routing-engine-item {
               leaf re-name {
                 type string;
               }
               choice output-tags {
                 case actual-tag {
                   container active-error-information {
                     uses active-error-information-block;
                   }
                 }
               }
             }
           }
         }
       }
     }
   }
   rpc get-pdu-active-error-information {
     description "Show active errors for PDU";
     input {
       leaf slot {
         description "PDU slot number";
         type union {
           type string {
             pattern "<.*>|$.*";
           }
           type uint32 {
             range "0 .. 3";
           }
         }
         mandatory true;
       }
     }
     output {
       choice output-tags {
         case actual-tag {
           container active-error-information {
             uses active-error-information-block;
           }
         }
         case multichassis-tag {
           container multi-routing-engine-results {
             list multi-routing-engine-item {
               leaf re-name {
                 type string;
               }
               choice output-tags {
                 case actual-tag {
                   container active-error-information {
                     uses active-error-information-block;
                   }
                 }
               }
             }
           }
         }
       }
     }
   }
   rpc get-active-error-detail-information {
     description "Show active errors detail";
     output {
       choice output-tags {
         case actual-tag {
           container active-error-detail-information {
             uses active-error-detail-information-block;
           }
         }
         case multichassis-tag {
           container multi-routing-engine-results {
             list multi-routing-engine-item {
               leaf re-name {
                 type string;
               }
               choice output-tags {
                 case actual-tag {
                   container active-error-detail-information {
                     uses active-error-detail-information-block;
                   }
                 }
               }
             }
           }
         }
       }
     }
   }
   rpc get-fpc-active-error-detail-information {
     description "Show active errors detail for FPC";
     input {
       leaf slot {
         description "FPC slot number";
         type union {
           type string {
             pattern "<.*>|$.*";
           }
           type uint32;
         }
         mandatory true;
       }
       leaf scope {
         description "Specify scope";
         type enumeration {
           enum "board" {
             description "Show board scope";
           }
           enum "pfe" {
             description "Show pfe scope";
           }
         }
       }
       leaf category {
         description "Specify category";
         type enumeration {
           enum "functional" {
             description "Show functional category";
           }
           enum "memory" {
             description "Show memory category";
           }
           enum "io" {
             description "Show io category";
           }
           enum "storage" {
             description "Show storage category";
           }
           enum "switch" {
             description "Show switch category";
           }
           enum "processing" {
             description "Show processing category";
           }
           enum "internal" {
             description "Show internal category";
           }
         }
       }
     }
     output {
       choice output-tags {
         case actual-tag {
           container active-error-detail-information {
             uses active-error-detail-information-block;
           }
         }
         case multichassis-tag {
           container multi-routing-engine-results {
             list multi-routing-engine-item {
               leaf re-name {
                 type string;
               }
               choice output-tags {
                 case actual-tag {
                   container active-error-detail-information {
                     uses active-error-detail-information-block;
                   }
                 }
               }
             }
           }
         }
       }
     }
   }
   rpc get-sib-active-error-detail-information {
     description "Show active errors detail for SIB";
     input {
       leaf slot {
         description "SIB slot number";
         type union {
           type string {
             pattern "<.*>|$.*";
           }
           type uint32;
         }
         mandatory true;
       }
       leaf scope {
         description "Specify scope";
         type enumeration {
           enum "board" {
             description "Show board scope";
           }
           enum "switch" {
             description "Show switch scope";
           }
         }
       }
       leaf category {
         description "Specify category";
         type enumeration {
           enum "functional" {
             description "Show functional category";
           }
           enum "memory" {
             description "Show memory category";
           }
           enum "io" {
             description "Show io category";
           }
           enum "storage" {
             description "Show storage category";
           }
           enum "switch" {
             description "Show switch category";
           }
           enum "processing" {
             description "Show processing category";
           }
           enum "internal" {
             description "Show internal category";
           }
         }
       }
     }
     output {
       choice output-tags {
         case actual-tag {
           container active-error-detail-information {
             uses active-error-detail-information-block;
           }
         }
         case multichassis-tag {
           container multi-routing-engine-results {
             list multi-routing-engine-item {
               leaf re-name {
                 type string;
               }
               choice output-tags {
                 case actual-tag {
                   container active-error-detail-information {
                     uses active-error-detail-information-block;
                   }
                 }
               }
             }
           }
         }
       }
     }
   }
   rpc get-feb-active-error-detail-information {
     description "Show active errors detail for FEB";
     input {
       leaf slot {
         description "FEB slot number";
         type union {
           type string {
             pattern "<.*>|$.*";
           }
           type uint32 {
             range "0 .. 1";
           }
         }
         mandatory true;
       }
       leaf scope {
         description "Specify scope";
         type enumeration {
           enum "board" {
             description "Show board scope";
           }
           enum "switch" {
             description "Show switch scope";
           }
         }
       }
       leaf category {
         description "Specify category";
         type enumeration {
           enum "functional" {
             description "Show functional category";
           }
           enum "memory" {
             description "Show memory category";
           }
           enum "io" {
             description "Show io category";
           }
           enum "storage" {
             description "Show storage category";
           }
           enum "switch" {
             description "Show switch category";
           }
           enum "processing" {
             description "Show processing category";
           }
           enum "internal" {
             description "Show internal category";
           }
         }
       }
     }
     output {
       choice output-tags {
         case actual-tag {
           container active-error-detail-information {
             uses active-error-detail-information-block;
           }
         }
         case multichassis-tag {
           container multi-routing-engine-results {
             list multi-routing-engine-item {
               leaf re-name {
                 type string;
               }
               choice output-tags {
                 case actual-tag {
                   container active-error-detail-information {
                     uses active-error-detail-information-block;
                   }
                 }
               }
             }
           }
         }
       }
     }
   }
   rpc get-re-active-error-detail-information {
     description "Show active errors detail for RE";
     input {
       leaf slot {
         description "RE slot number";
         type union {
           type string {
             pattern "<.*>|$.*";
           }
           type int32;
         }
         mandatory true;
       }
       leaf scope {
         description "Specify scope";
         type enumeration {
           enum "board" {
             description "Show board scope";
           }
         }
       }
       leaf category {
         description "Specify category";
         type enumeration {
           enum "functional" {
             description "Show functional category";
           }
           enum "memory" {
             description "Show memory category";
           }
           enum "io" {
             description "Show io category";
           }
           enum "storage" {
             description "Show storage category";
           }
           enum "switch" {
             description "Show switch category";
           }
           enum "processing" {
             description "Show processing category";
           }
           enum "internal" {
             description "Show internal category";
           }
         }
       }
     }
     output {
       choice output-tags {
         case actual-tag {
           container active-error-detail-information {
             uses active-error-detail-information-block;
           }
         }
         case multichassis-tag {
           container multi-routing-engine-results {
             list multi-routing-engine-item {
               leaf re-name {
                 type string;
               }
               choice output-tags {
                 case actual-tag {
                   container active-error-detail-information {
                     uses active-error-detail-information-block;
                   }
                 }
               }
             }
           }
         }
       }
     }
   }
   rpc get-inactive-error-information {
     description "Show inactive errors";
     output {
       choice output-tags {
         case actual-tag {
           container inactive-error-information {
             uses inactive-error-information-block;
           }
         }
         case multichassis-tag {
           container multi-routing-engine-results {
             list multi-routing-engine-item {
               leaf re-name {
                 type string;
               }
               choice output-tags {
                 case actual-tag {
                   container inactive-error-information {
                     uses inactive-error-information-block;
                   }
                 }
               }
             }
           }
         }
       }
     }
   }
   rpc get-fpc-inactive-error-information {
     description "Show inactive errors for FPC";
     input {
       leaf slot {
         description "FPC slot number";
         type union {
           type string {
             pattern "<.*>|$.*";
           }
           type uint32;
         }
         mandatory true;
       }
     }
     output {
       choice output-tags {
         case actual-tag {
           container inactive-error-information {
             uses inactive-error-information-block;
           }
         }
         case multichassis-tag {
           container multi-routing-engine-results {
             list multi-routing-engine-item {
               leaf re-name {
                 type string;
               }
               choice output-tags {
                 case actual-tag {
                   container inactive-error-information {
                     uses inactive-error-information-block;
                   }
                 }
               }
             }
           }
         }
       }
     }
   }
   rpc get-sib-inactive-error-information {
     description "Show inactive errors for SIB";
     input {
       leaf slot {
         description "SIB slot number";
         type union {
           type string {
             pattern "<.*>|$.*";
           }
           type uint32;
         }
         mandatory true;
       }
     }
     output {
       choice output-tags {
         case actual-tag {
           container inactive-error-information {
             uses inactive-error-information-block;
           }
         }
         case multichassis-tag {
           container multi-routing-engine-results {
             list multi-routing-engine-item {
               leaf re-name {
                 type string;
               }
               choice output-tags {
                 case actual-tag {
                   container inactive-error-information {
                     uses inactive-error-information-block;
                   }
                 }
               }
             }
           }
         }
       }
     }
   }
   rpc get-feb-inactive-error-information {
     description "Show inactive errors for FEB";
     input {
       leaf slot {
         description "FEB slot number";
         type union {
           type string {
             pattern "<.*>|$.*";
           }
           type uint32 {
             range "0 .. 1";
           }
         }
         mandatory true;
       }
     }
     output {
       choice output-tags {
         case actual-tag {
           container inactive-error-information {
             uses inactive-error-information-block;
           }
         }
         case multichassis-tag {
           container multi-routing-engine-results {
             list multi-routing-engine-item {
               leaf re-name {
                 type string;
               }
               choice output-tags {
                 case actual-tag {
                   container inactive-error-information {
                     uses inactive-error-information-block;
                   }
                 }
               }
             }
           }
         }
       }
     }
   }
   rpc get-re-inactive-error-information {
     description "Show inactive errors for RE";
     input {
       leaf slot {
         description "RE slot number";
         type union {
           type string {
             pattern "<.*>|$.*";
           }
           type int32;
         }
         mandatory true;
       }
     }
     output {
       choice output-tags {
         case actual-tag {
           container inactive-error-information {
             uses inactive-error-information-block;
           }
         }
         case multichassis-tag {
           container multi-routing-engine-results {
             list multi-routing-engine-item {
               leaf re-name {
                 type string;
               }
               choice output-tags {
                 case actual-tag {
                   container inactive-error-information {
                     uses inactive-error-information-block;
                   }
                 }
               }
             }
           }
         }
       }
     }
   }
   rpc get-cb-inactive-error-information {
     description "Show inactive errors for CB";
     input {
       leaf slot {
         description "CB slot number";
         type union {
           type string {
             pattern "<.*>|$.*";
           }
           type uint32;
         }
         mandatory true;
       }
     }
     output {
       choice output-tags {
         case actual-tag {
           container inactive-error-information {
             uses inactive-error-information-block;
           }
         }
         case multichassis-tag {
           container multi-routing-engine-results {
             list multi-routing-engine-item {
               leaf re-name {
                 type string;
               }
               choice output-tags {
                 case actual-tag {
                   container inactive-error-information {
                     uses inactive-error-information-block;
                   }
                 }
               }
             }
           }
         }
       }
     }
   }
   rpc get-fan-inactive-error-information {
     description "Show inactive errors for FAN";
     input {
       leaf slot {
         description "FAN slot number";
         type union {
           type string {
             pattern "<.*>|$.*";
           }
           type uint32 {
             range "0 .. 6";
           }
         }
         mandatory true;
       }
     }
     output {
       choice output-tags {
         case actual-tag {
           container inactive-error-information {
             uses inactive-error-information-block;
           }
         }
         case multichassis-tag {
           container multi-routing-engine-results {
             list multi-routing-engine-item {
               leaf re-name {
                 type string;
               }
               choice output-tags {
                 case actual-tag {
                   container inactive-error-information {
                     uses inactive-error-information-block;
                   }
                 }
               }
             }
           }
         }
       }
     }
   }
   rpc get-psm-inactive-error-information {
     description "Show inactive errors for PSM";
     input {
       leaf slot {
         description "PSM slot number";
         type union {
           type string {
             pattern "<.*>|$.*";
           }
           type uint32;
         }
         mandatory true;
       }
     }
     output {
       choice output-tags {
         case actual-tag {
           container inactive-error-information {
             uses inactive-error-information-block;
           }
         }
         case multichassis-tag {
           container multi-routing-engine-results {
             list multi-routing-engine-item {
               leaf re-name {
                 type string;
               }
               choice output-tags {
                 case actual-tag {
                   container inactive-error-information {
                     uses inactive-error-information-block;
                   }
                 }
               }
             }
           }
         }
       }
     }
   }
   rpc get-fpm-inactive-error-information {
     description "Show inactive errors for FPM";
     input {
       leaf slot {
         description "FPM slot number";
         type union {
           type string {
             pattern "<.*>|$.*";
           }
           type uint32;
         }
         mandatory true;
       }
     }
     output {
       choice output-tags {
         case actual-tag {
           container inactive-error-information {
             uses inactive-error-information-block;
           }
         }
         case multichassis-tag {
           container multi-routing-engine-results {
             list multi-routing-engine-item {
               leaf re-name {
                 type string;
               }
               choice output-tags {
                 case actual-tag {
                   container inactive-error-information {
                     uses inactive-error-information-block;
                   }
                 }
               }
             }
           }
         }
       }
     }
   }
   rpc get-chassis-inactive-error-information {
     description "Show inactive errors for chassis";
     input {
       leaf slot {
         description "Chassis slot number";
         type union {
           type string {
             pattern "<.*>|$.*";
           }
           type uint32;
         }
         mandatory true;
       }
     }
     output {
       choice output-tags {
         case actual-tag {
           container inactive-error-information {
             uses inactive-error-information-block;
           }
         }
         case multichassis-tag {
           container multi-routing-engine-results {
             list multi-routing-engine-item {
               leaf re-name {
                 type string;
               }
               choice output-tags {
                 case actual-tag {
                   container inactive-error-information {
                     uses inactive-error-information-block;
                   }
                 }
               }
             }
           }
         }
       }
     }
   }
   rpc get-ftc-inactive-error-information {
     description "Show inactive errors for FTC";
     input {
       leaf slot {
         description "FTC slot number";
         type union {
           type string {
             pattern "<.*>|$.*";
           }
           type uint32;
         }
         mandatory true;
       }
     }
     output {
       choice output-tags {
         case actual-tag {
           container inactive-error-information {
             uses inactive-error-information-block;
           }
         }
         case multichassis-tag {
           container multi-routing-engine-results {
             list multi-routing-engine-item {
               leaf re-name {
                 type string;
               }
               choice output-tags {
                 case actual-tag {
                   container inactive-error-information {
                     uses inactive-error-information-block;
                   }
                 }
               }
             }
           }
         }
       }
     }
   }
   rpc get-pdu-inactive-error-information {
     description "Show inactive errors for PDU";
     input {
       leaf slot {
         description "PDU slot number";
         type union {
           type string {
             pattern "<.*>|$.*";
           }
           type uint32 {
             range "0 .. 3";
           }
         }
         mandatory true;
       }
     }
     output {
       choice output-tags {
         case actual-tag {
           container inactive-error-information {
             uses inactive-error-information-block;
           }
         }
         case multichassis-tag {
           container multi-routing-engine-results {
             list multi-routing-engine-item {
               leaf re-name {
                 type string;
               }
               choice output-tags {
                 case actual-tag {
                   container inactive-error-information {
                     uses inactive-error-information-block;
                   }
                 }
               }
             }
           }
         }
       }
     }
   }
   rpc get-inactive-error-detail-information {
     description "Show inactive errors detail";
     output {
       choice output-tags {
         case actual-tag {
           container inactive-error-detail-information {
             uses inactive-error-detail-information-block;
           }
         }
         case multichassis-tag {
           container multi-routing-engine-results {
             list multi-routing-engine-item {
               leaf re-name {
                 type string;
               }
               choice output-tags {
                 case actual-tag {
                   container inactive-error-detail-information {
                     uses inactive-error-detail-information-block;
                   }
                 }
               }
             }
           }
         }
       }
     }
   }
   rpc get-fpc-inactive-error-detail-information {
     description "Show inactive errors detail for FPC";
     input {
       leaf slot {
         description "FPC slot number";
         type union {
           type string {
             pattern "<.*>|$.*";
           }
           type uint32;
         }
         mandatory true;
       }
       leaf scope {
         description "Specify scope";
         type enumeration {
           enum "board" {
             description "Show board scope";
           }
           enum "pfe" {
             description "Show pfe scope";
           }
         }
       }
       leaf category {
         description "Specify category";
         type enumeration {
           enum "functional" {
             description "Show functional category";
           }
           enum "memory" {
             description "Show memory category";
           }
           enum "io" {
             description "Show io category";
           }
           enum "storage" {
             description "Show storage category";
           }
           enum "switch" {
             description "Show switch category";
           }
           enum "processing" {
             description "Show processing category";
           }
           enum "internal" {
             description "Show internal category";
           }
         }
       }
     }
     output {
       choice output-tags {
         case actual-tag {
           container inactive-error-detail-information {
             uses inactive-error-detail-information-block;
           }
         }
         case multichassis-tag {
           container multi-routing-engine-results {
             list multi-routing-engine-item {
               leaf re-name {
                 type string;
               }
               choice output-tags {
                 case actual-tag {
                   container inactive-error-detail-information {
                     uses inactive-error-detail-information-block;
                   }
                 }
               }
             }
           }
         }
       }
     }
   }
   rpc get-sib-inactive-error-detail-information {
     description "Show inactive errors detail for SIB";
     input {
       leaf slot {
         description "SIB slot number";
         type union {
           type string {
             pattern "<.*>|$.*";
           }
           type uint32;
         }
         mandatory true;
       }
       leaf scope {
         description "Specify scope";
         type enumeration {
           enum "board" {
             description "Show board scope";
           }
           enum "switch" {
             description "Show switch scope";
           }
         }
       }
       leaf category {
         description "Specify category";
         type enumeration {
           enum "functional" {
             description "Show functional category";
           }
           enum "memory" {
             description "Show memory category";
           }
           enum "io" {
             description "Show io category";
           }
           enum "storage" {
             description "Show storage category";
           }
           enum "switch" {
             description "Show switch category";
           }
           enum "processing" {
             description "Show processing category";
           }
           enum "internal" {
             description "Show internal category";
           }
         }
       }
     }
     output {
       choice output-tags {
         case actual-tag {
           container inactive-error-detail-information {
             uses inactive-error-detail-information-block;
           }
         }
         case multichassis-tag {
           container multi-routing-engine-results {
             list multi-routing-engine-item {
               leaf re-name {
                 type string;
               }
               choice output-tags {
                 case actual-tag {
                   container inactive-error-detail-information {
                     uses inactive-error-detail-information-block;
                   }
                 }
               }
             }
           }
         }
       }
     }
   }
   rpc get-feb-inactive-error-detail-information {
     description "Show inactive errors detail for FEB";
     input {
       leaf slot {
         description "FEB slot number";
         type union {
           type string {
             pattern "<.*>|$.*";
           }
           type uint32 {
             range "0 .. 1";
           }
         }
         mandatory true;
       }
       leaf scope {
         description "Specify scope";
         type enumeration {
           enum "board" {
             description "Show board scope";
           }
           enum "switch" {
             description "Show switch scope";
           }
         }
       }
       leaf category {
         description "Specify category";
         type enumeration {
           enum "functional" {
             description "Show functional category";
           }
           enum "memory" {
             description "Show memory category";
           }
           enum "io" {
             description "Show io category";
           }
           enum "storage" {
             description "Show storage category";
           }
           enum "switch" {
             description "Show switch category";
           }
           enum "processing" {
             description "Show processing category";
           }
           enum "internal" {
             description "Show internal category";
           }
         }
       }
     }
     output {
       choice output-tags {
         case actual-tag {
           container inactive-error-detail-information {
             uses inactive-error-detail-information-block;
           }
         }
         case multichassis-tag {
           container multi-routing-engine-results {
             list multi-routing-engine-item {
               leaf re-name {
                 type string;
               }
               choice output-tags {
                 case actual-tag {
                   container inactive-error-detail-information {
                     uses inactive-error-detail-information-block;
                   }
                 }
               }
             }
           }
         }
       }
     }
   }
   rpc get-re-inactive-error-detail-information {
     description "Show inactive errors detail for RE";
     input {
       leaf slot {
         description "RE slot number";
         type union {
           type string {
             pattern "<.*>|$.*";
           }
           type int32;
         }
         mandatory true;
       }
       leaf scope {
         description "Specify scope";
         type enumeration {
           enum "board" {
             description "Show board scope";
           }
         }
       }
       leaf category {
         description "Specify category";
         type enumeration {
           enum "functional" {
             description "Show functional category";
           }
           enum "memory" {
             description "Show memory category";
           }
           enum "io" {
             description "Show io category";
           }
           enum "storage" {
             description "Show storage category";
           }
           enum "switch" {
             description "Show switch category";
           }
           enum "processing" {
             description "Show processing category";
           }
           enum "internal" {
             description "Show internal category";
           }
         }
       }
     }
     output {
       choice output-tags {
         case actual-tag {
           container inactive-error-detail-information {
             uses inactive-error-detail-information-block;
           }
         }
         case multichassis-tag {
           container multi-routing-engine-results {
             list multi-routing-engine-item {
               leaf re-name {
                 type string;
               }
               choice output-tags {
                 case actual-tag {
                   container inactive-error-detail-information {
                     uses inactive-error-detail-information-block;
                   }
                 }
               }
             }
           }
         }
       }
     }
   }
   rpc get-active-fru-error-information {
     description "Show fru error information";
     output {
       choice output-tags {
         case actual-tag {
           container active-fru-error-information {
             uses active-fru-error-information-block;
           }
         }
         case multichassis-tag {
           container multi-routing-engine-results {
             list multi-routing-engine-item {
               leaf re-name {
                 type string;
               }
               choice output-tags {
                 case actual-tag {
                   container active-fru-error-information {
                     uses active-fru-error-information-block;
                   }
                 }
               }
             }
           }
         }
       }
     }
   }
   rpc get-active-fru-error-detail-information {
     description "Show fru error information in detail";
     output {
       choice output-tags {
         case actual-tag {
           container active-fru-error-detail-information {
             uses active-fru-error-detail-information-block;
           }
         }
         case multichassis-tag {
           container multi-routing-engine-results {
             list multi-routing-engine-item {
               leaf re-name {
                 type string;
               }
               choice output-tags {
                 case actual-tag {
                   container active-fru-error-detail-information {
                     uses active-fru-error-detail-information-block;
                   }
                 }
               }
             }
           }
         }
       }
     }
   }
   rpc get-fpc-active-fru-error-detail-information {
     description "Show active errors for FPC";
     input {
       leaf slot {
         description "FPC slot number";
         type union {
           type string {
             pattern "<.*>|$.*";
           }
           type uint32;
         }
         mandatory true;
       }
     }
     output {
       choice output-tags {
         case actual-tag {
           container active-fru-error-detail-information {
             uses active-fru-error-detail-information-block;
           }
         }
         case multichassis-tag {
           container multi-routing-engine-results {
             list multi-routing-engine-item {
               leaf re-name {
                 type string;
               }
               choice output-tags {
                 case actual-tag {
                   container active-fru-error-detail-information {
                     uses active-fru-error-detail-information-block;
                   }
                 }
               }
             }
           }
         }
       }
     }
   }
   rpc get-sib-active-fru-error-detail-information {
     description "Show active errors for SIB";
     input {
       leaf slot {
         description "SIB slot number";
         type union {
           type string {
             pattern "<.*>|$.*";
           }
           type uint32;
         }
         mandatory true;
       }
     }
     output {
       choice output-tags {
         case actual-tag {
           container active-fru-error-detail-information {
             uses active-fru-error-detail-information-block;
           }
         }
         case multichassis-tag {
           container multi-routing-engine-results {
             list multi-routing-engine-item {
               leaf re-name {
                 type string;
               }
               choice output-tags {
                 case actual-tag {
                   container active-fru-error-detail-information {
                     uses active-fru-error-detail-information-block;
                   }
                 }
               }
             }
           }
         }
       }
     }
   }
   rpc get-feb-active-fru-error-detail-information {
     description "Show active errors for FEB";
     input {
       leaf slot {
         description "FEB slot number";
         type union {
           type string {
             pattern "<.*>|$.*";
           }
           type uint32 {
             range "0 .. 1";
           }
         }
         mandatory true;
       }
     }
     output {
       choice output-tags {
         case actual-tag {
           container active-fru-error-detail-information {
             uses active-fru-error-detail-information-block;
           }
         }
         case multichassis-tag {
           container multi-routing-engine-results {
             list multi-routing-engine-item {
               leaf re-name {
                 type string;
               }
               choice output-tags {
                 case actual-tag {
                   container active-fru-error-detail-information {
                     uses active-fru-error-detail-information-block;
                   }
                 }
               }
             }
           }
         }
       }
     }
   }
   rpc get-re-active-fru-error-detail-information {
     description "Show active errors for RE";
     input {
       leaf slot {
         description "RE slot number";
         type union {
           type string {
             pattern "<.*>|$.*";
           }
           type int32;
         }
         mandatory true;
       }
     }
     output {
       choice output-tags {
         case actual-tag {
           container active-fru-error-detail-information {
             uses active-fru-error-detail-information-block;
           }
         }
         case multichassis-tag {
           container multi-routing-engine-results {
             list multi-routing-engine-item {
               leaf re-name {
                 type string;
               }
               choice output-tags {
                 case actual-tag {
                   container active-fru-error-detail-information {
                     uses active-fru-error-detail-information-block;
                   }
                 }
               }
             }
           }
         }
       }
     }
   }
   rpc get-cb-active-fru-error-detail-information {
     description "Show active errors for CB";
     input {
       leaf slot {
         description "CB slot number";
         type union {
           type string {
             pattern "<.*>|$.*";
           }
           type uint32;
         }
         mandatory true;
       }
     }
     output {
       choice output-tags {
         case actual-tag {
           container active-fru-error-detail-information {
             uses active-fru-error-detail-information-block;
           }
         }
         case multichassis-tag {
           container multi-routing-engine-results {
             list multi-routing-engine-item {
               leaf re-name {
                 type string;
               }
               choice output-tags {
                 case actual-tag {
                   container active-fru-error-detail-information {
                     uses active-fru-error-detail-information-block;
                   }
                 }
               }
             }
           }
         }
       }
     }
   }
   rpc get-fan-active-fru-error-detail-information {
     description "Show active errors for FAN";
     input {
       leaf slot {
         description "FAN slot number";
         type union {
           type string {
             pattern "<.*>|$.*";
           }
           type uint32 {
             range "0 .. 6";
           }
         }
         mandatory true;
       }
     }
     output {
       choice output-tags {
         case actual-tag {
           container active-fru-error-detail-information {
             uses active-fru-error-detail-information-block;
           }
         }
         case multichassis-tag {
           container multi-routing-engine-results {
             list multi-routing-engine-item {
               leaf re-name {
                 type string;
               }
               choice output-tags {
                 case actual-tag {
                   container active-fru-error-detail-information {
                     uses active-fru-error-detail-information-block;
                   }
                 }
               }
             }
           }
         }
       }
     }
   }
   rpc get-psm-active-fru-error-detail-information {
     description "Show active errors for PSM";
     input {
       leaf slot {
         description "PSM slot number";
         type union {
           type string {
             pattern "<.*>|$.*";
           }
           type uint32;
         }
         mandatory true;
       }
     }
     output {
       choice output-tags {
         case actual-tag {
           container active-fru-error-detail-information {
             uses active-fru-error-detail-information-block;
           }
         }
         case multichassis-tag {
           container multi-routing-engine-results {
             list multi-routing-engine-item {
               leaf re-name {
                 type string;
               }
               choice output-tags {
                 case actual-tag {
                   container active-fru-error-detail-information {
                     uses active-fru-error-detail-information-block;
                   }
                 }
               }
             }
           }
         }
       }
     }
   }
   rpc get-fpm-active-fru-error-detail-information {
     description "Show active errors for FPM";
     input {
       leaf slot {
         description "FPM slot number";
         type union {
           type string {
             pattern "<.*>|$.*";
           }
           type uint32;
         }
         mandatory true;
       }
     }
     output {
       choice output-tags {
         case actual-tag {
           container active-fru-error-detail-information {
             uses active-fru-error-detail-information-block;
           }
         }
         case multichassis-tag {
           container multi-routing-engine-results {
             list multi-routing-engine-item {
               leaf re-name {
                 type string;
               }
               choice output-tags {
                 case actual-tag {
                   container active-fru-error-detail-information {
                     uses active-fru-error-detail-information-block;
                   }
                 }
               }
             }
           }
         }
       }
     }
   }
   rpc get-chassis-active-fru-error-detail-information {
     description "Show active errors for chassis";
     input {
       leaf slot {
         description "Chassis slot number";
         type union {
           type string {
             pattern "<.*>|$.*";
           }
           type uint32;
         }
         mandatory true;
       }
     }
     output {
       choice output-tags {
         case actual-tag {
           container active-fru-error-detail-information {
             uses active-fru-error-detail-information-block;
           }
         }
         case multichassis-tag {
           container multi-routing-engine-results {
             list multi-routing-engine-item {
               leaf re-name {
                 type string;
               }
               choice output-tags {
                 case actual-tag {
                   container active-fru-error-detail-information {
                     uses active-fru-error-detail-information-block;
                   }
                 }
               }
             }
           }
         }
       }
     }
   }
   rpc get-ftc-active-fru-error-detail-information {
     description "Show active errors for FTC";
     input {
       leaf slot {
         description "FTC slot number";
         type union {
           type string {
             pattern "<.*>|$.*";
           }
           type uint32;
         }
         mandatory true;
       }
     }
     output {
       choice output-tags {
         case actual-tag {
           container active-fru-error-detail-information {
             uses active-fru-error-detail-information-block;
           }
         }
         case multichassis-tag {
           container multi-routing-engine-results {
             list multi-routing-engine-item {
               leaf re-name {
                 type string;
               }
               choice output-tags {
                 case actual-tag {
                   container active-fru-error-detail-information {
                     uses active-fru-error-detail-information-block;
                   }
                 }
               }
             }
           }
         }
       }
     }
   }
   rpc get-pdu-active-fru-error-detail-information {
     description "Show active errors for PDU";
     input {
       leaf slot {
         description "PDU slot number";
         type union {
           type string {
             pattern "<.*>|$.*";
           }
           type uint32 {
             range "0 .. 3";
           }
         }
         mandatory true;
       }
     }
     output {
       choice output-tags {
         case actual-tag {
           container active-fru-error-detail-information {
             uses active-fru-error-detail-information-block;
           }
         }
         case multichassis-tag {
           container multi-routing-engine-results {
             list multi-routing-engine-item {
               leaf re-name {
                 type string;
               }
               choice output-tags {
                 case actual-tag {
                   container active-fru-error-detail-information {
                     uses active-fru-error-detail-information-block;
                   }
                 }
               }
             }
           }
         }
       }
     }
   }
   rpc get-active-fru-error-id-information {
     description "Show error information by error-id";
     input {
       leaf id {
         description "URI for the error";
         type string {
           length "1 .. 255";
         }
         mandatory true;
       }
     }
     output {
       choice output-tags {
         case actual-tag {
           container active-fru-error-id-information {
             uses active-fru-error-id-information-block;
           }
         }
         case multichassis-tag {
           container multi-routing-engine-results {
             list multi-routing-engine-item {
               leaf re-name {
                 type string;
               }
               choice output-tags {
                 case actual-tag {
                   container active-fru-error-id-information {
                     uses active-fru-error-id-information-block;
                   }
                 }
               }
             }
           }
         }
       }
     }
   }
   rpc get-system-error-information-fpc {
     description "Show system error status for FPC";
     input {
       leaf slot {
         description "FPC slot number";
         type union {
           type string {
             pattern "<.*>|$.*";
           }
           type uint32;
         }
         mandatory true;
       }
     }
     output {
       choice output-tags {
         case actual-tag {
           container system-error-information {
             uses system-error-information-block;
           }
         }
         case multichassis-tag {
           container multi-routing-engine-results {
             list multi-routing-engine-item {
               leaf re-name {
                 type string;
               }
               choice output-tags {
                 case actual-tag {
                   container system-error-information {
                     uses system-error-information-block;
                   }
                 }
               }
             }
           }
         }
       }
     }
   }
   rpc get-system-error-information-sib {
     description "Show system error status for SIB";
     input {
       leaf slot {
         description "SIB slot number";
         type union {
           type string {
             pattern "<.*>|$.*";
           }
           type uint32;
         }
         mandatory true;
       }
     }
     output {
       choice output-tags {
         case actual-tag {
           container system-error-information {
             uses system-error-information-block;
           }
         }
         case multichassis-tag {
           container multi-routing-engine-results {
             list multi-routing-engine-item {
               leaf re-name {
                 type string;
               }
               choice output-tags {
                 case actual-tag {
                   container system-error-information {
                     uses system-error-information-block;
                   }
                 }
               }
             }
           }
         }
       }
     }
   }
   rpc get-system-error-information-cb {
     description "Show system error status for CB";
     input {
       leaf slot {
         description "CB slot number";
         type union {
           type string {
             pattern "<.*>|$.*";
           }
           type uint32;
         }
         mandatory true;
       }
     }
     output {
       choice output-tags {
         case actual-tag {
           container system-error-information {
             uses system-error-information-block;
           }
         }
         case multichassis-tag {
           container multi-routing-engine-results {
             list multi-routing-engine-item {
               leaf re-name {
                 type string;
               }
               choice output-tags {
                 case actual-tag {
                   container system-error-information {
                     uses system-error-information-block;
                   }
                 }
               }
             }
           }
         }
       }
     }
   }
   rpc get-system-error-information-fan {
     description "Show system error status for Fan";
     input {
       leaf slot {
         description "Fantray slot number";
         type union {
           type string {
             pattern "<.*>|$.*";
           }
           type uint32;
         }
         mandatory true;
       }
     }
     output {
       choice output-tags {
         case actual-tag {
           container system-error-information {
             uses system-error-information-block;
           }
         }
         case multichassis-tag {
           container multi-routing-engine-results {
             list multi-routing-engine-item {
               leaf re-name {
                 type string;
               }
               choice output-tags {
                 case actual-tag {
                   container system-error-information {
                     uses system-error-information-block;
                   }
                 }
               }
             }
           }
         }
       }
     }
   }
   rpc get-system-error-information-psm {
     description "Show system error status for PSM";
     input {
       leaf slot {
         description "PSM slot number";
         type union {
           type string {
             pattern "<.*>|$.*";
           }
           type uint32;
         }
         mandatory true;
       }
     }
     output {
       choice output-tags {
         case actual-tag {
           container system-error-information {
             uses system-error-information-block;
           }
         }
         case multichassis-tag {
           container multi-routing-engine-results {
             list multi-routing-engine-item {
               leaf re-name {
                 type string;
               }
               choice output-tags {
                 case actual-tag {
                   container system-error-information {
                     uses system-error-information-block;
                   }
                 }
               }
             }
           }
         }
       }
     }
   }
   rpc get-system-error-information-ccg {
     description "Show system error status for CCG";
     input {
       leaf slot {
         description "CCG slot number";
         type union {
           type string {
             pattern "<.*>|$.*";
           }
           type uint32 {
             range "0 .. 1";
           }
         }
         mandatory true;
       }
     }
     output {
       choice output-tags {
         case actual-tag {
           container system-error-information {
             uses system-error-information-block;
           }
         }
         case multichassis-tag {
           container multi-routing-engine-results {
             list multi-routing-engine-item {
               leaf re-name {
                 type string;
               }
               choice output-tags {
                 case actual-tag {
                   container system-error-information {
                     uses system-error-information-block;
                   }
                 }
               }
             }
           }
         }
       }
     }
   }
   rpc get-system-error-information-re {
     description "Show system error status for RE";
     input {
       leaf slot {
         description "RE slot number";
         type union {
           type string {
             pattern "<.*>|$.*";
           }
           type int32;
         }
         mandatory true;
       }
     }
     output {
       choice output-tags {
         case actual-tag {
           container system-error-information {
             uses system-error-information-block;
           }
         }
         case multichassis-tag {
           container multi-routing-engine-results {
             list multi-routing-engine-item {
               leaf re-name {
                 type string;
               }
               choice output-tags {
                 case actual-tag {
                   container system-error-information {
                     uses system-error-information-block;
                   }
                 }
               }
             }
           }
         }
       }
     }
   }
   rpc get-system-error-history {
     description "Show system error history";
     output {
       choice output-tags {
         case actual-tag {
           container system-error-history {
             uses system-error-history-block;
           }
         }
         case multichassis-tag {
           container multi-routing-engine-results {
             list multi-routing-engine-item {
               leaf re-name {
                 type string;
               }
               choice output-tags {
                 case actual-tag {
                   container system-error-history {
                     uses system-error-history-block;
                   }
                 }
               }
             }
           }
         }
       }
     }
   }
   rpc get-system-error-history-fpc {
     description "Show system error history for FPC";
     input {
       leaf slot {
         description "FPC slot number";
         type union {
           type string {
             pattern "<.*>|$.*";
           }
           type uint32;
         }
         mandatory true;
       }
     }
     output {
       choice output-tags {
         case actual-tag {
           container system-error-history {
             uses system-error-history-block;
           }
         }
         case multichassis-tag {
           container multi-routing-engine-results {
             list multi-routing-engine-item {
               leaf re-name {
                 type string;
               }
               choice output-tags {
                 case actual-tag {
                   container system-error-history {
                     uses system-error-history-block;
                   }
                 }
               }
             }
           }
         }
       }
     }
   }
   rpc get-system-error-history-sib {
     description "Show system error history for SIB";
     input {
       leaf slot {
         description "SIB slot number";
         type union {
           type string {
             pattern "<.*>|$.*";
           }
           type uint32;
         }
         mandatory true;
       }
     }
     output {
       choice output-tags {
         case actual-tag {
           container system-error-history {
             uses system-error-history-block;
           }
         }
         case multichassis-tag {
           container multi-routing-engine-results {
             list multi-routing-engine-item {
               leaf re-name {
                 type string;
               }
               choice output-tags {
                 case actual-tag {
                   container system-error-history {
                     uses system-error-history-block;
                   }
                 }
               }
             }
           }
         }
       }
     }
   }
   rpc get-system-error-history-cb {
     description "Show system error history for CB";
     input {
       leaf slot {
         description "CB slot number";
         type union {
           type string {
             pattern "<.*>|$.*";
           }
           type uint32;
         }
         mandatory true;
       }
     }
     output {
       choice output-tags {
         case actual-tag {
           container system-error-history {
             uses system-error-history-block;
           }
         }
         case multichassis-tag {
           container multi-routing-engine-results {
             list multi-routing-engine-item {
               leaf re-name {
                 type string;
               }
               choice output-tags {
                 case actual-tag {
                   container system-error-history {
                     uses system-error-history-block;
                   }
                 }
               }
             }
           }
         }
       }
     }
   }
   rpc get-system-error-history-fan {
     description "Show system error history for Fan";
     input {
       leaf slot {
         description "Fantray slot number";
         type union {
           type string {
             pattern "<.*>|$.*";
           }
           type uint32;
         }
         mandatory true;
       }
     }
     output {
       choice output-tags {
         case actual-tag {
           container system-error-history {
             uses system-error-history-block;
           }
         }
         case multichassis-tag {
           container multi-routing-engine-results {
             list multi-routing-engine-item {
               leaf re-name {
                 type string;
               }
               choice output-tags {
                 case actual-tag {
                   container system-error-history {
                     uses system-error-history-block;
                   }
                 }
               }
             }
           }
         }
       }
     }
   }
   rpc get-system-error-history-psm {
     description "Show system error history for PSM";
     input {
       leaf slot {
         description "PSM slot number";
         type union {
           type string {
             pattern "<.*>|$.*";
           }
           type uint32;
         }
         mandatory true;
       }
     }
     output {
       choice output-tags {
         case actual-tag {
           container system-error-history {
             uses system-error-history-block;
           }
         }
         case multichassis-tag {
           container multi-routing-engine-results {
             list multi-routing-engine-item {
               leaf re-name {
                 type string;
               }
               choice output-tags {
                 case actual-tag {
                   container system-error-history {
                     uses system-error-history-block;
                   }
                 }
               }
             }
           }
         }
       }
     }
   }
   rpc get-system-error-history-ccg {
     description "Show system error history for CCG";
     input {
       leaf slot {
         description "CCG slot number";
         type union {
           type string {
             pattern "<.*>|$.*";
           }
           type uint32 {
             range "0 .. 1";
           }
         }
         mandatory true;
       }
     }
     output {
       choice output-tags {
         case actual-tag {
           container system-error-history {
             uses system-error-history-block;
           }
         }
         case multichassis-tag {
           container multi-routing-engine-results {
             list multi-routing-engine-item {
               leaf re-name {
                 type string;
               }
               choice output-tags {
                 case actual-tag {
                   container system-error-history {
                     uses system-error-history-block;
                   }
                 }
               }
             }
           }
         }
       }
     }
   }
   rpc get-system-error-history-re {
     description "Show system error history for RE";
     input {
       leaf slot {
         description "RE slot number";
         type union {
           type string {
             pattern "<.*>|$.*";
           }
           type int32;
         }
         mandatory true;
       }
     }
     output {
       choice output-tags {
         case actual-tag {
           container system-error-history {
             uses system-error-history-block;
           }
         }
         case multichassis-tag {
           container multi-routing-engine-results {
             list multi-routing-engine-item {
               leaf re-name {
                 type string;
               }
               choice output-tags {
                 case actual-tag {
                   container system-error-history {
                     uses system-error-history-block;
                   }
                 }
               }
             }
           }
         }
       }
     }
   }
   rpc get-health-mon-information {
     description "Show health monitoring parameters";
     output {
       choice output-tags {
         case actual-tag {
           container health-mon-information {
             uses health-mon-information-block;
           }
         }
         case multichassis-tag {
           container multi-routing-engine-results {
             list multi-routing-engine-item {
               leaf re-name {
                 type string;
               }
               choice output-tags {
                 case actual-tag {
                   container health-mon-information {
                     uses health-mon-information-block;
                   }
                 }
               }
             }
           }
         }
       }
     }
   }
   rpc get-health-mon-fpc-information {
     description "Health parameters for FPC";
     input {
       leaf fpc-slot {
         description "FPC slot number";
         type union {
           type string {
             pattern "<.*>|$.*";
           }
           type uint32;
         }
         mandatory true;
       }
     }
     output {
       choice output-tags {
         case output-tag {
           leaf output {
             type string;
           }
         }
         case actual-tag {
           anyxml health-mon-fpc-information;
         }
         case multichassis-tag {
           anyxml multi-routing-engine-results;
         }
       }
     }
   }
   rpc get-boot-console-information {
     description "Show boot console port information";
     input {
       uses command-forwarding;
     }
     output {
       choice output-tags {
         case output-tag {
           leaf output {
             type string;
           }
         }
         case multichassis-tag {
           anyxml multi-routing-engine-results;
         }
       }
     }
   }
   rpc get-buffer-informations {
     description "Show buffer statistics";
     input {
       uses command-forwarding;
     }
     output {
       choice output-tags {
         case actual-tag {
           container memory-statistics {
             uses memory-statistics-block;
           }
         }
         case multichassis-tag {
           container multi-routing-engine-results {
             list multi-routing-engine-item {
               leaf re-name {
                 type string;
               }
               choice output-tags {
                 case actual-tag {
                   container memory-statistics {
                     uses memory-statistics-block;
                   }
                 }
               }
             }
           }
         }
       }
     }
   }
   rpc get-queues-information {
     description "Show queue statistics";
     input {
       uses command-forwarding;
     }
     output {
       choice output-tags {
         case actual-tag {
           container queues-statistics {
             uses queues-statistics-block;
           }
         }
         case multichassis-tag {
           container multi-routing-engine-results {
             list multi-routing-engine-item {
               leaf re-name {
                 type string;
               }
               choice output-tags {
                 case actual-tag {
                   container queues-statistics {
                     uses queues-statistics-block;
                   }
                 }
               }
             }
           }
         }
       }
     }
   }
   rpc get-directory-usage-information {
     description "Show local directory information";
     input {
       uses command-forwarding;
       leaf path {
         description "Path of root directory to traverse";
         type string;
       }
       leaf depth {
         description "Depth of directories to traverse";
         type union {
           type uint32;
           type string {
             pattern "<.*>|$.*";
           }
         }
       }
     }
     output {
       choice output-tags {
         case actual-tag {
           container directory-usage-information {
             uses directory-usage-information-block;
           }
         }
         case multichassis-tag {
           container multi-routing-engine-results {
             list multi-routing-engine-item {
               leaf re-name {
                 type string;
               }
               choice output-tags {
                 case actual-tag {
                   container directory-usage-information {
                     uses directory-usage-information-block;
                   }
                 }
               }
             }
           }
         }
       }
     }
   }
   rpc get-auto-snapshot-information {
     description "Show auto-snapshot status when system booted from alternate slice";
     input {
       uses command-forwarding;
     }
     output {
       choice output-tags {
         case actual-tag {
           container auto-snapshot-information {
             uses auto-snapshot-information-block;
           }
         }
         case multichassis-tag {
           container multi-routing-engine-results {
             list multi-routing-engine-item {
               leaf re-name {
                 type string;
               }
               choice output-tags {
                 case actual-tag {
                   container auto-snapshot-information {
                     uses auto-snapshot-information-block;
                   }
                 }
               }
             }
           }
         }
       }
     }
   }
   rpc get-snapshot-information {
     description "Show snapshot information";
     input {
       uses command-forwarding;
       leaf slice {
         description "Show snapshot information from specified partition";
         status deprecated;
         type enumeration {
           enum "1" {
             description "Show snapshot information from first partition";
             status deprecated;
           }
           enum "2" {
             description "Show snapshot information from second partition";
             status deprecated;
           }
           enum "alternate" {
             description "Show snapshot information from alternate partition";
             status deprecated;
           }
         }
       }
       leaf media {
         description "Media to show snapshot information from";
         type enumeration {
           enum "removable-compact-flash" {
             description "Show snapshot information from removable compact flash";
           }
           enum "compact-flash" {
             description "Show snapshot information from compact flash";
           }
           enum "usb" {
             description "Show snapshot information from device connected to USB port";
           }
           enum "usb0" {
             description "Show snapshot information from device connected to USB0";
           }
           enum "usb1" {
             description "Show snapshot information from device connected to USB1";
           }
           enum "hard-disk" {
             description "Show snapshot information from hard disk";
           }
           enum "internal" {
             description "Show snapshot information from internal flash";
           }
           enum "external" {
             description "Show snapshot information from external flash";
           }
         }
       }
     }
     output {
       choice output-tags {
         case actual-tag {
           container snapshot-information {
             uses snapshot-information-block;
           }
         }
         case multichassis-tag {
           container multi-routing-engine-results {
             list multi-routing-engine-item {
               leaf re-name {
                 type string;
               }
               choice output-tags {
                 case actual-tag {
                   container snapshot-information {
                     uses snapshot-information-block;
                   }
                 }
               }
             }
           }
         }
       }
     }
   }
   rpc get-system-process-information {
     description "Show system process table";
     input {
       uses command-forwarding;
       leaf detail {
         description "Display detailed output";
         type empty;
       }
       leaf wide {
         description "Display information even if wider than 80 columns";
         type empty;
       }
     }
     output {
       choice output-tags {
         case output-tag {
           leaf output {
             type string;
           }
         }
         case multichassis-tag {
           anyxml multi-routing-engine-results;
         }
       }
     }
   }
   rpc get-system-process-brief-information {
     description "Display brief output";
     input {
       uses command-forwarding;
     }
     output {
       choice output-tags {
         case output-tag {
           leaf output {
             type string;
           }
         }
         case multichassis-tag {
           anyxml multi-routing-engine-results;
         }
       }
     }
   }
   rpc get-process-health-information {
     description "Show process health information";
     input {
       choice name_pid_choice {
         case process-name {
           leaf process-name {
             description "Process name";
             type string;
           }
         }
         case pid {
           leaf pid {
             description "Process identifier";
             type union {
               type string {
                 pattern "<.*>|$.*";
               }
               type uint32 {
                 range "1 .. 99999";
               }
             }
           }
         }
       }
     }
     output {
       choice output-tags {
         case output-tag {
           leaf output {
             type string;
           }
         }
         case actual-tag {
           anyxml system-processes-health-information;
         }
         case multichassis-tag {
           anyxml multi-routing-engine-results;
         }
       }
     }
   }
   rpc get-system-process-resource-limits {
     description "Show process resource limits";
     input {
       leaf process-name {
         description "Process name";
         type string;
       }
       leaf verbosity_level {
         default "brief";
         type enumeration {
           enum "brief" {
             description "Display brief output (default)";
           }
           enum "detail" {
             description "Display detailed output";
           }
         }
       }
     }
     output {
       choice output-tags {
         case output-tag {
           leaf output {
             type string;
           }
         }
         case actual-tag {
           anyxml secpolinfo-policy-information;
         }
         case multichassis-tag {
           anyxml multi-routing-engine-results;
         }
       }
     }
   }
   rpc get-statistics-information {
     description "Show statistics for protocol";
     input {
       uses command-forwarding;
       leaf subsystem {
         description "Name of the subsystem";
         type string;
         mandatory true;
       }
       leaf protocol {
         type enumeration {
           enum "ip" {
             description "IP version 4 (IPv4)";
           }
           enum "ip6" {
             description "IP version 6 (IPv6)";
           }
           enum "icmp" {
             description "Internet Control Message Protocol";
           }
           enum "nd6" {
             description "Internet Control Message Protocol for IPv6";
           }
           enum "icmp6" {
             description "Internet Control Message Protocol for IPv6";
           }
           enum "tcp" {
             description "Transmission Control Protocol";
           }
           enum "sctp" {
             description "Stream Control Transmission Protocol";
           }
           enum "udp" {
             description "User Datagram Protocol";
           }
           enum "igmp" {
             description "Internet Gateway Management Protocol";
           }
           enum "arp" {
             description "Address Resolution Protocol";
           }
           enum "clns" {
             description "Connectionless Network Service";
           }
           enum "esis" {
             description "End System-to-Intermediate System";
           }
           enum "tnp" {
             description "Trivial Network Protocol";
           }
           enum "rdp" {
             description "Reliable Datagram Protocol";
           }
           enum "ttp" {
             description "TNP Tunneling Protocol";
           }
           enum "tudp" {
             description "Trivial User Datagram Protocol";
           }
           enum "mpls" {
             description "Multiprotocol Label Switching";
           }
           enum "ethoamcfm" {
             description "Ethernet OAM protocol for connectivity fault management";
           }
           enum "ethoamlfm" {
             description "Ethernet OAM protocol for link fault management";
           }
           enum "jsr" {
             description "Juniper Socket Replication";
           }
           enum "jtd" {
             description "Juniper Tunnel Driver";
           }
         }
       }
       leaf backup {
         description "Statistics of backup JunosVM";
         type empty;
       }
     }
     output {
       choice output-tags {
         case actual-tag {
           container statistics {
             uses statistics-block;
           }
         }
         case multichassis-tag {
           container multi-routing-engine-results {
             list multi-routing-engine-item {
               leaf re-name {
                 type string;
               }
               choice output-tags {
                 case actual-tag {
                   container statistics {
                     uses statistics-block;
                   }
                 }
               }
             }
           }
         }
       }
     }
   }
   rpc get-system-netisr-system-statistics {
     description "Netisr statistics";
     input {
       uses command-forwarding;
       leaf packet-path {
         type enumeration {
           enum "qdrops" {
             description "Total packet path drop";
           }
           enum "per-priority-stats" {
             description "Netisr statistics at priority level";
           }
           enum "socket-drops" {
             description "Netisr socket drops";
           }
         }
       }
     }
     output {
       choice output-tags {
         case actual-tag {
           container statistics {
             uses statistics-block;
           }
         }
         case multichassis-tag {
           container multi-routing-engine-results {
             list multi-routing-engine-item {
               leaf re-name {
                 type string;
               }
               choice output-tags {
                 case actual-tag {
                   container statistics {
                     uses statistics-block;
                   }
                 }
               }
             }
           }
         }
       }
     }
   }
   rpc get-system-vpls-statistics {
     description "Virtual private LAN service";
     input {
       uses command-forwarding;
     }
     output {
       choice output-tags {
         case actual-tag {
           container statistics {
             uses statistics-block;
           }
         }
         case multichassis-tag {
           container multi-routing-engine-results {
             list multi-routing-engine-item {
               leaf re-name {
                 type string;
               }
               choice output-tags {
                 case actual-tag {
                   container statistics {
                     uses statistics-block;
                   }
                 }
               }
             }
           }
         }
       }
     }
   }
   rpc get-system-bridge-statistics {
     description "IEEE 802.1 Bridging";
     input {
       uses command-forwarding;
     }
     output {
       choice output-tags {
         case actual-tag {
           container statistics {
             uses statistics-block;
           }
         }
         case multichassis-tag {
           container multi-routing-engine-results {
             list multi-routing-engine-item {
               leaf re-name {
                 type string;
               }
               choice output-tags {
                 case actual-tag {
                   container statistics {
                     uses statistics-block;
                   }
                 }
               }
             }
           }
         }
       }
     }
   }
   rpc get-system-stats-extended {
     description "System wide statistics";
     input {
       leaf protocol {
         description "Show sysstem statistics extended protocol";
         type enumeration {
           enum "ipv4" {
             description "Display ipv4 sysstem statistics";
           }
           enum "ipv6" {
             description "Display ipv6 sysstem statistics";
           }
         }
       }
     }
     output {
       choice output-tags {
         case actual-tag {
           container extended-system-stats {
             uses extended-system-stats-block;
           }
         }
         case multichassis-tag {
           container multi-routing-engine-results {
             list multi-routing-engine-item {
               leaf re-name {
                 type string;
               }
               choice output-tags {
                 case actual-tag {
                   container extended-system-stats {
                     uses extended-system-stats-block;
                   }
                 }
               }
             }
           }
         }
       }
     }
   }
   rpc show-icmpd-internal-statistics {
     description "Display icmpd internal statistics";
     output {
       choice output-tags {
         case actual-tag {
           container icmpd-internal-statistics {
             uses icmpd-internal-statistics-block;
           }
         }
         case multichassis-tag {
           container multi-routing-engine-results {
             list multi-routing-engine-item {
               leaf re-name {
                 type string;
               }
               choice output-tags {
                 case actual-tag {
                   container icmpd-internal-statistics {
                     uses icmpd-internal-statistics-block;
                   }
                 }
               }
             }
           }
         }
       }
     }
   }
   rpc show-kfw-statistics {
     description "Display statistics for kfirewall-agent";
     output {
       choice output-tags {
         case actual-tag {
           container kfw-statistics {
             uses kfw-statistics-block;
           }
         }
         case multichassis-tag {
           container multi-routing-engine-results {
             list multi-routing-engine-item {
               leaf re-name {
                 type string;
               }
               choice output-tags {
                 case actual-tag {
                   container kfw-statistics {
                     uses kfw-statistics-block;
                   }
                 }
               }
             }
           }
         }
       }
     }
   }
   rpc get-system-storage {
     description "Show local storage data";
     input {
       uses command-forwarding;
       leaf detail {
         description "Display detailed output";
         type empty;
       }
     }
     output {
       choice output-tags {
         case actual-tag {
           container system-storage-information {
             uses system-storage-information-block;
           }
         }
         case multichassis-tag {
           container multi-routing-engine-results {
             list multi-routing-engine-item {
               leaf re-name {
                 type string;
               }
               choice output-tags {
                 case actual-tag {
                   container system-storage-information {
                     uses system-storage-information-block;
                   }
                 }
               }
             }
           }
         }
       }
     }
   }
   rpc get-system-storage-satellite {
     description "Show satellite device storage data";
     input {
       leaf fpc-slot {
         description "Satellite slot number";
         type union {
           type string {
             pattern "<.*>|$.*";
           }
           type uint32 {
             range "65 .. 254";
           }
         }
       }
       leaf device-alias {
         description "Device alias";
         type string;
       }
     }
     output {
       choice output-tags {
         case output-tag {
           leaf output {
             type string;
           }
         }
         case multichassis-tag {
           anyxml multi-routing-engine-results;
         }
       }
     }
   }
   rpc get-system-storage-analysis-information {
     description "Analyse system storage usage";
     input {
       uses command-forwarding;
       leaf brief {
         description "Brief";
         type empty;
       }
       leaf extensive {
         description "Extensive";
         type empty;
       }
       leaf list-large-files {
         description "Large files";
         type empty;
       }
       leaf apps-using-deleted-files {
         description "Applications using deleted files";
         type empty;
       }
       leaf files-hidden-by-mount {
         description "Files hidden by mount";
         type empty;
       }
     }
     output {
       choice output-tags {
         case actual-tag {
           container system-storage-analysis-information {
             uses system-storage-analysis-information-block;
           }
         }
         case multichassis-tag {
           container multi-routing-engine-results {
             list multi-routing-engine-item {
               leaf re-name {
                 type string;
               }
               choice output-tags {
                 case actual-tag {
                   container system-storage-analysis-information {
                     uses system-storage-analysis-information-block;
                   }
                 }
               }
             }
           }
         }
       }
     }
   }
   rpc get-storage-analysis-dir {
     description "Analyze a directory path";
     input {
       uses command-forwarding;
       leaf directory-path {
         description "Directory path to analyze";
         type string;
         mandatory true;
       }
       leaf filesystem-only {
         description "Restrict to path's own filesystem (skip nested mounts)";
         type empty;
       }
       leaf brief {
         description "Brief";
         type empty;
       }
       leaf extensive {
         description "Extensive";
         type empty;
       }
       leaf list-large-files {
         description "Large files";
         type empty;
       }
       leaf apps-using-deleted-files {
         description "Applications using deleted files";
         type empty;
       }
       leaf files-hidden-by-mount {
         description "Files hidden by mount";
         type empty;
       }
     }
     output {
       choice output-tags {
         case actual-tag {
           container system-storage-analysis-information {
             uses system-storage-analysis-information-block;
           }
         }
         case multichassis-tag {
           container multi-routing-engine-results {
             list multi-routing-engine-item {
               leaf re-name {
                 type string;
               }
               choice output-tags {
                 case actual-tag {
                   container system-storage-analysis-information {
                     uses system-storage-analysis-information-block;
                   }
                 }
               }
             }
           }
         }
       }
     }
   }
   rpc get-switchover-information {
     description "Show Routing Engine graceful switchover information";
     input {
       uses command-forwarding;
     }
     output {
       choice output-tags {
         case actual-tag {
           container switchover-information {
             uses switchover-information-block;
           }
         }
         case multichassis-tag {
           container multi-routing-engine-results {
             list multi-routing-engine-item {
               leaf re-name {
                 type string;
               }
               choice output-tags {
                 case actual-tag {
                   container switchover-information {
                     uses switchover-information-block;
                   }
                 }
               }
             }
           }
         }
       }
     }
   }
   rpc get-system-services-reverse-information {
     description "Show reverse telnet/SSH connection information";
     output {
       choice output-tags {
         case actual-tag {
           container system-services-reverse-information {
             uses system-services-reverse-information-block;
           }
         }
         case multichassis-tag {
           container multi-routing-engine-results {
             list multi-routing-engine-item {
               leaf re-name {
                 type string;
               }
               choice output-tags {
                 case actual-tag {
                   container system-services-reverse-information {
                     uses system-services-reverse-information-block;
                   }
                 }
               }
             }
           }
         }
       }
     }
   }
   rpc get-dhcp-binding-information {
     description "Show DHCP client binding information";
     input {
       uses command-forwarding;
       leaf detail {
         description "Display detailed information";
         type empty;
       }
       leaf address {
         description "Address of DHCP client binding";
         type jt:ipaddr;
       }
     }
     output {
       choice output-tags {
         case output-tag {
           leaf output {
             type string;
           }
         }
         case actual-tag {
           anyxml dhcp-binding-information;
         }
         case multichassis-tag {
           anyxml multi-routing-engine-results;
         }
       }
     }
   }
   rpc get-dhcp-conflict-information {
     description "Show DHCP address conflict";
     input {
       uses command-forwarding;
     }
     output {
       choice output-tags {
         case output-tag {
           leaf output {
             type string;
           }
         }
         case actual-tag {
           anyxml dhcp-conflict-information;
         }
         case multichassis-tag {
           anyxml multi-routing-engine-results;
         }
       }
     }
   }
   rpc get-dhcp-global-information {
     description "Show DHCP global scope information";
     input {
       uses command-forwarding;
     }
     output {
       choice output-tags {
         case output-tag {
           leaf output {
             type string;
           }
         }
         case actual-tag {
           anyxml dhcp-global-information;
         }
         case multichassis-tag {
           anyxml multi-routing-engine-results;
         }
       }
     }
   }
   rpc get-dhcp-pool-information {
     description "Show DHCP address pool information";
     input {
       uses command-forwarding;
       leaf detail {
         description "Display detailed information";
         type empty;
       }
       leaf subnet-address {
         description "Logical subnet of address pool";
         type jt:ipprefix;
       }
     }
     output {
       choice output-tags {
         case output-tag {
           leaf output {
             type string;
           }
         }
         case actual-tag {
           anyxml dhcp-pool-information;
         }
         case multichassis-tag {
           anyxml multi-routing-engine-results;
         }
       }
     }
   }
   rpc get-dhcp-statistics-information {
     description "Show DHCP statistics";
     input {
       uses command-forwarding;
     }
     output {
       choice output-tags {
         case output-tag {
           leaf output {
             type string;
           }
         }
         case actual-tag {
           anyxml dhcp-statistics-information;
         }
         case multichassis-tag {
           anyxml multi-routing-engine-results;
         }
       }
     }
   }
   rpc get-service-deployment-service-information {
     description "Show service deployment service information";
     output {
       choice output-tags {
         case output-tag {
           leaf output {
             type string;
           }
         }
         case actual-tag {
           anyxml service-deployment-service-information;
         }
         case multichassis-tag {
           anyxml multi-routing-engine-results;
         }
       }
     }
   }
   rpc get-outbound-ssh-service-information {
     description "Outbound SSH connections";
     input {
       leaf client-id {
         description "Client application identifier";
         type string;
       }
       leaf verbosity {
         description "Level of detail needed";
         default "brief";
         type enumeration {
           enum "brief" {
             description "Brief output";
           }
           enum "detail" {
             description "Detailed output";
           }
         }
       }
     }
     output {
       choice output-tags {
         case actual-tag {
           container outbound-ssh-service-information {
             uses outbound-ssh-service-information-block;
           }
         }
         case multichassis-tag {
           container multi-routing-engine-results {
             list multi-routing-engine-item {
               leaf re-name {
                 type string;
               }
               choice output-tags {
                 case actual-tag {
                   container outbound-ssh-service-information {
                     uses outbound-ssh-service-information-block;
                   }
                 }
               }
             }
           }
         }
       }
     }
   }
   rpc get-system-memory-information {
     description "Show system memory usage";
     input {
       uses command-forwarding;
     }
     output {
       choice output-tags {
         case actual-tag {
           container system-memory-information {
             uses system-memory-information-block;
           }
         }
         case multichassis-tag {
           container multi-routing-engine-results {
             list multi-routing-engine-item {
               leaf re-name {
                 type string;
               }
               choice output-tags {
                 case actual-tag {
                   container system-memory-information {
                     uses system-memory-information-block;
                   }
                 }
               }
             }
           }
         }
       }
     }
   }
   rpc get-system-virtual-memory-information {
     description "Show kernel dynamic memory usage";
     input {
       uses command-forwarding;
     }
     output {
       choice output-tags {
         case actual-tag {
           container system-virtual-memory-information {
             uses system-virtual-memory-information-block;
           }
         }
         case multichassis-tag {
           container multi-routing-engine-results {
             list multi-routing-engine-item {
               leaf re-name {
                 type string;
               }
               choice output-tags {
                 case actual-tag {
                   container system-virtual-memory-information {
                     uses system-virtual-memory-information-block;
                   }
                 }
               }
             }
           }
         }
       }
     }
   }
   rpc get-system-users-information {
     description "Show users who are currently logged in";
     input {
       uses command-forwarding;
       leaf no-resolve {
         description "Don't attempt to print addresses symbolically";
         type empty;
       }
     }
     output {
       choice output-tags {
         case actual-tag {
           container system-users-information {
             uses system-users-information-block;
           }
         }
         case multichassis-tag {
           container multi-routing-engine-results {
             list multi-routing-engine-item {
               leaf re-name {
                 type string;
               }
               choice output-tags {
                 case actual-tag {
                   container system-users-information {
                     uses system-users-information-block;
                   }
                 }
               }
             }
           }
         }
       }
     }
   }
   rpc get-syslog-events {
     description "Show system log messages";
     input {
       leaf stream {
         description "Name of stream (log file) containing messages to filter";
         type string {
         }
         mandatory true;
       }
       leaf event {
         description "Event ID of messages to include in output";
         type string {
           length "1 .. 256";
         }
       }
       leaf process {
         description "Name of process generating messages to include in output";
         type string {
           length "1 .. 256";
         }
       }
       leaf-list priority {
         ordered-by user;
         description "Facility and severity of messages to include in output";
         type string;
       }
       leaf host {
         description "Name of host generating messages to include in output";
         type string {
           length "1 .. 256";
         }
       }
       leaf start-time {
         description "Earliest timestamp of messages to include in output";
         type jt:time;
       }
       choice stop-time-choice {
         case current-time {
           leaf current-time {
             description "Include messages up to current time";
             type empty;
           }
         }
         case stop-time {
           leaf stop-time {
             description "Latest timestamp of messages to include in output";
             type jt:time;
           }
         }
       }
       leaf-list parameter {
         ordered-by user;
         description "Parameter (key=value) of messages to include in output";
         type jt:regular-expression;
       }
       leaf text-pattern {
         description "Pattern in messages to include in output";
         type jt:regular-expression;
       }
       leaf count {
         description "Number of messages to include in output";
         type union {
           type uint32;
           type string {
             pattern "<.*>|$.*";
           }
         }
       }
       leaf recorded {
         description "Match only the recorded messages";
         type empty;
       }
       leaf connection-id {
         description "Connection ID";
         type string;
       }
       leaf total-events {
         description "Print total count of the messages matching filter criteria";
         type empty;
       }
       leaf start-count {
         description "Print start-count";
         type union {
           type uint32;
           type string {
             pattern "<.*>|$.*";
           }
         }
       }
       leaf end-count {
         description "Print end-count";
         type union {
           type uint32;
           type string {
             pattern "<.*>|$.*";
           }
         }
       }
       leaf pretty {
         description "Display output in pretty format";
         type empty;
       }
       leaf print-json {
         description "Print the output of pretty in json format";
         type empty;
       }
       leaf reverse {
         description "Print the logs in reverse order";
         type empty;
       }
     }
     output {
       choice output-tags {
         case actual-tag {
           container syslog-events {
             uses syslog-events-block;
           }
         }
         case multichassis-tag {
           container multi-routing-engine-results {
             list multi-routing-engine-item {
               leaf re-name {
                 type string;
               }
               choice output-tags {
                 case actual-tag {
                   container syslog-events {
                     uses syslog-events-block;
                   }
                 }
               }
             }
           }
         }
       }
     }
   }
   rpc get-hw-resource-utilization-information {
     description "Show HW Resource utilization information";
     output {
       choice output-tags {
         case actual-tag {
           container hw-resource-utilization-information {
             uses hw-resource-utilization-information-block;
           }
         }
         case multichassis-tag {
           container multi-routing-engine-results {
             list multi-routing-engine-item {
               leaf re-name {
                 type string;
               }
               choice output-tags {
                 case actual-tag {
                   container hw-resource-utilization-information {
                     uses hw-resource-utilization-information-block;
                   }
                 }
               }
             }
           }
         }
       }
     }
   }
   rpc get-hwrm-utilization-information {
     description "Show HW Resource Monitoring utilization information";
     output {
       choice output-tags {
         case output-tag {
           leaf output {
             type string;
           }
         }
         case multichassis-tag {
           anyxml multi-routing-engine-results;
         }
       }
     }
   }
   rpc get-recycle-bandwidth-profile-information {
     description "Show recycle bandwidth application details";
     output {
       choice output-tags {
         case actual-tag {
           container recycle-bandwidth-profile-information {
             uses recycle-bandwidth-profile-information-block;
           }
         }
         case multichassis-tag {
           container multi-routing-engine-results {
             list multi-routing-engine-item {
               leaf re-name {
                 type string;
               }
               choice output-tags {
                 case actual-tag {
                   container recycle-bandwidth-profile-information {
                     uses recycle-bandwidth-profile-information-block;
                   }
                 }
               }
             }
           }
         }
       }
     }
   }
   rpc get-recycle-voq-information {
     description "Show stats for recycle port";
     input {
       leaf port-no {
         description "Port number of available recycle ports";
         type union {
           type string {
             pattern "<.*>|$.*";
           }
           type uint32 {
             range "0 .. 4096";
           }
         }
         mandatory true;
       }
     }
     output {
       choice output-tags {
         case actual-tag {
           container recycle-voq-information {
             uses recycle-voq-information-block;
           }
         }
         case multichassis-tag {
           container multi-routing-engine-results {
             list multi-routing-engine-item {
               leaf re-name {
                 type string;
               }
               choice output-tags {
                 case actual-tag {
                   container recycle-voq-information {
                     uses recycle-voq-information-block;
                   }
                 }
               }
             }
           }
         }
       }
     }
   }
   rpc get-recycle-bandwidth-available-details {
     description "Show recycle bandwidth availability details";
     output {
       choice output-tags {
         case actual-tag {
           container recycle-bandwidth-available-details {
             uses recycle-bandwidth-available-details-block;
           }
         }
         case multichassis-tag {
           container multi-routing-engine-results {
             list multi-routing-engine-item {
               leaf re-name {
                 type string;
               }
               choice output-tags {
                 case actual-tag {
                   container recycle-bandwidth-available-details {
                     uses recycle-bandwidth-available-details-block;
                   }
                 }
               }
             }
           }
         }
       }
     }
   }
   rpc get-firewall-profile-summary {
     description "Display summary of active firewall profiles";
     output {
       choice output-tags {
         case actual-tag {
           container firewall-profile-summary {
             uses firewall-profile-summary-block;
           }
         }
         case multichassis-tag {
           container multi-routing-engine-results {
             list multi-routing-engine-item {
               leaf re-name {
                 type string;
               }
               choice output-tags {
                 case actual-tag {
                   container firewall-profile-summary {
                     uses firewall-profile-summary-block;
                   }
                 }
               }
             }
           }
         }
       }
     }
   }
   rpc get-firewall-all-profile-information {
     description "Display the firewall profiles";
     input {
       choice profile-options {
         case filter-modify-mbb {
           leaf filter-modify-mbb {
             description "Display MBB firewall profile information";
             type empty;
           }
         }
         case ingress-inet6-user-acl {
           leaf ingress-inet6-user-acl {
             description "Display ingress inet6 user-acl firewall profile information";
             type empty;
           }
         }
         case ingress-inet6-lo0-acl {
           leaf ingress-inet6-lo0-acl {
             description "Display ingress inet6 lo0 firewall profile information";
             type empty;
           }
         }
         case egress-inet6-user-acl {
           leaf egress-inet6-user-acl {
             description "Display egress inet6 user-acl firewall profile information";
             type empty;
           }
         }
       }
     }
     output {
       choice output-tags {
         case actual-tag {
           container firewall-profile-information {
             uses firewall-profile-information-block;
           }
         }
         case multichassis-tag {
           container multi-routing-engine-results {
             list multi-routing-engine-item {
               leaf re-name {
                 type string;
               }
               choice output-tags {
                 case actual-tag {
                   container firewall-profile-information {
                     uses firewall-profile-information-block;
                   }
                 }
               }
             }
           }
         }
       }
     }
   }
   rpc get-hw-profile-information {
     description "Show hardware profile details";
     output {
       choice output-tags {
         case actual-tag {
           container hw-profile-information {
             uses hw-profile-information-block;
           }
         }
         case multichassis-tag {
           container multi-routing-engine-results {
             list multi-routing-engine-item {
               leaf re-name {
                 type string;
               }
               choice output-tags {
                 case actual-tag {
                   container hw-profile-information {
                     uses hw-profile-information-block;
                   }
                 }
               }
             }
           }
         }
       }
     }
   }
   rpc get-cntr-profile-information {
     description "Show counter profile details";
     output {
       choice output-tags {
         case actual-tag {
           container cntr-profile-information {
             uses cntr-profile-information-block;
           }
         }
         case multichassis-tag {
           container multi-routing-engine-results {
             list multi-routing-engine-item {
               leaf re-name {
                 type string;
               }
               choice output-tags {
                 case actual-tag {
                   container cntr-profile-information {
                     uses cntr-profile-information-block;
                   }
                 }
               }
             }
           }
         }
       }
     }
   }
   rpc get-system-resource-cleanup-processes-information {
     description "Show process resource cleanup information";
     input {
       leaf detail {
         description "Display detailed information";
         type empty;
       }
       choice name_pid_choice {
         case process-name {
           leaf process-name {
             description "Process name";
             type string;
           }
         }
         case pid {
           leaf pid {
             description "Process identifier";
             type union {
               type string {
                 pattern "<.*>|$.*";
               }
               type uint32 {
                 range "1 .. 99999";
               }
             }
           }
         }
       }
     }
     output {
       choice output-tags {
         case output-tag {
           leaf output {
             type string;
           }
         }
         case actual-tag {
           anyxml system-resource-cleanup-processes-information;
         }
         case multichassis-tag {
           anyxml multi-routing-engine-results;
         }
       }
     }
   }
   rpc get-resource-monitor-summary-fpc-information {
     description "Show Resource Monitor summary";
     output {
       choice output-tags {
         case actual-tag {
           container resource-monitor-summary-fpc-information {
             uses resource-monitor-summary-fpc-information-block;
           }
         }
         case multichassis-tag {
           container multi-routing-engine-results {
             list multi-routing-engine-item {
               leaf re-name {
                 type string;
               }
               choice output-tags {
                 case actual-tag {
                   container resource-monitor-summary-fpc-information {
                     uses resource-monitor-summary-fpc-information-block;
                   }
                 }
               }
             }
           }
         }
       }
     }
   }
   rpc get-resource-monitor-detail-fpc-information {
     description "Show Resource Monitor detail";
     output {
       choice output-tags {
         case actual-tag {
           container resource-monitor-detail-fpc-information {
             uses resource-monitor-detail-fpc-information-block;
           }
         }
         case multichassis-tag {
           container multi-routing-engine-results {
             list multi-routing-engine-item {
               leaf re-name {
                 type string;
               }
               choice output-tags {
                 case actual-tag {
                   container resource-monitor-detail-fpc-information {
                     uses resource-monitor-detail-fpc-information-block;
                   }
                 }
               }
             }
           }
         }
       }
     }
   }
   rpc get-resource-monitor-fpc-information {
     description "Show Line Card Resource utilization for monitoring";
     output {
       choice output-tags {
         case actual-tag {
           container resource-monitor-fpc-information {
             uses resource-monitor-fpc-information-block;
           }
         }
         case multichassis-tag {
           container multi-routing-engine-results {
             list multi-routing-engine-item {
               leaf re-name {
                 type string;
               }
               choice output-tags {
                 case actual-tag {
                   container resource-monitor-fpc-information {
                     uses resource-monitor-fpc-information-block;
                   }
                 }
               }
             }
           }
         }
       }
     }
   }
   rpc get-resource-monitor-fpc-slot-information {
     description "FPC Slot number";
     input {
       leaf slot {
         description "FPC slot number";
         type union {
           type string {
             pattern "<.*>|$.*";
           }
           type uint32 {
             range "0 .. 255";
           }
         }
         mandatory true;
       }
     }
     output {
       choice output-tags {
         case actual-tag {
           container resource-monitor-fpc-slot-information {
             uses resource-monitor-fpc-slot-information-block;
           }
         }
         case multichassis-tag {
           container multi-routing-engine-results {
             list multi-routing-engine-item {
               leaf re-name {
                 type string;
               }
               choice output-tags {
                 case actual-tag {
                   container resource-monitor-fpc-slot-information {
                     uses resource-monitor-fpc-slot-information-block;
                   }
                 }
               }
             }
           }
         }
       }
     }
   }
   rpc get-resource-monitor-ifd-mapping-information {
     description "Display ifd to queue mapping";
     input {
       leaf fpc {
         description "FPC number";
         type union {
           type string {
             pattern "<.*>|$.*";
           }
           type uint32 {
             range "0 .. 255";
           }
         }
         mandatory true;
       }
     }
     output {
       choice output-tags {
         case actual-tag {
           container resource-monitor-ifd-mapping-information {
             uses resource-monitor-ifd-mapping-information-block;
           }
         }
         case multichassis-tag {
           container multi-routing-engine-results {
             list multi-routing-engine-item {
               leaf re-name {
                 type string;
               }
               choice output-tags {
                 case actual-tag {
                   container resource-monitor-ifd-mapping-information {
                     uses resource-monitor-ifd-mapping-information-block;
                   }
                 }
               }
             }
           }
         }
       }
     }
   }
   rpc get-subscribers-limit-level {
     description "Show Subscriber limit";
     input {
       leaf chassis {
         description "Show Subscriber limit of chassis level";
         type empty;
         mandatory true;
       }
       leaf fpc {
         description "Show Subscriber limit of fpc level";
         type union {
           type string {
             pattern "<.*>|$.*";
           }
           type uint32 {
             range "0 .. 255";
           }
         }
         mandatory true;
       }
       leaf pic {
         description "Show Subscriber limit of pic level";
         type union {
           type string {
             pattern "<.*>|$.*";
           }
           type int32 {
             range "0 .. 3";
           }
         }
       }
       leaf port {
         description "Show Subscriber limit of port level";
         type union {
           type string {
             pattern "<.*>|$.*";
           }
           type uint32 {
             range "0 .. 23";
           }
         }
       }
       leaf extensive {
         description "Display extensive output";
         type empty;
       }
     }
     output {
       choice output-tags {
         case actual-tag {
           container subscribers-limit-level {
             uses subscribers-limit-level-block;
           }
         }
         case multichassis-tag {
           container multi-routing-engine-results {
             list multi-routing-engine-item {
               leaf re-name {
                 type string;
               }
               choice output-tags {
                 case actual-tag {
                   container subscribers-limit-level {
                     uses subscribers-limit-level-block;
                   }
                 }
               }
             }
           }
         }
       }
     }
   }
   rpc get-system-monitor-memory-events {
     description "Display history of events minor/major/critical ";
     output {
       choice output-tags {
         case output-tag {
           leaf output {
             type string;
           }
         }
         case actual-tag {
           anyxml system-monitor-memory-events;
         }
         case multichassis-tag {
           anyxml multi-routing-engine-results;
         }
       }
     }
   }
   rpc get-system-monitor-memory-status {
     description "Display current status of the events minor/major/critical";
     output {
       choice output-tags {
         case output-tag {
           leaf output {
             type string;
           }
         }
         case actual-tag {
           anyxml system-monitor-memory-events-status;
         }
         case multichassis-tag {
           anyxml multi-routing-engine-results;
         }
       }
     }
   }
   rpc get-system-monitor-memory-status-all {
     description "Display current status of all events";
     output {
       choice output-tags {
         case output-tag {
           leaf output {
             type string;
           }
         }
         case actual-tag {
           anyxml system-monitor-memory-status-all;
         }
         case multichassis-tag {
           anyxml multi-routing-engine-results;
         }
       }
     }
   }
   rpc get-system-monitor-memory-status-system {
     description "Display current status of system events";
     output {
       choice output-tags {
         case output-tag {
           leaf output {
             type string;
           }
         }
         case actual-tag {
           anyxml system-monitor-memory-status-system;
         }
         case multichassis-tag {
           anyxml multi-routing-engine-results;
         }
       }
     }
   }
   rpc get-system-monitor-memory-status-process {
     description "Display current status of process events";
     output {
       choice output-tags {
         case output-tag {
           leaf output {
             type string;
           }
         }
         case actual-tag {
           anyxml system-monitor-memory-status-process;
         }
         case multichassis-tag {
           anyxml multi-routing-engine-results;
         }
       }
     }
   }
   rpc get-system-monitor-memory-actions {
     description "Display history of actions taken on events";
     output {
       choice output-tags {
         case output-tag {
           leaf output {
             type string;
           }
         }
         case actual-tag {
           anyxml system-monitor-memory-actions;
         }
         case multichassis-tag {
           anyxml multi-routing-engine-results;
         }
       }
     }
   }
   rpc get-system-firmware-information {
     description "Show all firmware version information";
     input {
       uses command-forwarding;
       leaf compatibility {
         description "Show all firmware compatibility information";
         type empty;
       }
       choice which-arg {
         case fpc {
           leaf fpc {
             description "Show Flexible PIC Concentrator firmware information";
             type union {
               type string {
                 pattern "<.*>|$.*";
               }
               type uint32;
             }
           }
         }
         case routing-engine {
         }
         case sfb {
           leaf sfb {
             description "Show Switch Fabric Board firmware information";
             type union {
               type string {
                 pattern "<.*>|$.*";
               }
               type uint32;
             }
           }
         }
         case pem {
           leaf pem {
             description "Show Power Entry Module firmware information";
             type union {
               type string {
                 pattern "<.*>|$.*";
               }
               type uint32;
             }
           }
         }
         case ftc {
           leaf ftc {
             description "Show Fan Tray Controller firmware information";
             type union {
               type string {
                 pattern "<.*>|$.*";
               }
               type uint32;
             }
           }
         }
         case cb {
           leaf cb {
             description "Show Control Board firmware information";
             type union {
               type string {
                 pattern "<.*>|$.*";
               }
               type uint32;
             }
           }
         }
         case feb {
           leaf feb {
             description "Show Forwarding Engine Board firmware information";
             type union {
               type string {
                 pattern "<.*>|$.*";
               }
               type uint32;
             }
           }
         }
         case psm {
           leaf psm {
             description "Show Power Supply Module firmware information";
             type union {
               type string {
                 pattern "<.*>|$.*";
               }
               type uint32;
             }
           }
         }
       }
     }
     output {
       choice output-tags {
         case actual-tag {
           container system-firmware-information {
             uses system-firmware-information-block;
           }
         }
         case multichassis-tag {
           container multi-routing-engine-results {
             list multi-routing-engine-item {
               leaf re-name {
                 type string;
               }
               choice output-tags {
                 case actual-tag {
                   container system-firmware-information {
                     uses system-firmware-information-block;
                   }
                 }
               }
             }
           }
         }
       }
     }
   }
   rpc get-cdb-advertisement {
     description "Show system firmware optics cdb-advertisement";
     input {
       uses command-forwarding;
       leaf fpc-slot {
         description "FPC slot";
         type union {
           type string {
             pattern "<.*>|$.*";
           }
           type uint32;
         }
         mandatory true;
       }
       leaf pic-slot {
         description "PIC slot number";
         type union {
           type string {
             pattern "<.*>|$.*";
           }
           type uint32;
         }
         mandatory true;
       }
       leaf port-number {
         description "Enter Port number";
         type union {
           type string {
             pattern "<.*>|$.*";
           }
           type uint32;
         }
         mandatory true;
       }
     }
     output {
       choice output-tags {
         case actual-tag {
           container cdb-advertisement {
             uses cdb-advertisement-block;
           }
         }
         case multichassis-tag {
           container multi-routing-engine-results {
             list multi-routing-engine-item {
               leaf re-name {
                 type string;
               }
               choice output-tags {
                 case actual-tag {
                   container cdb-advertisement {
                     uses cdb-advertisement-block;
                   }
                 }
               }
             }
           }
         }
       }
     }
   }
   rpc get-firmware-update {
     description "Show system firmware optics status";
     input {
       uses command-forwarding;
     }
     output {
       choice output-tags {
         case output-tag {
           leaf output {
             type string;
           }
         }
         case actual-tag {
           anyxml firmware-update;
         }
         case multichassis-tag {
           anyxml multi-routing-engine-results;
         }
       }
     }
   }
   rpc get-system-golden-firmware-information {
     description "Show all golden firmware version information";
     status deprecated;
     input {
       uses command-forwarding;
     }
     output {
       choice output-tags {
         case actual-tag {
           container system-golden-firmware-information {
             uses system-golden-firmware-information-block;
           }
         }
         case multichassis-tag {
           container multi-routing-engine-results {
             list multi-routing-engine-item {
               leaf re-name {
                 type string;
               }
               choice output-tags {
                 case actual-tag {
                   container system-golden-firmware-information {
                     uses system-golden-firmware-information-block;
                   }
                 }
               }
             }
           }
         }
       }
     }
   }
   rpc get-system-detail-firmware-information {
     description "Show all firmware version details";
     input {
       uses command-forwarding;
       choice which-arg {
         case fpc {
           leaf fpc {
             description "Show Flexible PIC Concentrator firmware information";
             type union {
               type string {
                 pattern "<.*>|$.*";
               }
               type uint32;
             }
           }
         }
         case sfb {
           leaf sfb {
             description "Show Switch Fabric Board firmware information";
             type union {
               type string {
                 pattern "<.*>|$.*";
               }
               type uint32;
             }
           }
         }
       }
     }
     output {
       choice output-tags {
         case actual-tag {
           container system-detail-firmware-information {
             uses system-detail-firmware-information-block;
           }
         }
         case multichassis-tag {
           container multi-routing-engine-results {
             list multi-routing-engine-item {
               leaf re-name {
                 type string;
               }
               choice output-tags {
                 case actual-tag {
                   container system-detail-firmware-information {
                     uses system-detail-firmware-information-block;
                   }
                 }
               }
             }
           }
         }
       }
     }
   }
   rpc get-fm-appstatus-information {
     description "Show fabric application status information";
     input {
       uses command-forwarding;
     }
     output {
       choice output-tags {
         case actual-tag {
           container fm-appstatus-information {
             uses fm-appstatus-information-block;
           }
         }
         case multichassis-tag {
           container multi-routing-engine-results {
             list multi-routing-engine-item {
               leaf re-name {
                 type string;
               }
               choice output-tags {
                 case actual-tag {
                   container fm-appstatus-information {
                     uses fm-appstatus-information-block;
                   }
                 }
               }
             }
           }
         }
       }
     }
   }
   rpc get-filesystem-encryption-status {
     description "Show filesystem encryption details";
     input {
       uses command-forwarding;
     }
     output {
       choice output-tags {
         case actual-tag {
           container filesystem-encryption-status {
             uses filesystem-encryption-status-block;
           }
         }
         case multichassis-tag {
           container multi-routing-engine-results {
             list multi-routing-engine-item {
               leaf re-name {
                 type string;
               }
               choice output-tags {
                 case actual-tag {
                   container filesystem-encryption-status {
                     uses filesystem-encryption-status-block;
                   }
                 }
               }
             }
           }
         }
       }
     }
   }
   rpc get-system-memory-profiling {
     description "Status of memory profiling for the application";
     input {
       leaf node {
         description "Node name";
         type string;
       }
       leaf application {
         description "Application name";
         type string;
         mandatory true;
       }
     }
     output {
       choice output-tags {
         case actual-tag {
           container memory-profiling-status {
             uses memory-profiling-status-block;
           }
         }
         case multichassis-tag {
           container multi-routing-engine-results {
             list multi-routing-engine-item {
               leaf re-name {
                 type string;
               }
               choice output-tags {
                 case actual-tag {
                   container memory-profiling-status {
                     uses memory-profiling-status-block;
                   }
                 }
               }
             }
           }
         }
       }
     }
   }
   rpc show-ztp-state {
     description "Show ZTP state information";
     output {
       choice output-tags {
         case actual-tag {
           container system-ztp-info {
             uses system-ztp-info-block;
           }
         }
         case multichassis-tag {
           container multi-routing-engine-results {
             list multi-routing-engine-item {
               leaf re-name {
                 type string;
               }
               choice output-tags {
                 case actual-tag {
                   container system-ztp-info {
                     uses system-ztp-info-block;
                   }
                 }
               }
             }
           }
         }
       }
     }
   }
   rpc get-system-software-list {
     description "List all software versions installed";
     output {
       choice output-tags {
         case actual-tag {
           container system-software-list {
             uses system-software-list-block;
           }
         }
         case multichassis-tag {
           container multi-routing-engine-results {
             list multi-routing-engine-item {
               leaf re-name {
                 type string;
               }
               choice output-tags {
                 case actual-tag {
                   container system-software-list {
                     uses system-software-list-block;
                   }
                 }
               }
             }
           }
         }
       }
     }
   }
   rpc get-system-add-restart-detail {
     description "Show software add restart detailed info";
     output {
       choice output-tags {
         case actual-tag {
           container system-add-restart-information {
             uses system-add-restart-information-block;
           }
         }
         case multichassis-tag {
           container multi-routing-engine-results {
             list multi-routing-engine-item {
               leaf re-name {
                 type string;
               }
               choice output-tags {
                 case actual-tag {
                   container system-add-restart-information {
                     uses system-add-restart-information-block;
                   }
                 }
               }
             }
           }
         }
       }
     }
   }
   rpc get-system-hitless-reboot-detail {
     description "Show software hitless reboot detailed info";
     output {
       choice output-tags {
         case actual-tag {
           container system-hitless-reboot-information {
             uses system-hitless-reboot-information-block;
           }
         }
         case multichassis-tag {
           container multi-routing-engine-results {
             list multi-routing-engine-item {
               leaf re-name {
                 type string;
               }
               choice output-tags {
                 case actual-tag {
                   container system-hitless-reboot-information {
                     uses system-hitless-reboot-information-block;
                   }
                 }
               }
             }
           }
         }
       }
     }
   }
   rpc get-system-applications-information {
     description "Show all applications summary information in a system or node";
     input {
       leaf node {
         description "Node name";
         type string;
       }
       leaf app {
         description "Application name";
         type string;
       }
       leaf level {
         default "brief";
         type enumeration {
           enum "brief" {
             description "Display brief output";
           }
           enum "detail" {
             description "Display detailed output";
           }
         }
       }
     }
     output {
       choice output-tags {
         case actual-tag {
           container system-applications-info {
             uses system-applications-info-block;
           }
         }
         case multichassis-tag {
           container multi-routing-engine-results {
             list multi-routing-engine-item {
               leaf re-name {
                 type string;
               }
               choice output-tags {
                 case actual-tag {
                   container system-applications-info {
                     uses system-applications-info-block;
                   }
                 }
               }
             }
           }
         }
       }
     }
   }
   rpc get-system-application-error-information {
     description "Show error related to given application";
     input {
       leaf node {
         description "Node name";
         type string;
       }
       leaf app {
         description "Application name";
         type string;
       }
       leaf level {
         default "brief";
         type enumeration {
           enum "brief" {
             description "Display brief output";
           }
           enum "detail" {
             description "Display detailed output";
           }
         }
       }
     }
     output {
       choice output-tags {
         case actual-tag {
           container application-error-info {
             uses application-error-info-block;
           }
         }
         case multichassis-tag {
           container multi-routing-engine-results {
             list multi-routing-engine-item {
               leaf re-name {
                 type string;
               }
               choice output-tags {
                 case actual-tag {
                   container application-error-info {
                     uses application-error-info-block;
                   }
                 }
               }
             }
           }
         }
       }
     }
   }
   rpc get-fpc-healthz-detail-information {
     description "Show health-status detail for FPC";
     input {
       leaf slot {
         description "FPC slot number";
         type union {
           type string {
             pattern "<.*>|$.*";
           }
           type uint32;
         }
         mandatory true;
       }
     }
     output {
       choice output-tags {
         case actual-tag {
           container healthz-detail-information {
             uses healthz-detail-information-block;
           }
         }
         case multichassis-tag {
           container multi-routing-engine-results {
             list multi-routing-engine-item {
               leaf re-name {
                 type string;
               }
               choice output-tags {
                 case actual-tag {
                   container healthz-detail-information {
                     uses healthz-detail-information-block;
                   }
                 }
               }
             }
           }
         }
       }
     }
   }
   rpc get-sib-healthz-detail-information {
     description "Show health status detail for SIB";
     input {
       leaf slot {
         description "SIB slot number";
         type union {
           type string {
             pattern "<.*>|$.*";
           }
           type uint32;
         }
         mandatory true;
       }
     }
     output {
       choice output-tags {
         case actual-tag {
           container healthz-detail-information {
             uses healthz-detail-information-block;
           }
         }
         case multichassis-tag {
           container multi-routing-engine-results {
             list multi-routing-engine-item {
               leaf re-name {
                 type string;
               }
               choice output-tags {
                 case actual-tag {
                   container healthz-detail-information {
                     uses healthz-detail-information-block;
                   }
                 }
               }
             }
           }
         }
       }
     }
   }
   rpc get-cb-healthz-detail-information {
     description "Show health errors detail for CB";
     input {
       leaf slot {
         description "CB slot number";
         type union {
           type string {
             pattern "<.*>|$.*";
           }
           type uint32;
         }
         mandatory true;
       }
     }
     output {
       choice output-tags {
         case actual-tag {
           container healthz-detail-information {
             uses healthz-detail-information-block;
           }
         }
         case multichassis-tag {
           container multi-routing-engine-results {
             list multi-routing-engine-item {
               leaf re-name {
                 type string;
               }
               choice output-tags {
                 case actual-tag {
                   container healthz-detail-information {
                     uses healthz-detail-information-block;
                   }
                 }
               }
             }
           }
         }
       }
     }
   }
   rpc get-re-healthz-detail-information {
     description "Show health errors detail for RE";
     input {
       leaf slot {
         description "RE slot number";
         type union {
           type string {
             pattern "<.*>|$.*";
           }
           type int32;
         }
         mandatory true;
       }
     }
     output {
       choice output-tags {
         case actual-tag {
           container healthz-detail-information {
             uses healthz-detail-information-block;
           }
         }
         case multichassis-tag {
           container multi-routing-engine-results {
             list multi-routing-engine-item {
               leaf re-name {
                 type string;
               }
               choice output-tags {
                 case actual-tag {
                   container healthz-detail-information {
                     uses healthz-detail-information-block;
                   }
                 }
               }
             }
           }
         }
       }
     }
   }
   rpc get-chassis-healthz-detail-information {
     description "Show health status detail for Chassis";
     input {
       leaf slot {
         description "CHASSIS slot number";
         type union {
           type string {
             pattern "<.*>|$.*";
           }
           type uint32 {
             range 0;
           }
         }
         mandatory true;
       }
     }
     output {
       choice output-tags {
         case actual-tag {
           container healthz-detail-information {
             uses healthz-detail-information-block;
           }
         }
         case multichassis-tag {
           container multi-routing-engine-results {
             list multi-routing-engine-item {
               leaf re-name {
                 type string;
               }
               choice output-tags {
                 case actual-tag {
                   container healthz-detail-information {
                     uses healthz-detail-information-block;
                   }
                 }
               }
             }
           }
         }
       }
     }
   }
   rpc get-psm-healthz-detail-information {
     description "Show health errors detail for PSM";
     input {
       leaf slot {
         description "PSM slot number";
         type union {
           type string {
             pattern "<.*>|$.*";
           }
           type uint32;
         }
         mandatory true;
       }
     }
     output {
       choice output-tags {
         case actual-tag {
           container healthz-detail-information {
             uses healthz-detail-information-block;
           }
         }
         case multichassis-tag {
           container multi-routing-engine-results {
             list multi-routing-engine-item {
               leaf re-name {
                 type string;
               }
               choice output-tags {
                 case actual-tag {
                   container healthz-detail-information {
                     uses healthz-detail-information-block;
                   }
                 }
               }
             }
           }
         }
       }
     }
   }
   rpc get-fan-healthz-detail-information {
     description "Show health errors detail for Fan";
     input {
       leaf slot {
         description "FAN slot number";
         type union {
           type string {
             pattern "<.*>|$.*";
           }
           type uint32;
         }
         mandatory true;
       }
     }
     output {
       choice output-tags {
         case actual-tag {
           container healthz-detail-information {
             uses healthz-detail-information-block;
           }
         }
         case multichassis-tag {
           container multi-routing-engine-results {
             list multi-routing-engine-item {
               leaf re-name {
                 type string;
               }
               choice output-tags {
                 case actual-tag {
                   container healthz-detail-information {
                     uses healthz-detail-information-block;
                   }
                 }
               }
             }
           }
         }
       }
     }
   }
   rpc get-application-healthz-detail-information {
     description "Show applications";
     input {
       leaf node {
         description "Node name";
         type string;
         mandatory true;
       }
       leaf app {
         description "Application name";
         type string;
         mandatory true;
       }
     }
     output {
       choice output-tags {
         case actual-tag {
           container healthz-detail-information {
             uses healthz-detail-information-block;
           }
         }
         case multichassis-tag {
           container multi-routing-engine-results {
             list multi-routing-engine-item {
               leaf re-name {
                 type string;
               }
               choice output-tags {
                 case actual-tag {
                   container healthz-detail-information {
                     uses healthz-detail-information-block;
                   }
                 }
               }
             }
           }
         }
       }
     }
   }
   rpc show-kfw-information {
     description "Display information for host firewall";
     output {
       choice output-tags {
         case actual-tag {
           container kfw-information {
             uses kfw-information-block;
           }
         }
         case multichassis-tag {
           container multi-routing-engine-results {
             list multi-routing-engine-item {
               leaf re-name {
                 type string;
               }
               choice output-tags {
                 case actual-tag {
                   container kfw-information {
                     uses kfw-information-block;
                   }
                 }
               }
             }
           }
         }
       }
     }
   }
   rpc get-system-nodes-information {
     description "Show all nodes in the system";
     input {
       leaf node {
         description "Node name";
         type string;
       }
     }
     output {
       choice output-tags {
         case actual-tag {
           container system-nodes-info {
             uses system-nodes-info-block;
           }
         }
         case multichassis-tag {
           container multi-routing-engine-results {
             list multi-routing-engine-item {
               leaf re-name {
                 type string;
               }
               choice output-tags {
                 case actual-tag {
                   container system-nodes-info {
                     uses system-nodes-info-block;
                   }
                 }
               }
             }
           }
         }
       }
     }
   }
   rpc get-system-node-attributes-information {
     description "Show node attribute configuration";
     output {
       choice output-tags {
         case actual-tag {
           container system-node-attributes-info {
             uses system-node-attributes-info-block;
           }
         }
         case multichassis-tag {
           container multi-routing-engine-results {
             list multi-routing-engine-item {
               leaf re-name {
                 type string;
               }
               choice output-tags {
                 case actual-tag {
                   container system-node-attributes-info {
                     uses system-node-attributes-info-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping system-dual-phase-bootup-status-block {
     leaf dual-phase-bootup-status-mode {
       type string;
     }
   }
   grouping genstate-path-cli-command-mapping-information-block {
     leaf genstate-path {
       type string;
       description
         "The input genstate path";
     }
     leaf mapped-cli-command {
       type string;
       description
         "The mapped CLI command";
     }
   }
   grouping commit-information-block {
     container pending-commit {
       leaf user {
         type string;
         description
           "User name executing this script";
       }
       leaf client {
         type string;
         description
           "This client application performed the commit";
       }
       leaf date-time {
         type string;
       }
       leaf log {
         type string;
         description
           "Log message for this commit";
       }
     }
     container prepared-commit {
       leaf user {
         type string;
         description
           "User name executing this script";
       }
       leaf client {
         type string;
         description
           "This client application performed the commit";
       }
       leaf log {
         type string;
         description
           "Log message for this commit";
       }
     }
     list commit-history {
       key "sequence-number";
       leaf sequence-number {
         type int32;
         description
           "Commit sequence number, 0 being the most recent";
       }
       leaf date-time {
         type string;
       }
       leaf user {
         type string;
         description
           "User name executing this script";
       }
       leaf client {
         type string;
         description
           "This client application performed the commit";
       }
       leaf comment {
         type string;
       }
       leaf configuration-revision {
         type string;
         description
           "Configuration revision information";
       }
       leaf log {
         type string;
         description
           "Log message for this commit";
       }
       leaf commit-confirmed {
         type string;
         description
           "Commit confirmed rollback state";
       }
     }
     container rescue-configuration {
       leaf date-time {
         type string;
       }
       leaf user {
         type string;
         description
           "User name executing this script";
       }
       leaf client {
         type string;
         description
           "This client application performed the commit";
       }
       leaf comment {
         type string;
       }
       leaf log {
         type string;
         description
           "Log message for this commit";
       }
     }
   }
   grouping commit-revision-information-block {
     leaf revision {
       type string;
     }
     leaf date-time {
       type string;
     }
     leaf user {
       type string;
       description
         "User name executing this script";
     }
     leaf client {
       type string;
       description
         "This client application performed the commit";
     }
     leaf comment {
       type string;
     }
     leaf log {
       type string;
       description
         "Log message for this commit";
     }
     leaf db-modified {
       type empty;
     }
     leaf new-db-revision {
       type uint32;
     }
     leaf old-db-revision {
       type uint32;
     }
   }
   grouping commit-synchronize-server-block {
     list commit-sync-jobs {
       key "job-id";
       description
         "Commit sync jobs details";
       leaf job-id {
         type int32;
         description
           "Job id";
       }
       leaf commit-sync-model {
         type string;
         description
           "Commit synchronize model";
       }
       leaf database {
         type string;
         description
           "Type of database";
       }
       leaf database-version {
         type string;
         description
           "New commit version";
       }
     }
   }
   grouping commit-server-information-block {
     leaf server-status {
       type string;
       description
         "Commit server status";
     }
     container jobs-detail {
       description
         "Jobs processed by commit server";
       list job {
         leaf job-id {
           type uint32;
           description
             "Job id";
         }
       }
     }
   }
   grouping commit-server-queue-information-block {
     list commit-server-queue {
       leaf queue-name {
         type string;
         description
           "Commit queue name";
       }
       list job {
         leaf job-id {
           type uint32;
           description
             "Job id";
         }
         leaf job-date {
           type string;
           description
             "Commit job modify date";
         }
         leaf job-status {
           type string;
           description
             "Commit job status";
         }
         leaf jobs-none {
           type empty;
         }
         leaf job-patch {
           type string;
           description
             "Job patch";
         }
       }
     }
   }
   grouping configuration-revision-information-block {
     leaf rollback-number {
       type int32;
       description
         "Show corresponding rollback number";
     }
     container load-configuration-results {
       leaf load-success {
         type empty;
         description
           "Load completed with no errors";
       }
       leaf load-error-count {
         type int32;
         description
           "Number of errors during load";
       }
       leaf diff-error-count {
         type int32;
         description
           "Number of errors";
       }
       leaf rollback-success {
         type empty;
         description
           "Rollback occurred";
       }
     }
     container configuration-information {
       leaf configuration-output {
         type string;
       }
       leaf json-output {
         type string;
       }
       container file-destination {
         leaf source-filename {
           type string;
         }
         leaf alias-filename {
           type string;
         }
         leaf export-data-type {
           type string;
           description
             "Type of data being exported";
         }
         leaf source-address {
           type string;
         }
         leaf routing-instance {
           type string;
         }
       }
       container configuration-detail {
         leaf indent {
           type int32;
         }
         container configuration-detail-line {
           leaf indent {
             type int32;
           }
           leaf detail-name {
             type string;
           }
           leaf detail-value {
             type string;
           }
           leaf detail-message {
             type string;
           }
         }
       }
     }
   }
   grouping database-usage-block {
     leaf maximum-size {
       type string;
       description
         "Show maximum size of database";
     }
     leaf current-size {
       type string;
       description
         "Show current database size on disk";
     }
     leaf actual-usage {
       type string;
       description
         "Show actual database usage";
     }
     leaf available-space {
       type string;
       description
         "Show available database space";
     }
     leaf memory-allocator-used {
       type string;
       description
         "Show memory allocator used";
     }
     leaf external-fragmentation {
       type string;
       description
         "Show external fragmentation space of the database";
     }
     leaf internal-fragmentation {
       type string;
       description
         "Show internal fragmentation space of the database";
     }
     leaf total-pages-allocated {
       type string;
       description
         "Show total number of pages allocated";
     }
     leaf total-pages-freed {
       type string;
       description
         "Show total number of pages freed";
     }
     leaf total-pages-reused {
       type string;
       description
         "Show pages reused";
     }
     leaf curr-active-pages {
       type string;
       description
         "Show current active pages";
     }
     leaf curr-free-pages {
       type string;
       description
         "Show current free pages";
     }
   }
   grouping database-status-information-block {
     list database-status {
       key "pid";
       leaf user {
         type string;
         description
           "User name executing this script";
       }
       leaf terminal {
         type string;
       }
       leaf pid {
         type int32;
         description
           "PID of the process that generated the event";
       }
       leaf start-time {
         type string;
       }
       leaf idle-time {
         type string;
         description
           "Time since the user last typed anything";
       }
       leaf commit-at {
         type empty;
       }
       leaf commit-script-running {
         type empty;
       }
       leaf exclusive {
         type empty;
       }
       leaf edit-path {
         type string;
       }
       leaf waiting-for-user-input {
         type empty;
       }
     }
   }
   grouping directory-list-block {
     list directory {
       description
         "Information about system directory usage";
       leaf directory-name {
         type string;
         description
           "Directory name";
       }
       list file-information {
         leaf file-name {
           type string;
           description
             "File name";
         }
         leaf file-symlink {
           type empty;
           description
             "File is a symlink";
         }
         leaf file-executable {
           type empty;
           description
             "File is executable";
         }
         leaf file-directory {
           type empty;
           description
             "File is a directory";
         }
         leaf file-symlink-target {
           type string;
           description
             "Symlink location";
         }
         leaf file-permissions {
           type string;
           description
             "File permissions";
         }
         leaf file-links {
           type int32;
           description
             "Number of links";
         }
         leaf file-owner {
           type string;
           description
             "File owner";
         }
         leaf file-group {
           type string;
           description
             "File group";
         }
         leaf file-size {
           type int32;
           description
             "File size";
         }
         leaf file-date {
           type int32;
           description
             "File date";
         }
       }
       leaf total-file-blocks {
         type int32;
         description
           "Total number of blocks used by files in this directory";
       }
       leaf total-files {
         type int32;
         description
           "Total number of files in this directory";
       }
     }
   }
   grouping system-login-password-expiry-information-block {
     leaf no-password-expiry {
       type empty;
       description
         "There is no expiry for passwords";
     }
     container password-expiry-users-table {
       list password-expiry-user-entry {
         description
           "Show password expiry information of a user";
         leaf password-expiry-user {
           type string;
           description
             "Password expiry user name";
         }
         leaf password-expiry-information {
           type string;
           description
             "Password expiry information";
         }
       }
     }
   }
   grouping system-login-lockout-information-block {
     leaf no-login-lockout {
       type empty;
       description
         "No users locked out from logins";
     }
     leaf no-login-lockout-user {
       type empty;
       description
         "User not locked out from logins";
     }
     container login-lockout-users-table {
       list login-lockout-user-entry {
         description
           "Login lockout information for a user";
         leaf login-lockout-user {
           type string;
           description
             "Name of user being locked out";
         }
         leaf login-lockout-start-time {
           type string;
           description
             "The time the lockout started";
         }
         leaf login-lockout-end-time {
           type string;
           description
             "The time the lockout ends";
         }
       }
     }
   }
   grouping alarm-information-block {
     container alarm-summary {
       description
         "Number of alarms currently active";
       leaf active-alarm-count {
         type int32;
         description
           "Number of active alarms";
       }
       leaf no-active-alarms {
         type empty;
         description
           "No active alarms";
       }
       leaf active-fpc-slot {
         type int32;
         description
           "FPC slot with active alarms";
       }
       leaf no-active-fpc-slot {
         type int32;
         description
           "FPC slot with non active alarms";
       }
     }
     list alarm-detail {
       description
         "Detailed information about an active alarm";
       leaf alarm-time {
         type string;
         description
           "Time of the alarm";
       }
       leaf alarm-class {
         type string;
         description
           "Class of the alarm";
       }
       leaf alarm-description {
         type string;
         description
           "Description of the alarm";
       }
       leaf alarm-short-description {
         type string;
         description
           "Short description of the alarm";
       }
       leaf alarm-type {
         type string;
         description
           "Type (class) of the alarm";
       }
     }
   }
   grouping system-alarm-reference-information-block {
     list alarm-reference-brief {
       leaf class {
         type string;
       }
       leaf severity {
         type string;
       }
       leaf reason {
         type string;
       }
     }
     list alarm-reference-detail {
       leaf class {
         type string;
       }
       leaf reason {
         type string;
       }
       leaf severity {
         type string;
       }
       leaf remedy {
         type string;
       }
     }
   }
   grouping unified-services-status-information-block {
     leaf unified-services-status {
       type string;
       description
         "Unified Services Status";
     }
   }
   grouping system-uptime-information-block {
     leaf time-source {
       type string;
       description
         "Time Source";
     }
     container system-uptime-information-brief {
       description
         "Uptime info across the system";
       leaf date-time {
         type string;
       }
       leaf time-length {
         type string;
       }
       leaf active-user-count-brief {
         type int32;
         description
           "Number of users currently logged in, across the system";
       }
     }
     container last-configured-time {
       description
         "Last configured time";
       leaf date-time {
         type string;
       }
       leaf time-length {
         type string;
       }
       leaf user {
         type string;
         description
           "User name executing this script";
       }
     }
     container current-time {
       description
         "Current time";
       leaf date-time {
         type string;
       }
     }
     container node-booted-time {
       description
         "Node booted time";
       leaf date-time {
         type string;
       }
       leaf time-length {
         type string;
       }
     }
     container system-booted-time {
       description
         "System booted time";
       leaf date-time {
         type string;
       }
       leaf time-length {
         type string;
       }
     }
     container protocols-started-time {
       description
         "Protocols started time";
       leaf date-time {
         type string;
       }
       leaf time-length {
         type string;
       }
     }
     container uptime-information {
       description
         "System uptime details";
       leaf date-time {
         type string;
       }
       leaf up-time {
         type string;
         description
           "Uptime in ascii format";
       }
       leaf active-user-count {
         type int32;
         description
           "Number of users currently logged in";
       }
       leaf load-average-1 {
         type string;
         description
           "Load average for last 1 minute";
       }
       leaf load-average-5 {
         type string;
         description
           "Load average for last 5 minutes";
       }
       leaf load-average-15 {
         type string;
         description
           "Load average for last 15 minutes";
       }
       container user-table {
         list user-entry {
           leaf user {
             type string;
             description
               "User name executing this script";
           }
           leaf tty {
             type string;
             description
               "Name of the terminal the user is on";
           }
           leaf from {
             type string;
             description
               "Host from which the user is logged on";
           }
           leaf login-time {
             type string;
             description
               "Time the user logged on";
           }
           leaf idle-time {
             type string;
             description
               "Time since the user last typed anything";
           }
           leaf command {
             type string;
           }
         }
         container process-table {
           list process-entry {
             leaf process-id {
               type int32;
               description
                 "Process identifier";
             }
             leaf command {
               type string;
             }
           }
         }
       }
     }
   }
   grouping macsec-license-information-block {
     leaf total-flex-only-macsec-bandwidth {
       type int32;
       description
         "Total flex only MACSec bandwidth";
     }
     leaf total-flex-capable-macsec-bandwidth {
       type int32;
       description
         "Total flex capable MACSec bandwidth";
     }
     leaf total-macsec-bandwidth {
       type int32;
       description
         "Total MACSec bandwidth";
     }
   }
   grouping license-summary-information-block {
     leaf licensing-mode {
       type string;
       description
         "Mode of license";
     }
     leaf licensing-persona {
       type string;
       description
         "Persona of license";
     }
     leaf last-sync-time {
       type string;
     }
     container license-usage-summary {
       description
         "Information about features licensed on this device";
       leaf features-used {
         type empty;
         description
           "Licensed features are being used";
       }
       leaf no-feature-used {
         type empty;
         description
           "No licensed feature is being used";
       }
       list feature-summary {
         key "name";
         leaf name {
           type string;
           description
             "Identifier for this object";
         }
         leaf used-licensed {
           type int32;
           description
             "Number used that require a license";
         }
         leaf licensed {
           type int32;
           description
             "Number available in valid licenses";
         }
         leaf needed {
           type int32;
           description
             "Number used that require a license above licensed count";
         }
         leaf validity-type {
           type string;
           description
             "Type of validity of the license";
         }
         leaf end-date {
           type string;
         }
         leaf description {
           type string;
           description
             "Description of feature";
         }
         leaf used-given {
           type int32;
           description
             "Number used that do not require a license";
         }
         container remaining-time {
           leaf remaining-validity-value {
             type int32;
             description
               "Integer value";
           }
           leaf remaining-validity-time-unit {
             type string;
             description
               "Unit of time measurement";
           }
         }
       }
     }
     container license-detail-usage-summary {
       description
         "Information about features licensed on this device";
       leaf no-feature-used {
         type empty;
         description
           "No licensed feature is being used";
       }
       leaf features-used {
         type empty;
         description
           "Licensed features are being used";
       }
       list feature-summary {
         key "name";
         leaf name {
           type string;
           description
             "Identifier for this object";
         }
         leaf used-licensed {
           type int32;
           description
             "Number used that require a license";
         }
         leaf licensed {
           type int32;
           description
             "Number available in valid licenses";
         }
         leaf needed {
           type int32;
           description
             "Number used that require a license above licensed count";
         }
         leaf license-available {
           type int32;
           description
             "Number of network license available";
         }
         leaf validity-type {
           type string;
           description
             "Type of validity of the license";
         }
         leaf end-date {
           type string;
         }
         leaf description {
           type string;
           description
             "Description of feature";
         }
         leaf used-given {
           type int32;
           description
             "Number used that do not require a license";
         }
         container remaining-time {
           leaf remaining-validity-value {
             type int32;
             description
               "Integer value";
           }
           leaf remaining-validity-time-unit {
             type string;
             description
               "Unit of time measurement";
           }
         }
       }
     }
     container license-information {
       description
         "Information about feature licenses installed on device";
       leaf licenses-installed {
         type empty;
         description
           "Feature licenses are installed";
       }
       leaf no-licenses-installed {
         type empty;
         description
           "No feature licenses are installed";
       }
       list license {
         key "name";
         leaf name {
           type string;
           description
             "Identifier for this object";
         }
         leaf license-sku-name {
           type string;
           description
             "SKU name of this license key";
         }
         leaf license-version {
           type int32;
           description
             "Version of license";
         }
         leaf license-order-type {
           type string;
           description
             "Type of license order type";
         }
         leaf license-type {
           type string;
           description
             "Type of license";
         }
         leaf device-reference {
           type string;
           description
             "License is tied to this device";
         }
         leaf num-units {
           type int32;
           description
             "Number of units of the license";
         }
         leaf software-sn {
           type string;
           description
             "License is tied to this Software Serial Number";
         }
         leaf customer-reference {
           type string;
           description
             "Customer id of the license";
         }
         leaf release-version {
           type string;
           description
             "License defines the JUNOS release version it is tied to.";
         }
         leaf upgrade-license {
           type string;
           description
             "License defines if this is a software upgrade license tied to 
             JUNOS release";
         }
         leaf group-reference {
           type string;
           description
             "License is tied to this group";
         }
         leaf-list group-define {
           type string;
           description
             "License defines device to be part of this license group";
         }
         leaf-list unsupported-attribute {
           type int32;
           description
             "An attribute that is not recognized by this implementation";
         }
         leaf lease-end-date {
           type string;
         }
         leaf-list license-state {
           type string;
           description
             "License state";
         }
         container feature-block {
           list feature {
             key "name";
             description
               "A single feature instance";
             leaf name {
               type string;
               description
                 "Identifier for this object";
             }
             leaf description {
               type string;
               description
                 "Description of feature";
             }
             leaf num-units {
               type int32;
               description
                 "Number of units of the license";
             }
             container validity-information {
               leaf validity-type {
                 type string;
                 description
                   "Type of validity of the license";
               }
               leaf-list license-state {
                 type string;
                 description
                   "License state";
               }
               container original-validity {
                 leaf original-validity-value {
                   type int32;
                   description
                     "Integer value";
                 }
                 leaf original-validity-time-unit {
                   type string;
                   description
                     "Unit of time measurement";
                 }
               }
               container remaining-time {
                 leaf remaining-validity-value {
                   type int32;
                   description
                     "Integer value";
                 }
                 leaf remaining-validity-time-unit {
                   type string;
                   description
                     "Unit of time measurement";
                 }
               }
               leaf start-date {
                 type string;
               }
               leaf end-date {
                 type string;
               }
             }
           }
         }
       }
     }
   }
   grouping license-information-block {
     leaf no-licenses-installed {
       type empty;
       description
         "No feature licenses are installed";
     }
     leaf licenses-installed {
       type empty;
       description
         "Feature licenses are installed";
     }
     list license {
       key "name";
       leaf name {
         type string;
         description
           "Identifier for this object";
       }
       leaf license-sku-name {
         type string;
         description
           "SKU name of this license key";
       }
       leaf license-version {
         type int32;
         description
           "Version of license";
       }
       leaf license-order-type {
         type string;
         description
           "Type of license order type";
       }
       leaf license-type {
         type string;
         description
           "Type of license";
       }
       leaf device-reference {
         type string;
         description
           "License is tied to this device";
       }
       leaf num-units {
         type int32;
         description
           "Number of units of the license";
       }
       leaf software-sn {
         type string;
         description
           "License is tied to this Software Serial Number";
       }
       leaf customer-reference {
         type string;
         description
           "Customer id of the license";
       }
       leaf release-version {
         type string;
         description
           "License defines the JUNOS release version it is tied to.";
       }
       leaf upgrade-license {
         type string;
         description
           "License defines if this is a software upgrade license tied to 
           JUNOS release";
       }
       leaf group-reference {
         type string;
         description
           "License is tied to this group";
       }
       leaf-list group-define {
         type string;
         description
           "License defines device to be part of this license group";
       }
       leaf-list unsupported-attribute {
         type int32;
         description
           "An attribute that is not recognized by this implementation";
       }
       leaf lease-end-date {
         type string;
       }
       leaf-list license-state {
         type string;
         description
           "License state";
       }
       container feature-block {
         list feature {
           key "name";
           description
             "A single feature instance";
           leaf name {
             type string;
             description
               "Identifier for this object";
           }
           leaf description {
             type string;
             description
               "Description of feature";
           }
           leaf num-units {
             type int32;
             description
               "Number of units of the license";
           }
           container validity-information {
             leaf validity-type {
               type string;
               description
                 "Type of validity of the license";
             }
             leaf-list license-state {
               type string;
               description
                 "License state";
             }
             container original-validity {
               leaf original-validity-value {
                 type int32;
                 description
                   "Integer value";
               }
               leaf original-validity-time-unit {
                 type string;
                 description
                   "Unit of time measurement";
               }
             }
             container remaining-time {
               leaf remaining-validity-value {
                 type int32;
                 description
                   "Integer value";
               }
               leaf remaining-validity-time-unit {
                 type string;
                 description
                   "Unit of time measurement";
               }
             }
             leaf start-date {
               type string;
             }
             leaf end-date {
               type string;
             }
           }
         }
       }
     }
   }
   grouping license-key-information-block {
     list license-key {
       key "name";
       leaf name {
         type string;
         description
           "Identifier for this object";
       }
       leaf key-data {
         type string;
         description
           "Textual license key";
       }
     }
   }
   grouping license-usage-summary-block {
     leaf features-used {
       type empty;
       description
         "Licensed features are being used";
     }
     leaf no-feature-used {
       type empty;
       description
         "No licensed feature is being used";
     }
     list feature-summary {
       key "name";
       leaf name {
         type string;
         description
           "Identifier for this object";
       }
       leaf used-licensed {
         type int32;
         description
           "Number used that require a license";
       }
       leaf licensed {
         type int32;
         description
           "Number available in valid licenses";
       }
       leaf needed {
         type int32;
         description
           "Number used that require a license above licensed count";
       }
       leaf validity-type {
         type string;
         description
           "Type of validity of the license";
       }
       leaf end-date {
         type string;
       }
       leaf description {
         type string;
         description
           "Description of feature";
       }
       leaf used-given {
         type int32;
         description
           "Number used that do not require a license";
       }
       container remaining-time {
         leaf remaining-validity-value {
           type int32;
           description
             "Integer value";
         }
         leaf remaining-validity-time-unit {
           type string;
           description
             "Unit of time measurement";
         }
       }
     }
   }
   grouping license-feature-list-information-block {
     list feature-info {
       key "name";
       leaf feature-id {
         type int32;
         description
           "Feature Id";
       }
       leaf name {
         type string;
         description
           "Identifier for this object";
       }
     }
   }
   grouping license-fpc-information-block {
     container flex-only-fpc-bandwidth-info {
       description
         "Flex only linecards bandwidth information";
       leaf fpc-header {
         type empty;
         description
           "FPC being used on device";
       }
       leaf no-fpc-used {
         type empty;
         description
           "No FPC used on the device";
       }
       container fpc-bandwidth {
         leaf license-advance-bandwidth {
           type int32;
           description
             "Bandwidth usage in active ports";
         }
         container fpc-info-summary {
           description
             "Information about fpc bandwidth usage on this device";
           list fpc-info {
             key "fpc";
             leaf fpc {
               type int32;
               description
                 "FPC slot";
             }
             leaf fpc-serial-number {
               type string;
               description
                 "FPC serial number";
             }
           }
         }
       }
     }
     container flex-capable-fpc-bandwidth-info {
       description
         "Flex capable linecards bandwidth information";
       leaf fpc-header {
         type empty;
         description
           "FPC being used on device";
       }
       leaf no-fpc-used {
         type empty;
         description
           "No FPC used on the device";
       }
       container fpc-bandwidth {
         leaf license-advance-bandwidth {
           type int32;
           description
             "Bandwidth usage in active ports";
         }
         container fpc-info-summary {
           description
             "Information about fpc bandwidth usage on this device";
           list fpc-info {
             key "fpc";
             leaf fpc {
               type int32;
               description
                 "FPC slot";
             }
             leaf fpc-serial-number {
               type string;
               description
                 "FPC serial number";
             }
           }
         }
       }
     }
   }
   grouping license-bandwidth-summary-block {
     leaf license-advance-bandwidth {
       type int32;
       description
         "Bandwidth usage in active ports";
     }
   }
   grouping license-bandwidth-information-block {
     leaf no-bandwidth-used {
       type empty;
       description
         "No active ports on the device";
     }
     leaf bandwidth-used {
       type empty;
       description
         "License bandwidth being used on device";
     }
     list bandwidth-summary {
       leaf port-name {
         type string;
         description
           "Port used for bandwidth";
       }
       leaf port-speed {
         type int32;
         description
           "Bandwidth Usage (in gbps)";
       }
       leaf license-bandwidth-tier {
         type string;
         description
           "License bandwidth tier";
       }
     }
   }
   grouping license-linecard-bandwidth-block {
     leaf no-flex-only-linecards-used {
       type empty;
       description
         "No flex-only linecard is being used";
     }
     leaf flex-only-linecards-used {
       type empty;
       description
         "Flex-only linecards are being used";
     }
     list feature-summary {
       key "name";
       leaf name {
         type string;
         description
           "Identifier for this object";
       }
       leaf used-licensed {
         type int32;
         description
           "Number used that require a license";
       }
       leaf licensed {
         type int32;
         description
           "Number available in valid licenses";
       }
       leaf needed {
         type int32;
         description
           "Number used that require a license above licensed count";
       }
       leaf description {
         type string;
         description
           "Description of feature";
       }
       leaf used-given {
         type int32;
         description
           "Number used that do not require a license";
       }
     }
   }
   grouping system-information-block {
     leaf host-name {
       type string;
       description
         "Hostname of router";
     }
     leaf hardware-model {
       type string;
       description
         "Platform";
     }
     leaf flavor {
       type string;
       description
         "System flavor (cSRX only : #CPU-#G)";
     }
     leaf os-name {
       type string;
       description
         "Operating System Name";
     }
     leaf os-version {
       type string;
       description
         "Operating System Version";
     }
     leaf configured-host-name {
       type string;
       description
         "Configured hostname of the router";
     }
     leaf serial-number {
       type string;
       description
         "Chassis Serial Number";
     }
     leaf virtual-chassis {
       type empty;
       description
         "System is a Virtual Chassis";
     }
     leaf cluster-node {
       type empty;
       description
         "Node of a cluster";
     }
     leaf blade-server {
       type empty;
       description
         "System is a Blade Server";
     }
     leaf aggregation-device {
       type string;
       description
         "System is an Aggregation Device";
     }
     list package-information {
       key "name";
       leaf name {
         type string;
         description
           "Syslog message tag name";
       }
       leaf version {
         type string;
         description
           "JUNOS version";
       }
       leaf package-name {
         type string;
         description
           "Name of software package";
       }
     }
   }
   grouping system-timex-information-block {
     leaf sync-status {
       type int32;
       description
         "Sync status";
     }
     leaf offset-seconds {
       type decimal64 {
         fraction-digits 9;
       }
       description
         "Offset";
     }
     leaf frequency-adjustment-ratio {
       type decimal64 {
         fraction-digits 9;
       }
       description
         "Frequency adjustment in parts per million (ppm)";
     }
     leaf maxerror-seconds {
       type decimal64 {
         fraction-digits 9;
       }
       description
         "Maximum error in seconds (s)";
     }
     leaf estimated-error-seconds {
       type decimal64 {
         fraction-digits 9;
       }
       description
         "Estimated error in seconds (s)";
     }
     leaf clock-status {
       type int32;
       description
         "Clock status flag";
     }
     leaf loop-time-constant {
       type int32;
       description
         "Phase-Locked Loop (PLL) time constant";
     }
     leaf tick-seconds {
       type decimal64 {
         fraction-digits 9;
       }
       description
         "Seconds added per clock tick";
     }
     leaf pps-frequency-hertz {
       type decimal64 {
         fraction-digits 9;
       }
       description
         "Pulse Per Second (PPS) frequency adjustment in ppm";
     }
     leaf pps-jitter-seconds {
       type decimal64 {
         fraction-digits 9;
       }
       description
         "PPS jitter in seconds (s)";
     }
     leaf pps-shift-seconds {
       type int32;
       description
         "Interval duration in seconds (s)";
     }
     leaf pps-stability-hertz {
       type decimal64 {
         fraction-digits 9;
       }
       description
         "PPS stability in parts per million (ppm)";
     }
     leaf pps-jitter-total {
       type int32;
       description
         "Number of times jitter limit was exceeded";
     }
     leaf pps-calibration-total {
       type int32;
       description
         "Number of successful calibration intervals";
     }
     leaf pps-error-total {
       type int32;
       description
         "Number of calibration errors";
     }
     leaf pps-stability-exceeded-total {
       type int32;
       description
         "Number of times the stability limit was exceeded";
     }
     leaf tai-offset-seconds {
       type int32;
       description
         "International Atomic Time (TAI) offset in seconds";
     }
   }
   grouping yang-package-information-block {
     list yang-package {
       leaf package-id {
         type string;
         description
           "Package ID";
       }
       leaf yang-modules {
         type string;
         description
           "YANG module(s)";
       }
       leaf action-scripts {
         type string;
         description
           "Action script(s)";
       }
       leaf trans-scripts {
         type string;
         description
           "Translation script(s)";
       }
       leaf trans-scripts-status {
         type string;
         description
           "Translation script(s) status";
       }
       leaf proxy-xml-yang-modules {
         type string;
         description
           "XML proxy YANG module(s)";
       }
       leaf snmp-yang-modules {
         type string;
         description
           "SNMP custom MIB YANG module(s)";
       }
     }
   }
   grouping clients-block {
     container client {
       leaf client-name {
         type string;
         description
           "The registered name of the client";
       }
       leaf client-status {
         type string;
         description
           "The state of the client (attached or detached)";
       }
       leaf client-last-heartbeat {
         type string;
         description
           "The timestamp of the last heartbeat message received from the 
           client";
       }
     }
   }
   grouping endpoints-block {
     list endpoint {
       leaf name {
         type string;
       }
       leaf flapped {
         type uint32;
         description
           "No. of times Endpoint flapped";
       }
       leaf status {
         type string;
       }
       leaf uptime {
         type uint32;
       }
       container cpri {
         leaf channel-prio {
           type string;
         }
         leaf channel-status {
           type string;
         }
         leaf gtp-proxy-smd-ep {
           type string;
         }
         leaf gtp-proxy-smd-ep-status {
           type string;
         }
         leaf smd-gtp-proxy-ep {
           type string;
         }
         leaf smd-gtp-proxy-ep-status {
           type string;
         }
         leaf gtp-proxy-smd-tx {
           type uint64;
         }
         leaf gtp-proxy-smd-tx-drop {
           type uint64;
         }
         leaf smd-gtp-proxy-rx {
           type uint64;
         }
         leaf pkts-clients-rx {
           type uint64;
         }
         leaf pkts-aggr-rx {
           type uint64;
         }
         leaf pkts-enqueue-rx-fail {
           type uint64;
         }
         leaf pkts-terminated-locally {
           type uint64;
         }
         leaf pkts-clients-cp-to-up {
           type uint64;
         }
         leaf pkts-clients-up-to-cp {
           type uint64;
         }
         leaf pkts-aggr-cp-to-up {
           type uint64;
         }
         leaf pkts-aggr-cp-to-up-fail {
           type uint64;
         }
         leaf pkts-aggr-up-to-cp {
           type uint64;
         }
         leaf pkts-aggr-up-to-cp-fail {
           type uint64;
         }
         leaf pkts-injected-locally-to-up {
           type uint64;
         }
         leaf pkts-injected-locally-to-cp {
           type uint64;
         }
         leaf last-local-seq-num-tx {
           type uint32;
         }
         leaf last-local-seq-num-rx {
           type uint32;
         }
         leaf last-remote-seq-num-rx {
           type uint32;
         }
         leaf tot-local-echo-pkt-rx {
           type uint64;
         }
         leaf tot-remote-echo-pkt-rx {
           type uint32;
         }
         leaf num-echo-lost {
           type uint32;
         }
         list cpri-status {
           leaf channel-prio {
             type string;
           }
           leaf channel-status {
             type string;
           }
           leaf gtp-proxy-smd-ep {
             type string;
           }
           leaf gtp-proxy-smd-ep-status {
             type string;
           }
           leaf smd-gtp-proxy-ep {
             type string;
           }
           leaf smd-gtp-proxy-ep-status {
             type string;
           }
         }
         list cpri-info {
           leaf channel-prio {
             type string;
           }
           leaf gtp-proxy-smd-ep {
             type string;
           }
           leaf gtp-proxy-smd-tx {
             type uint64;
           }
           leaf gtp-proxy-smd-tx-drop {
             type uint64;
           }
           leaf smd-gtp-proxy-ep {
             type string;
           }
           leaf smd-gtp-proxy-rx {
             type uint64;
           }
           leaf pkts-clients-rx {
             type uint64;
           }
           leaf pkts-aggr-rx {
             type uint64;
           }
           leaf pkts-enqueue-rx-fail {
             type uint64;
           }
           leaf pkts-terminated-locally {
             type uint64;
           }
           leaf pkts-clients-cp-to-up {
             type uint64;
           }
           leaf pkts-clients-up-to-cp {
             type uint64;
           }
           leaf pkts-aggr-cp-to-up {
             type uint64;
           }
           leaf pkts-aggr-cp-to-up-fail {
             type uint64;
           }
           leaf pkts-aggr-up-to-cp {
             type uint64;
           }
           leaf pkts-aggr-up-to-cp-fail {
             type uint64;
           }
           leaf pkts-injected-locally-to-up {
             type uint64;
           }
           leaf pkts-injected-locally-to-cp {
             type uint64;
           }
           leaf last-local-seq-num-tx {
             type uint32;
           }
           leaf last-local-seq-num-rx {
             type uint32;
           }
           leaf last-remote-seq-num-rx {
             type uint32;
           }
           leaf tot-local-echo-pkt-rx {
             type uint64;
           }
           leaf tot-remote-echo-pkt-rx {
             type uint32;
           }
           leaf num-echo-lost {
             type uint32;
           }
         }
       }
       container dtls {
         leaf state {
           type string;
         }
         leaf mode {
           type string;
         }
         leaf encrypt-pkt-rx {
           type uint64;
         }
         leaf encrypt-pkt-tx {
           type uint64;
         }
         leaf handshake-pkt-rx {
           type uint64;
         }
         leaf handshake-pkt-tx {
           type uint64;
         }
         leaf app-pkt-dropped-tx {
           type uint64;
         }
         leaf sess-restart {
           type uint64;
         }
         leaf handshake-restart {
           type uint64;
         }
       }
       container client-conn {
         leaf conn-down-events {
           type uint64;
         }
         leaf conn-up-events {
           type uint64;
         }
         leaf flow-control-invoked {
           type uint64;
         }
         leaf flow-control-released {
           type uint64;
         }
         leaf pkts-to-daemon {
           type uint64;
         }
         leaf pkts-from-daemon {
           type uint64;
         }
         leaf msgs-to-daemon {
           type uint64;
         }
         leaf msgs-from-daemon {
           type uint64;
         }
       }
       container ipcconn {
         leaf sends-total {
           type uint32;
         }
         leaf sends-clean {
           type uint32;
         }
         leaf sends-pending {
           type uint32;
         }
         leaf sends-partial {
           type uint32;
         }
         leaf sends-terminal {
           type uint32;
         }
         leaf sends-pending-serviced {
           type uint32;
         }
         leaf sends-stored {
           type uint32;
         }
         leaf sends-store-failed {
           type uint32;
         }
         leaf sends-failed-total {
           type uint32;
         }
         leaf egress-queue-dequeues {
           type uint32;
         }
         leaf egress-queue-enqueues {
           type uint32;
         }
         leaf egress-queue-size {
           type uint32;
         }
         leaf egress-queue-accum-time {
           type uint32;
         }
         leaf receives {
           type uint32;
         }
         leaf receives-serviced {
           type uint32;
         }
         leaf recv-msg-cb-disables {
           type uint32;
         }
         leaf recv-msg-cb-enables {
           type uint32;
         }
       }
       container pfcp {
         leaf msg-name {
           type string;
           description
             "PFCP msg name";
         }
         leaf msg-count {
           type uint64;
           description
             "PFCP msg counter";
         }
         leaf rx-total {
           type uint32;
           description
             "Packets received";
         }
         leaf tx-total {
           type uint32;
           description
             "Packets transmitted";
         }
         leaf rx-invalid {
           type uint64;
           description
             "Invalid packets received";
         }
         leaf tx-err {
           type uint64;
           description
             "Transmit errors";
         }
         leaf max-retx {
           type uint64;
           description
             "Maximum retransmission count";
         }
         leaf retx {
           type uint64;
           description
             "Retransmission count";
         }
         leaf hb-failure {
           type uint32;
           description
             "Heartbeat failure count";
         }
         leaf avg-rtt-secs {
           type uint32;
           description
             "Average round trip time in seconds";
         }
         leaf ep-pfcp-tx-info {
           type string;
         }
         container msg-list {
           list msg-entry {
             description
               "PFCP msg counter";
             leaf msg-name {
               type string;
               description
                 "PFCP msg name";
             }
             leaf msg-count {
               type uint64;
               description
                 "PFCP msg counter";
             }
           }
         }
         container rx-info {
           description
             "PFCP Rx information";
           leaf rx-total {
             type uint32;
             description
               "Packets received";
           }
           leaf rx-invalid {
             type uint64;
             description
               "Invalid packets received";
           }
           list msg-entry {
             description
               "PFCP msg counter";
             leaf msg-name {
               type string;
               description
                 "PFCP msg name";
             }
             leaf msg-count {
               type uint64;
               description
                 "PFCP msg counter";
             }
           }
         }
         container tx-info {
           description
             "PFCP tx information";
           leaf tx-total {
             type uint32;
             description
               "Packets transmitted";
           }
           leaf avg-rtt-secs {
             type uint32;
             description
               "Average round trip time in seconds";
           }
           leaf tx-err {
             type uint64;
             description
               "Transmit errors";
           }
           leaf max-retx {
             type uint64;
             description
               "Maximum retransmission count";
           }
           leaf retx {
             type uint64;
             description
               "Retransmission count";
           }
           list msg-entry {
             description
               "PFCP msg counter";
             leaf msg-name {
               type string;
               description
                 "PFCP msg name";
             }
             leaf msg-count {
               type uint64;
               description
                 "PFCP msg counter";
             }
           }
         }
       }
       container repss {
         leaf chain-len {
           type uint32;
           description
             "Chain length";
         }
         leaf unique-id {
           type uint32;
           description
             "Unique Id";
         }
         leaf seq-num {
           type uint32;
           description
             "Sequence no.";
         }
       }
       container transport {
         leaf tmsg-name {
           type string;
           description
             "Transport msg name";
         }
         leaf tmsg-count {
           type uint32;
           description
             "Transport msg counter";
         }
         container tx {
           description
             "Transport Tx information";
           list tx-tmsg-entry {
             leaf tmsg-name {
               type string;
               description
                 "Transport msg name";
             }
             leaf tmsg-count {
               type uint32;
               description
                 "Transport msg counter";
             }
           }
         }
         container rx {
           description
             "Transport Rx information";
           list rx-tmsg-entry {
             leaf tmsg-name {
               type string;
               description
                 "Transport msg name";
             }
             leaf tmsg-count {
               type uint32;
               description
                 "Transport msg counter";
             }
           }
         }
       }
       leaf security {
         type string;
         description
           "Security status";
       }
       leaf last-updated {
         type uint32;
       }
     }
   }
   grouping services-block {
     container evpn {
       container evpn-vxlan {
         container peer-summary {
           leaf name {
             type string;
             description
               "Name";
           }
           leaf status {
             type string;
             description
               "Status";
           }
         }
         container servers {
           list server {
             leaf name {
               type string;
               description
                 "Name";
             }
             leaf status {
               type string;
               description
                 "Status";
             }
           }
           list server-detail {
             leaf name {
               type string;
               description
                 "Name";
             }
             leaf status {
               type string;
               description
                 "Status";
             }
             container interfaces {
               list interface {
                 leaf name {
                   type string;
                   description
                     "Name";
                 }
                 leaf oper-status {
                   type string;
                   description
                     "Operation status";
                 }
                 leaf admin-status {
                   type string;
                   description
                     "Admin status";
                 }
                 leaf ae-bundle-name {
                   type string;
                   description
                     "Ae name";
                 }
               }
             }
             list lldp {
               leaf local-interface-name {
                 type string;
                 description
                   "Local interface name";
               }
               leaf local-interface-status {
                 type string;
                 description
                   "Local interface status";
               }
               leaf parent-local-interface-name {
                 type string;
                 description
                   "Parent local interface name";
               }
             }
             list lacp {
               leaf name {
                 type string;
                 description
                   "Name";
               }
               leaf receive-state {
                 type string;
                 description
                   "Recieve state";
               }
               leaf transmit-state {
                 type string;
                 description
                   "Transmit state";
               }
             }
           }
         }
         container peer-detail {
           leaf name {
             type string;
             description
               "Name";
           }
           leaf status {
             type string;
             description
               "Status";
           }
           container interfaces {
             list interface {
               leaf name {
                 type string;
                 description
                   "Name";
               }
               leaf oper-status {
                 type string;
                 description
                   "Operation status";
               }
               leaf admin-status {
                 type string;
                 description
                   "Admin status";
               }
               leaf ae-bundle-name {
                 type string;
                 description
                   "Ae name";
               }
             }
           }
           list lldp {
             leaf local-interface-name {
               type string;
               description
                 "Local interface name";
             }
             leaf local-interface-status {
               type string;
               description
                 "Local interface status";
             }
             leaf parent-local-interface-name {
               type string;
               description
                 "Parent local interface name";
             }
           }
           list lacp {
             leaf name {
               type string;
               description
                 "Name";
             }
             leaf receive-state {
               type string;
               description
                 "Recieve state";
             }
             leaf transmit-state {
               type string;
               description
                 "Transmit state";
             }
           }
         }
         container loopback {
           leaf name {
             type string;
             description
               "Name";
           }
           leaf status {
             type string;
             description
               "Status";
           }
         }
         container vtep {
           leaf name {
             type string;
             description
               "Name";
           }
           leaf status {
             type string;
             description
               "Status";
           }
         }
         container underlay {
           leaf name {
             type string;
             description
               "Name";
           }
           leaf status {
             type string;
             description
               "Status";
           }
         }
         container overlay {
           leaf name {
             type string;
             description
               "Name";
           }
           leaf status {
             type string;
             description
               "Status";
           }
         }
         container sync-check {
           container forwarding-state {
             leaf routing-instance {
               type string;
               description
                 "Routing instance";
             }
             leaf vlan-id {
               type string;
               description
                 "Vlan id";
             }
             leaf status {
               type string;
               description
                 "Status";
             }
           }
         }
       }
     }
     list services-brief {
       leaf service-name {
         type string;
         description
           "The registered name of a service";
       }
       leaf service-status {
         type string;
         description
           "The status of service";
       }
       leaf service-state {
         type string;
         description
           "The state of service";
       }
       leaf service-ep-count {
         type uint32;
         description
           "Total number of Endpoints";
       }
       leaf service-healthy-ep-count {
         type uint32;
         description
           "Total number of Healthy Endpoints";
       }
     }
   }
   grouping service-block {
     container service-detail {
       container service-information {
         leaf service-name {
           type string;
           description
             "The registered name of a service";
         }
         leaf service-status {
           type string;
           description
             "The status of service";
         }
         leaf service-state {
           type string;
           description
             "The state of service";
         }
         leaf restarted {
           type uint32;
           description
             "Service restart count";
         }
         leaf last-updated {
           type uint32;
           description
             "Time since last upated";
         }
         leaf cpu-util {
           type uint32;
         }
         leaf mem-util {
           type uint32;
         }
       }
     }
   }
   grouping subscriber-management-user-plane-associations-block {
     leaf assoc-cp-name {
       type string;
       description
         "The administratively assigned name of the control plane";
     }
     leaf assoc-cp-address {
       type string;
       description
         "The IP address of the user plane";
     }
     leaf assoc-cp-state {
       type string;
       description
         "The status of association";
     }
     leaf assoc-cp-assoc-time {
       type string;
       description
         "The time that the user plane established the association";
     }
     leaf assoc-cp-assoc-updates {
       type uint64;
       description
         "The number of association updates requests from this user plane";
     }
   }
   grouping subscriber-management-user-plane-clients-block {
     leaf client-name {
       type string;
       description
         "The registered name of the client";
     }
     leaf client-status {
       type string;
       description
         "The state of the client (attached or detached)";
     }
     leaf client-last-heartbeat {
       type string;
       description
         "The timestamp of the last heartbeat message received from the 
         client";
     }
   }
   grouping subscriber-management-user-plane-services-block {
     list subscriber-management-services-brief {
       leaf service-name {
         type string;
         description
           "The registered name of a service";
       }
       leaf service-status {
         type string;
         description
           "The status of service";
       }
       leaf service-state {
         type string;
         description
           "The state of service";
       }
       leaf service-ep-count {
         type uint32;
         description
           "Total number of Endpoints";
       }
       leaf service-healthy-ep-count {
         type uint32;
         description
           "Total number of Healthy Endpoints";
       }
     }
   }
   grouping subscriber-management-control-plane-detail-block {
     leaf control-plane-addr {
       type string;
       description
         "Address of control plane";
     }
   }
   grouping subscriber-management-route-information-block {
     list subscriber-management-route {
       description
         "Information about the IPv4/IPv6 subscriber-management route";
       leaf route-nh-index {
         type int32;
         description
           "Index of next-hop associated with the route";
       }
       leaf pseudo-ifl-index {
         type int32;
         description
           "Pseudo IFL index";
       }
       leaf nh-bbe-index {
         type int32;
         description
           "Next-hop BBE index";
       }
       leaf nh-ref-count {
         type int32;
         description
           "Next-hop reference count";
       }
       leaf nh-flags {
         type string;
         description
           "Next-hop flags";
       }
       leaf address-family {
         type string;
         description
           "Route address family";
       }
       leaf routing-instance {
         type string;
         description
           "Routing instance associated with the route";
       }
       leaf krt-table-kernel-id {
         type int32;
         description
           "Kernel identifier for table";
       }
       leaf local-route-count {
         type int32;
         description
           "Number of local routes in this routing instance";
       }
       leaf access-route-count {
         type int32;
         description
           "Number of access routes in this routing instance";
       }
       leaf access-int-route-count {
         type int32;
         description
           "Number of access-internal routes in this routing instance";
       }
       leaf kernel-route-count {
         type int32;
         description
           "Number of kernel routes in this routing instance";
       }
       leaf dirty-local-route-count {
         type int32;
         description
           "Number of incomplete local routes in this routing instance";
       }
       leaf dirty-access-route-count {
         type int32;
         description
           "Number of incomplete access routes in this routing instance";
       }
       leaf dirty-access-int-route-count {
         type int32;
         description
           "Number of incomplete access-internal routes in this routing 
           instance";
       }
       leaf dirty-kernel-route-count {
         type int32;
         description
           "Number of incomplete kernel routes in this routing instance";
       }
       leaf dirty-inflight-route-count {
         type int32;
         description
           "Number of incomplete inflight routes in this routing instance";
       }
       leaf discard-route-count {
         type int32;
         description
           "Number of discard routes in this routing instance";
       }
       leaf gateway-route-count {
         type int32;
         description
           "Number of gateway routes in this routing instance";
       }
       leaf gateway-route-pending-count {
         type int32;
         description
           "Number of gateway routes pending in this routing instance";
       }
       leaf up-name {
         type string;
         description
           "Name of the user plane node";
       }
       leaf route-prefix {
         type jt:ipaddr;
         description
           "IPv4 or IPv6 prefix for the route";
       }
       leaf route-type {
         type string;
         description
           "Route type associated with the route";
       }
       leaf interface-name {
         type string;
         description
           "Name of the interface associated with the route";
       }
       leaf route-proto-type {
         type string;
         description
           "Protocol associated with the route";
       }
       leaf route-intf-index {
         type uint32;
         description
           "Index of interface associated with the route";
       }
       leaf route-int-intf-index {
         type uint32;
         description
           "Index of internal interface associated with the route";
       }
       leaf route-index {
         type int32;
         description
           "Route index associated with the route";
       }
       leaf route-tag {
         type int32;
         description
           "Route tag";
       }
       leaf route-metric {
         type int32;
         description
           "Route metric";
       }
       leaf route-preference {
         type int32;
         description
           "Route preference";
       }
       leaf route-tag2 {
         type int32;
         description
           "Route tag2";
       }
       leaf route-ref-count {
         type int32;
         description
           "Route reference count";
       }
       leaf mac-addr {
         type jt:mac-addr;
         description
           "Media access control (hardware) address associated with the 
           route";
       }
       leaf route-flags {
         type string;
         description
           "Route flags";
       }
     }
     container subscriber-management-route-nh {
       leaf route-nh-index {
         type int32;
         description
           "Index of next-hop associated with the route";
       }
       leaf pseudo-ifl-index {
         type int32;
         description
           "Pseudo IFL index";
       }
       leaf nh-bbe-index {
         type int32;
         description
           "Next-hop BBE index";
       }
       leaf nh-ref-count {
         type int32;
         description
           "Next-hop reference count";
       }
       leaf nh-flags {
         type string;
         description
           "Next-hop flags";
       }
       leaf address-family {
         type string;
         description
           "Route address family";
       }
     }
     list subscriber-management-route-summary {
       description
         "Summarized information about the IPv4/IPv6 subscriber-management 
         routes";
       leaf routing-instance {
         type string;
         description
           "Routing instance associated with the route";
       }
       leaf krt-table-kernel-id {
         type int32;
         description
           "Kernel identifier for table";
       }
       leaf address-family {
         type string;
         description
           "Route address family";
       }
       leaf local-route-count {
         type int32;
         description
           "Number of local routes in this routing instance";
       }
       leaf access-route-count {
         type int32;
         description
           "Number of access routes in this routing instance";
       }
       leaf access-int-route-count {
         type int32;
         description
           "Number of access-internal routes in this routing instance";
       }
       leaf kernel-route-count {
         type int32;
         description
           "Number of kernel routes in this routing instance";
       }
       leaf dirty-local-route-count {
         type int32;
         description
           "Number of incomplete local routes in this routing instance";
       }
       leaf dirty-access-route-count {
         type int32;
         description
           "Number of incomplete access routes in this routing instance";
       }
       leaf dirty-access-int-route-count {
         type int32;
         description
           "Number of incomplete access-internal routes in this routing 
           instance";
       }
       leaf dirty-kernel-route-count {
         type int32;
         description
           "Number of incomplete kernel routes in this routing instance";
       }
       leaf dirty-inflight-route-count {
         type int32;
         description
           "Number of incomplete inflight routes in this routing instance";
       }
       leaf discard-route-count {
         type int32;
         description
           "Number of discard routes in this routing instance";
       }
       leaf gateway-route-count {
         type int32;
         description
           "Number of gateway routes in this routing instance";
       }
       leaf gateway-route-pending-count {
         type int32;
         description
           "Number of gateway routes pending in this routing instance";
       }
       leaf up-name {
         type string;
         description
           "Name of the user plane node";
       }
     }
   }
   grouping subscriber-management-ipv6-ra-block {
     list ipv6-ra-interface {
       leaf interface-name {
         type string;
         description
           "Name of the interface associated with the route";
       }
       leaf ipv6-ra-advertisements-sent {
         type int32;
         description
           "Number of router advertisements sent";
       }
       leaf ipv6-ra-advertisement-sent-time {
         type string;
         description
           "How long since the last router advertisement was sent";
       }
       leaf ipv6-ra-solicits-received {
         type int32;
         description
           "Number of router solicitations received";
       }
       leaf ipv6-ra-solicit-receive-time {
         type string;
         description
           "How long since the last router solicitation was received";
       }
       leaf ipv6-ra-solicits-sent {
         type int32;
         description
           "Number of router solicitations sent";
       }
       leaf ipv6-ra-solicit-sent-time {
         type string;
         description
           "How long since the last router solicitation was sent";
       }
       leaf ipv6-ra-advertisements-received {
         type int32;
         description
           "Number of router advertisements received";
       }
       leaf ipv6-ra-solicit-router-advertisement-unicast {
         type int32;
         description
           "Enable forwarding IPv6 Solicited Router Advert as unicast";
       }
       leaf ipv6-ra-solicit-router-advertisement-preference {
         type string;
         description
           "Preference for Router Selection based on RA";
       }
       leaf ipv6-ra-passive-mode {
         type int32;
         description
           "Passive mode";
       }
       leaf ipv6-ra-proxy-parameter-preference {
         type string;
         description
           "Preference to select configured or proxied parameters for 
           downstream interface";
       }
       leaf ipv6-ra-proxy-blackout-timer {
         type string;
         description
           "Proxy blackout timer";
       }
       leaf ipv6-ra-proxy-downstream-mode {
         type int32;
         description
           "Proxy downstream interface mode";
       }
       leaf ipv6-ra-proxy-upstream-mode {
         type int32;
         description
           "Proxy upstream interface";
       }
       leaf-list ipv6-ra-proxy-downstream {
         type string;
         description
           "Proxy downstream interface";
       }
       container vrrp-group {
         leaf vrrp-group-id {
           type int32;
           description
             "Group ID of the configured VRRP group";
         }
         leaf vrrp-advertisements-sent {
           type int32;
           description
             "Number of advertisements sent";
         }
         leaf vrrp-advertisement-sent-time {
           type string;
           description
             "How long since the last advertisement was sent";
         }
         leaf vrrp-solicits-received {
           type int32;
           description
             "Number of router solicitations received";
         }
         leaf vrrp-solicit-receive-time {
           type string;
           description
             "How long since the last solicitation was sent";
         }
         leaf vrrp-advertisements-received {
           type int32;
           description
             "Number of advertisements received";
         }
       }
       list ipv6-ra-advertisement {
         leaf ipv6-source-address {
           type jt:ipv6addr;
           description
             "Sender of the advertisement";
         }
         leaf ipv6-ra-time-since {
           type string;
           description
             "How long since the advertisement was received";
         }
         leaf ipv6-ra-managed-flag {
           type int32;
           description
             "Advertised managed flag";
         }
         leaf ipv6-ra-managed-flag-conflict {
           type int32;
           description
             "Conflict with the advertised managed flag";
         }
         leaf ipv6-ra-other-config-flag {
           type int32;
           description
             "Advertised other configuration flag";
         }
         leaf ipv6-ra-other-config-flag-conflict {
           type int32;
           description
             "Conflict with the advertised other configuration flag";
         }
         leaf ipv6-ra-link-mtu {
           type int32;
           description
             "Advertised link MTU";
         }
         leaf ipv6-ra-link-mtu-conflict {
           type int32;
           description
             "Conflict with the advertised link MTU";
         }
         leaf ipv6-ra-reachable-time {
           type int32;
           description
             "Advertised reachable time";
         }
         leaf ipv6-ra-reachable-time-conflict {
           type int32;
           description
             "Conflict with the advertised reachable time";
         }
         leaf ipv6-ra-default-lifetime {
           type int32;
           description
             "Advertised default lifetime flag";
         }
         leaf ipv6-ra-default-lifetime-conflict {
           type int32;
           description
             "Conflict with the advertised default lifetime flag";
         }
         leaf ipv6-ra-retransmit-timer {
           type int32;
           description
             "Advertised retransmit timer flag";
         }
         leaf ipv6-ra-retransmit-timer-conflict {
           type int32;
           description
             "Conflict with the advertised retransmit timer flag";
         }
         leaf ipv6-ra-current-hop-limit {
           type int32;
           description
             "Advertised current hop limit flag";
         }
         leaf ipv6-ra-current-hop-limit-conflict {
           type int32;
           description
             "Conflict with the advertised current hop limit flag";
         }
         list ipv6-ra-rdnss {
           leaf ipv6-ra-rdnss-address {
             type jt:ipv6addr;
             description
               "Advertised RDNSS address";
           }
           leaf ipv6-ra-rdnss-lifetime {
             type int32;
             description
               "Advertised lifetime of the RDNSS address";
           }
           leaf ipv6-ra-rdnss-lifetime-conflict {
             type int32;
             description
               "Conflict with the advertised lifetime of the RDNSS address";
           }
         }
         list ipv6-ra-prefix {
           leaf ipv6-ra-prefix-address {
             type jt:ipv6prefix;
             description
               "Advertised prefix";
           }
           leaf ipv6-ra-prefix-valid-lifetime {
             type int32;
             description
               "Advertised valid lifetime of the prefix";
           }
           leaf ipv6-ra-prefix-valid-lifetime-conflict {
             type int32;
             description
               "Conflict with the advertised valid lifetime of the prefix";
           }
           leaf ipv6-ra-prefix-preferred-lifetime {
             type int32;
             description
               "Advertised preferred lifetime of the prefix";
           }
           leaf ipv6-ra-prefix-preferred-lifetime-conflict {
             type int32;
             description
               "Conflict with the advertised preferred lifetime of the 
               prefix";
           }
           leaf ipv6-ra-prefix-on-link {
             type int32;
             description
               "Advertised on-link flag of the prefix";
           }
           leaf ipv6-ra-prefix-on-link-conflict {
             type int32;
             description
               "Conflict with the advertised on-link flag of the prefix";
           }
           leaf ipv6-ra-prefix-autonomous {
             type int32;
             description
               "Advertised autonomous flag of the prefix";
           }
           leaf ipv6-ra-prefix-autonomous-conflict {
             type int32;
             description
               "Conflict with the advertised autonomous flag of the prefix";
           }
         }
         list ipv6-ra-heard-dnssl {
           leaf ipv6-ra-heard-dnssl-name {
             type string;
             description
               "Heard DNSSL suffix";
           }
           leaf ipv6-ra-heard-dnssl-lifetime {
             type int32;
             description
               "Heard DNSSL lifetime";
           }
         }
         list ipv6-ra-route {
           leaf ipv6-ra-route-address {
             type string;
             description
               "Route information received in router advertisements";
           }
           leaf ipv6-ra-route-prefix-length {
             type int32;
             description
               "Prefix length";
           }
           leaf ipv6-ra-route-preference {
             type string;
             description
               "Route preference received in router advertisements";
           }
           leaf ipv6-ra-route-lifetime {
             type string;
             description
               "Route lifetime received in router advertisements";
           }
         }
         list ipv6-ra-nat {
           leaf ipv6-ra-nat-address {
             type string;
             description
               "NAT prefix";
           }
           leaf ipv6-ra-nat-prefix-length {
             type int32;
             description
               "NAT prefix length";
           }
           leaf ipv6-ra-nat-lifetime {
             type string;
             description
               "NAT prefix lifetime";
           }
         }
       }
       list ipv6-ra-dnssl {
         leaf ipv6-ra-dnssl-name {
           type string;
           description
             "Advertised DNSSL suffix";
         }
         leaf ipv6-ra-dnssl-lifetime {
           type int32;
           description
             "Advertised DNSSL lifetime";
         }
       }
       list ipv6-ra-config-route {
         leaf ipv6-ra-config-route-address {
           type string;
           description
             "Route information received in router advertisements";
         }
         leaf ipv6-ra-config-route-prefix-length {
           type int32;
           description
             "Prefix length";
         }
         leaf ipv6-ra-config-route-preference {
           type string;
           description
             "Route preference configured";
         }
         leaf ipv6-ra-config-route-lifetime {
           type string;
           description
             "Route lifetime configured";
         }
       }
       list ipv6-ra-config-nat {
         leaf ipv6-ra-config-nat-address {
           type string;
           description
             "NAT prefix";
         }
         leaf ipv6-ra-config-nat-prefix-length {
           type int32;
           description
             "NAT prefix length";
         }
         leaf ipv6-ra-config-nat-lifetime {
           type string;
           description
             "NAT prefix lifetime";
         }
       }
     }
   }
   grouping subscriber-management-napt-pool-stats-block {
     container napt-pool-addresses {
       leaf external-ip-address {
         type string;
         description
           "Public ip address";
       }
       leaf access-physical-interface-name {
         type string;
         description
           "Access PFE";
       }
       leaf access-routing-instance {
         type string;
         description
           "Access routing instance";
       }
       leaf block-size {
         type int32;
         description
           "Block-size";
       }
       leaf block-in-use {
         type string;
         description
           "Block-use";
       }
     }
   }
   grouping subscriber-management-routing-instance-block {
     list ri-info {
       leaf ri-name {
         type string;
         description
           "The name of the routing instance";
       }
       leaf ri-state {
         type string;
         description
           "The state of the routing instance";
       }
     }
   }
   grouping system-error-information-block {
     container system-error-information-attr {
       leaf fact-id {
         type int32;
       }
       leaf summary-header {
         type string;
       }
       leaf group {
         type string;
       }
       leaf scope {
         type string;
       }
       leaf correlation-enabled {
         type string;
       }
       leaf timestamp-raised {
         type string;
       }
       leaf desc {
         type string;
       }
       leaf actions-taken {
         type string;
       }
       leaf root-cause-events {
         type string;
       }
       leaf affected-events {
         type string;
       }
     }
   }
   grouping active-error-count-information-block {
     list error-count-information {
       leaf minor-occur-count {
         type uint32;
         description
           "Minor occur-count";
       }
       leaf minor-clear-count {
         type uint32;
       }
       leaf minor-action-taken {
         type uint32;
       }
       leaf major-occur-count {
         type uint32;
         description
           "Major occur-count";
       }
       leaf major-clear-count {
         type uint32;
       }
       leaf major-action-taken {
         type uint32;
       }
       leaf fatal-occur-count {
         type uint32;
         description
           "Fatal occur-count";
       }
       leaf fatal-clear-count {
         type uint32;
       }
       leaf fatal-action-taken {
         type uint32;
       }
     }
   }
   grouping active-error-information-block {
     container fru-error-information {
       list fru {
         list scope {
         }
       }
     }
     list fru {
       leaf name {
         type string;
         description
           "Name of this FRU";
       }
       container error-information {
         leaf minor-occur-count {
           type uint32;
           description
             "Minor occur-count";
         }
         leaf major-occur-count {
           type uint32;
           description
             "Major occur-count";
         }
         leaf fatal-occur-count {
           type uint32;
           description
             "Fatal occur-count";
         }
       }
       list scope {
       }
     }
   }
   grouping active-error-detail-information-block {
     list fru {
       leaf name {
         type string;
         description
           "Name of this FRU";
       }
       container error-detail-information {
         leaf error {
           type string;
           description
             "Error";
         }
         leaf identifier {
           type string;
           description
             "Identifier";
         }
         leaf details {
           type string;
           description
             "Details";
         }
         leaf state {
           type string;
           description
             "State";
         }
         leaf-list scope-type {
           type string;
           description
             "Scope type";
         }
         leaf category-type {
           type string;
           description
             "Category";
         }
         leaf level {
           type string;
           description
             "Level";
         }
         leaf threshold {
           type string;
           description
             "Threshold";
         }
         leaf limit {
           type uint32;
           description
             "Limit";
         }
         leaf occur-count {
           type uint32;
           description
             "Occur-Count";
         }
         leaf clear-count {
           type uint32;
           description
             "Clear-Count";
         }
         leaf last-occured {
           type string;
           description
             "Last occured";
         }
       }
       list scope {
       }
     }
   }
   grouping inactive-error-information-block {
     container fru-error-information {
       list fru {
         list scope {
         }
       }
     }
     list fru {
       leaf name {
         type string;
         description
           "Name of this FRU";
       }
       container error-information {
         leaf minor-occur-count {
           type uint32;
           description
             "Minor occur-count";
         }
         leaf major-occur-count {
           type uint32;
           description
             "Major occur-count";
         }
         leaf fatal-occur-count {
           type uint32;
           description
             "Fatal occur-count";
         }
       }
       list scope {
       }
     }
   }
   grouping inactive-error-detail-information-block {
     list fru {
       leaf name {
         type string;
         description
           "Name of this FRU";
       }
       container error-detail-information {
         leaf error {
           type string;
           description
             "Error";
         }
         leaf identifier {
           type string;
           description
             "Identifier";
         }
         leaf details {
           type string;
           description
             "Details";
         }
         leaf state {
           type string;
           description
             "State";
         }
         leaf-list scope-type {
           type string;
           description
             "Scope type";
         }
         leaf category-type {
           type string;
           description
             "Category";
         }
         leaf level {
           type string;
           description
             "Level";
         }
         leaf threshold {
           type string;
           description
             "Threshold";
         }
         leaf limit {
           type uint32;
           description
             "Limit";
         }
         leaf occur-count {
           type uint32;
           description
             "Occur-Count";
         }
         leaf clear-count {
           type uint32;
           description
             "Clear-Count";
         }
         leaf last-occured {
           type string;
           description
             "Last occured";
         }
       }
       list scope {
       }
     }
   }
   grouping active-fru-error-information-block {
     leaf-list slot {
       type uint32;
       description
         "FPC slot";
     }
     leaf minor-level-occured {
       type uint32;
     }
     leaf minor-level-cleared {
       type uint32;
     }
     leaf minor-level-threshold {
       type uint32;
     }
     leaf minor-level-action-taken {
       type uint32;
     }
     leaf minor-level-action {
       type string;
     }
     leaf major-level-occured {
       type uint32;
     }
     leaf major-level-cleared {
       type uint32;
     }
     leaf major-level-threshold {
       type uint32;
     }
     leaf major-level-action-taken {
       type uint32;
     }
     leaf major-level-action {
       type string;
     }
     leaf fatal-level-occured {
       type uint32;
     }
     leaf fatal-level-cleared {
       type uint32;
     }
     leaf fatal-level-threshold {
       type uint32;
     }
     leaf fatal-level-action-taken {
       type uint32;
     }
     leaf fatal-level-action {
       type string;
     }
     container health-mon-info {
       leaf location {
         type string;
         description
           "Location";
       }
     }
   }
   grouping active-fru-error-detail-information-block {
     container system-information {
       list fru {
         list scope {
         }
       }
     }
     list fru {
       leaf name {
         type string;
         description
           "Name of this FRU";
       }
       list scope {
         leaf-list scope-type {
           type string;
           description
             "Scope type";
         }
         list category {
           leaf cat {
             type string;
           }
           leaf minor-level-occured {
             type uint32;
           }
           leaf minor-level-cleared {
             type uint32;
           }
           leaf minor-level-threshold {
             type uint32;
           }
           leaf minor-level-action-taken {
             type uint32;
           }
           leaf minor-level-action {
             type string;
           }
           leaf major-level-occured {
             type uint32;
           }
           leaf major-level-cleared {
             type uint32;
           }
           leaf major-level-threshold {
             type uint32;
           }
           leaf major-level-action-taken {
             type uint32;
           }
           leaf major-level-action {
             type string;
           }
           leaf fatal-level-occured {
             type uint32;
           }
           leaf fatal-level-cleared {
             type uint32;
           }
           leaf fatal-level-threshold {
             type uint32;
           }
           leaf fatal-level-action-taken {
             type uint32;
           }
           leaf fatal-level-action {
             type string;
           }
         }
       }
     }
   }
   grouping active-fru-error-id-information-block {
     list fru {
       leaf name {
         type string;
         description
           "Name of this FRU";
       }
       container error-detail-information {
         leaf error {
           type string;
           description
             "Error";
         }
         leaf identifier {
           type string;
           description
             "Identifier";
         }
         leaf details {
           type string;
           description
             "Details";
         }
         leaf state {
           type string;
           description
             "State";
         }
         leaf-list scope-type {
           type string;
           description
             "Scope type";
         }
         leaf category-type {
           type string;
           description
             "Category";
         }
         leaf oc-category {
           type string;
           description
             "OC category";
         }
         leaf level {
           type string;
           description
             "Level";
         }
         leaf threshold {
           type string;
           description
             "Threshold";
         }
         leaf limit {
           type uint32;
           description
             "Limit";
         }
         leaf occur-count {
           type uint32;
           description
             "Occur-Count";
         }
         leaf clear-count {
           type uint32;
           description
             "Clear-Count";
         }
         leaf last-occured {
           type string;
           description
             "Last occured";
         }
       }
       list scope {
       }
     }
   }
   grouping system-error-history-block {
     container system-error-history-attr {
       leaf summary-header {
         type string;
       }
       leaf group {
         type string;
       }
       leaf scope {
         type string;
       }
       leaf correlation-enabled {
         type string;
       }
       leaf timestamp-raised {
         type string;
       }
       leaf desc {
         type string;
       }
       leaf timestamp-cleared {
         type string;
       }
     }
   }
   grouping health-mon-information-block {
     list fpc {
       leaf-list slot {
         type uint32;
         description
           "FPC slot";
       }
       container health-mon-info {
         leaf component {
           type string;
           description
             "Component";
         }
         leaf health-parameter {
           type string;
           description
             "Health parameter";
         }
         leaf param-value {
           type string;
           description
             "Value";
         }
         leaf threshold {
           type string;
           description
             "Threshold";
         }
         leaf comments {
           type string;
           description
             "Comments";
         }
         leaf location {
           type string;
           description
             "Location";
         }
       }
     }
   }
   grouping memory-statistics-block {
     leaf current-mbufs {
       type uint64;
       description
         "Current mbufs in use";
     }
     leaf cached-mbufs {
       type uint64;
       description
         "Cached mbufs";
     }
     leaf total-mbufs {
       type uint64;
       description
         "Total mbufs";
     }
     leaf current-mbuf-clusters {
       type uint64;
       description
         "Current mbuf clusters in use";
     }
     leaf cached-mbuf-clusters {
       type uint64;
       description
         "Cached mbuf clusters";
     }
     leaf total-mbuf-clusters {
       type uint64;
       description
         "Total mbuf clusters in use";
     }
     leaf max-mbuf-clusters {
       type uint64;
       description
         "Maximum mbuf clusters";
     }
     leaf packet-count {
       type uint64;
       description
         "Number of current allocations";
     }
     leaf packet-free {
       type uint64;
       description
         "Number of cached free items";
     }
     leaf current-jumbo-clusters-4k {
       type uint64;
       description
         "Current jumbo clusters";
     }
     leaf cached-jumbo-clusters-4k {
       type uint64;
       description
         "Cached jumbo clusters";
     }
     leaf total-jumbo-clusters-4k {
       type uint64;
       description
         "Total jumbo clusters";
     }
     leaf max-jumbo-clusters-4k {
       type uint64;
       description
         "Maximum jumbo clusters";
     }
     leaf current-jumbo-clusters-9k {
       type uint64;
       description
         "Current jumbo clusters";
     }
     leaf cached-jumbo-clusters-9k {
       type uint64;
       description
         "Cached jumbo clusters";
     }
     leaf total-jumbo-clusters-9k {
       type uint64;
       description
         "Total jumbo clusters";
     }
     leaf max-jumbo-clusters-9k {
       type uint64;
       description
         "Maximum jumbo clusters";
     }
     leaf current-jumbo-clusters-16k {
       type uint64;
       description
         "Current jumbo clusters";
     }
     leaf cached-jumbo-clusters-16k {
       type uint64;
       description
         "Cached jumbo clusters";
     }
     leaf total-jumbo-clusters-16k {
       type uint64;
       description
         "Total jumbo clusters";
     }
     leaf max-jumbo-clusters-16k {
       type uint64;
       description
         "Maximum jumbo clusters";
     }
     leaf current-bytes-in-use {
       type uint64;
       description
         "Bytes in use currently";
     }
     leaf cached-bytes {
       type uint64;
       description
         "Cached bytes";
     }
     leaf total-bytes {
       type uint64;
       description
         "Total bytes";
     }
     leaf mbuf-failures {
       type uint64;
       description
         "No of mbuf requests denied";
     }
     leaf cluster-failures {
       type uint64;
       description
         "No of cluster requests denied";
     }
     leaf packet-failures {
       type uint64;
       description
         "No of mbuf+cluster requests denied";
     }
     leaf jumbo-cluster-failures-4k {
       type uint64;
       description
         "No of jumbo cluster(4k) failures";
     }
     leaf jumbo-cluster-failures-9k {
       type uint64;
       description
         "No of jumbo cluster(9k) failures";
     }
     leaf jumbo-cluster-failures-16k {
       type uint64;
       description
         "No of jumbo cluster(16k) failures";
     }
     leaf current-sfbufs {
       type int32;
       description
         "No of sfbufs in use";
     }
     leaf peak-sfbufs {
       type int32;
       description
         "Peak no of sfbufs";
     }
     leaf max-sfbufs {
       type int32;
       description
         "Maximum sfbufs";
     }
     leaf sfbuf-requests-denied {
       type uint64;
       description
         "No of requests for sfbufs denied";
     }
     leaf sfbuf-requests-delayed {
       type uint64;
       description
         "No of requests for sfbufs delayed";
     }
     leaf io-initiated {
       type uint64;
       description
         "No of requests for I/O initiated by sendfile";
     }
     leaf protocol-drain-routine-calls {
       type uint32;
       description
         "No of calls to protocol drain routines";
     }
     leaf mbuf-requests-delayed {
       type uint32;
       description
         "No of mbuf requests delayed";
     }
     leaf cluster-requests-delayed {
       type uint32;
       description
         "No of cluster requests delayed";
     }
     leaf mbuf-tag-count {
       type uint64;
       description
         "Total mbuf tag count";
     }
   }
   grouping queues-statistics-block {
     container interface-queues-statistics {
       container interface-queue {
         leaf name {
           type string;
           description
             "Name of interface/protocol";
         }
         leaf octets-in-queue {
           type uint32;
           description
             "Number of octets in queue";
         }
         leaf max-octets-allowed {
           type uint32;
           description
             "Maximum octets allowed in queue";
         }
         leaf packets-in-queue {
           type uint32;
           description
             "Number of packets in queue";
         }
         leaf max-packets-allowed {
           type uint32;
           description
             "Maximum number of packets allowed in queue";
         }
         leaf number-of-queue-drops {
           type uint32;
           description
             "Number of drops in queue";
         }
       }
     }
     container protocol-queues-statistics {
       container protocol-queue {
         leaf name {
           type string;
           description
             "Name of interface/protocol";
         }
         leaf octets-in-queue {
           type uint32;
           description
             "Number of octets in queue";
         }
         leaf max-octets-allowed {
           type uint32;
           description
             "Maximum octets allowed in queue";
         }
         leaf packets-in-queue {
           type uint32;
           description
             "Number of packets in queue";
         }
         leaf max-packets-allowed {
           type uint32;
           description
             "Maximum number of packets allowed in queue";
         }
         leaf number-of-queue-drops {
           type uint32;
           description
             "Number of drops in queue";
         }
       }
     }
   }
   grouping directory-usage-information-block {
     list directory {
       description
         "Information about system directory usage";
       leaf used-space {
         type string;
         description
           "Total amount of space used";
       }
       leaf directory-name {
         type string;
         description
           "Directory name";
       }
     }
   }
   grouping auto-snapshot-information-block {
     leaf auto-snapshot-configuration {
       type string;
       description
         "Autosnapshot configuration";
     }
     leaf auto-snapshot-state {
       type string;
       description
         "Autosnapshot current state";
     }
     leaf auto-snapshot-note {
       type string;
       description
         "Autosnapshot note";
     }
   }
   grouping snapshot-information-block {
     leaf snapshot-medium {
       type string;
       description
         "Media type of the snapshot";
     }
     leaf creation-date {
       type string;
       description
         "Snapshot creation date";
     }
     container inform {
       leaf source-daemon {
         type string;
       }
       leaf message {
         type string;
         description
           "Syslog message text";
       }
     }
     container snapshot-copy {
       leaf source-directory {
         type string;
         description
           "Directory to backup";
       }
       leaf destination-directory {
         type string;
         description
           "Backup directory";
       }
     }
     container archived-directory-list {
       leaf directory-name {
         type string;
         description
           "Directory name";
       }
     }
     container snapshot-partitions {
       description
         "Partitions on snapshot medium";
       list partition-information {
         description
           "Partition information";
         leaf partition {
           type string;
           description
             "Partition letter";
         }
         leaf mount-point {
           type string;
           description
             "Mount point";
         }
         leaf partition-size {
           type string;
           description
             "Size of partition";
         }
         leaf snapshot-argument {
           type string;
           description
             "Argument to snapshot used to configure size";
         }
       }
     }
     container software-version {
       description
         "Version of software snapshot";
       list package {
         description
           "Package in software snapshot";
         leaf package-name {
           type string;
           description
             "Name of software package";
         }
         leaf package-version {
           type string;
           description
             "Version of software package";
         }
       }
     }
   }
   grouping statistics-block {
     container tcp {
       leaf packets-sent {
         type uint32;
         description
           "Packets sent";
       }
       leaf sent-data-packets {
         type uint32;
         description
           "Data packets";
       }
       leaf data-packets-bytes {
         type uint32;
         description
           "In terms of bytes";
       }
       leaf sent-data-packets-retransmitted {
         type uint32;
         description
           "Data packets retransmitted";
       }
       leaf retransmitted-bytes {
         type uint32;
         description
           "In terms of bytes";
       }
       leaf sent-data-unnecessary-retransmitted {
         type uint32;
         description
           "Data unnecessary retransmitted";
       }
       leaf sent-resends-by-mtu-discovery {
         type uint32;
         description
           "Resends initiated by MTU discovery";
       }
       leaf sent-ack-only-packets {
         type uint32;
         description
           "Ack-only packets";
       }
       leaf sent-packets-delayed {
         type uint32;
         description
           "Number of packets delayed";
       }
       leaf sent-urg-only-packets {
         type uint32;
         description
           "URG only packets";
       }
       leaf sent-window-probe-packets {
         type uint32;
         description
           "Window probe packets";
       }
       leaf sent-window-update-packets {
         type uint32;
         description
           "Window update packets";
       }
       leaf sent-control-packets {
         type uint32;
         description
           "Control packets";
       }
       leaf packets-received {
         type uint32;
         description
           "Packets received";
       }
       leaf received-acks {
         type uint32;
         description
           "Acks";
       }
       leaf acks-bytes {
         type uint32;
         description
           "Number of bytes";
       }
       leaf received-duplicate-acks {
         type uint32;
         description
           "Dupliacte acks";
       }
       leaf received-acks-for-unsent-data {
         type uint32;
         description
           "Acks for unsent data";
       }
       leaf packets-received-in-sequence {
         type uint32;
         description
           "Packets received in-sequence";
       }
       leaf in-sequence-bytes {
         type uint32;
         description
           "Packets received in-sequence in bytes";
       }
       leaf received-completely-duplicate-packet {
         type uint32;
         description
           "Completely duplicate packets";
       }
       leaf duplicate-in-bytes {
         type uint32;
         description
           "Completely duplicate packets in bytes";
       }
       leaf received-old-duplicate-packets {
         type uint32;
         description
           "Old duplicate packets";
       }
       leaf received-packets-with-some-dupliacte-data {
         type uint32;
         description
           "Packets with some duplicate data";
       }
       leaf some-duplicate-in-bytes {
         type uint32;
         description
           "Packets with some duplicate data in bytes";
       }
       leaf received-out-of-order-packets {
         type uint32;
         description
           "Out-of-order packets";
       }
       leaf out-of-order-in-bytes {
         type uint32;
         description
           "Out-of-order packets in bytes";
       }
       leaf received-packets-of-data-after-window {
         type uint32;
         description
           "Packets of data after window";
       }
       leaf bytes {
         type uint32;
         description
           "Packets of data after window in bytes";
       }
       leaf received-window-probes {
         type uint32;
         description
           "Window probes";
       }
       leaf received-window-update-packets {
         type uint32;
       }
       leaf packets-received-after-close {
         type uint32;
         description
           "Packets received after close";
       }
       leaf received-discarded-for-bad-checksum {
         type uint32;
         description
           "Discarded for bad checksum";
       }
       leaf received-discarded-for-bad-header-offset {
         type uint32;
         description
           "Discarded for bad header offset fields";
       }
       leaf received-discarded-because-packet-too-short {
         type uint32;
         description
           "Discarded because packet too short";
       }
       leaf connection-requests {
         type uint32;
         description
           "Connection requests";
       }
       leaf connection-accepts {
         type uint32;
         description
           "Connection accepts";
       }
       leaf bad-connection-attempts {
         type uint32;
         description
           "Bad connection attempts";
       }
       leaf listen-queue-overflows {
         type uint32;
         description
           "Listen queue overflows";
       }
       leaf bad-rst-window {
         type uint32;
         description
           "Ignored RSTs in the windows";
       }
       leaf connections-established {
         type uint32;
         description
           "Connections established";
       }
       leaf connections-closed {
         type uint32;
         description
           "Connections closed";
       }
       leaf drops {
         type uint32;
         description
           "Drops";
       }
       leaf connections-updated-rtt-on-close {
         type uint32;
         description
           "Connections updated cached RTT on close";
       }
       leaf connections-updated-variance-on-close {
         type uint32;
         description
           "Connections updated cached RTT variance on close";
       }
       leaf connections-updated-ssthresh-on-close {
         type uint32;
         description
           "Connections updated cached ssthresh on close";
       }
       leaf embryonic-connections-dropped {
         type uint32;
         description
           "Embryonic connections dropped";
       }
       leaf segments-updated-rtt {
         type uint32;
         description
           "Segments updated RTT";
       }
       leaf attempts {
         type uint32;
         description
           "Attempts";
       }
       leaf retransmit-timeouts {
         type uint32;
         description
           "Retransmit timeouts";
       }
       leaf connections-dropped-by-retransmit-timeout {
         type uint32;
         description
           "Connections dropped";
       }
       leaf persist-timeouts {
         type uint32;
         description
           "Persist timeouts";
       }
       leaf connections-dropped-by-persist-timeout {
         type uint32;
       }
       leaf keepalive-timeouts {
         type uint32;
         description
           "Keepalive timeouts";
       }
       leaf keepalive-probes-sent {
         type uint32;
         description
           "Keepalive probes sent";
       }
       leaf keepalive-connections-dropped {
         type uint32;
         description
           "Keepalive connections dropped";
       }
       leaf ack-header-predictions {
         type uint32;
         description
           "Correct ACK header predictions";
       }
       leaf data-packet-header-predictions {
         type uint32;
         description
           "Correct data packet header predictions";
       }
       leaf syncache-entries-added {
         type uint32;
         description
           "Syncache entries added";
       }
       leaf retransmitted {
         type uint32;
         description
           "Retransmitted in syncache entries added";
       }
       leaf dupsyn {
         type uint32;
         description
           "Dupsyn in syncache entries added";
       }
       leaf dropped {
         type uint32;
         description
           "Dropped in syncache entries added";
       }
       leaf completed {
         type uint32;
         description
           "Completed in syncache entries added";
       }
       leaf bucket-overflow {
         type uint32;
         description
           "Bucket overflow in syncache entries added";
       }
       leaf cache-overflow {
         type uint32;
         description
           "Cache overflow in syncache entries added";
       }
       leaf reset {
         type uint32;
         description
           "Reset in syncache entries added";
       }
       leaf stale {
         type uint32;
         description
           "Stale in syncache entries added";
       }
       leaf aborted {
         type uint32;
         description
           "Aborted in syncache entries added";
       }
       leaf badack {
         type uint32;
         description
           "Bad ACK in syncache entries added";
       }
       leaf unreach {
         type uint32;
         description
           "Unreach in syncache entries added";
       }
       leaf zone-failures {
         type uint32;
         description
           "Zone failures in syncache entries added";
       }
       leaf cookies-sent {
         type uint32;
         description
           "Cookies sent";
       }
       leaf cookies-received {
         type uint32;
         description
           "Cookies received";
       }
       leaf sack-recovery-episodes {
         type uint32;
         description
           "SACK recovery episodes";
       }
       leaf segment-retransmits {
         type uint32;
         description
           "Segment retransmits in SACK recovery episodes";
       }
       leaf byte-retransmits {
         type uint32;
         description
           "Byte retransmits in SACK recovery episodes";
       }
       leaf sack-options-received {
         type uint32;
         description
           "SACK options (SACK blocks) received";
       }
       leaf sack-opitions-sent {
         type uint32;
         description
           "SACK options (SACK blocks) sent";
       }
       leaf sack-scoreboard-overflow {
         type uint32;
         description
           "SACK scoreboard overflow";
       }
       leaf acks-sent-in-response-but-not-exact-rsts {
         type uint32;
         description
           "ACKs sent in response to in-window but not exact RSTs";
       }
       leaf acks-sent-in-response-to-syns-on-established-connections {
         type uint32;
         description
           "ACKs sent in response to in-window SYNs on established 
           connections";
       }
       leaf rcv-packets-dropped-due-to-bad-address {
         type uint32;
         description
           "Rcv packets dropped dropped by TCP due to bad address";
       }
       leaf out-of-sequence-segment-drops {
         type uint32;
         description
           "Out-of-sequence segment drops due to insufficient memory";
       }
       leaf rst-packets {
         type uint32;
         description
           "RST packets";
       }
       leaf icmp-packets-ignored {
         type uint32;
         description
           "ICMP packets ignored by TCP";
       }
       leaf send-packets-dropped {
         type uint32;
         description
           "Send packets dropped by TCP due to auth errors";
       }
       leaf rcv-packets-dropped {
         type uint32;
       }
       leaf outgoing-segments-dropped {
         type uint32;
         description
           "Outgoing segments dropped due to policing";
       }
       leaf received-synfin-dropped {
         type uint32;
         description
           "SYN,FIN packets dropped";
       }
       leaf received-ipsec-dropped {
         type uint32;
         description
           "Packets dropped due to IPSEC validation failed";
       }
       leaf received-mac-dropped {
         type uint32;
         description
           "Packets dropped due to MAC validation failed";
       }
       leaf received-minttl-exceeded {
         type uint32;
         description
           "Packets dropped as TTL exceed min TTL";
       }
       leaf listenstate-badflags-dropped {
         type uint32;
         description
           "Packets dropped due to non expected TCP flags in listen state";
       }
       leaf finwaitstate-badflags-dropped {
         type uint32;
         description
           "Packets dropped as TCP flags other than FIN/RST not expected in 
           FIN wait state";
       }
       leaf received-dos-attack {
         type uint32;
         description
           "Packets dropped as part of DoS Attack";
       }
       leaf received-bad-synack {
         type uint32;
         description
           "Packets dropped due to bad SYN,ACK in SYN sent or received state";
       }
       leaf syncache-zone-full {
         type uint32;
         description
           "Packets dropped as sc zone full";
       }
       leaf received-rst-firewallfilter {
         type uint32;
         description
           "Received RST during reset send from firewall";
       }
       leaf received-noack-timewait {
         type uint32;
         description
           "Packets dropped as this is not ACK in timewait check";
       }
       leaf received-no-timewait-state {
         type uint32;
         description
           "Packets dropped as no timewait state";
       }
       leaf received-rst-timewait-state {
         type uint32;
         description
           "Packets dropped as reset received in timewait check";
       }
       leaf received-timewait-drops {
         type uint32;
         description
           "Packets dropped during timewait check";
       }
       leaf received-badaddr-timewait-state {
         type uint32;
         description
           "Packets dropped due as broadcast/multicast address in timewait";
       }
       leaf received-ackoff-in-syn-sentrcvd {
         type uint32;
         description
           "Packets dropped as no ack received when other than SYN sent or 
           received state";
       }
       leaf received-badaddr-firewall {
         type uint32;
         description
           "Packets dropped broadcast/multicast address in firewall match";
       }
       leaf received-nosyn-syn-sent {
         type uint32;
         description
           "Packets dropped as no SYN received in SYN sent state";
       }
       leaf received-badrst-syn-sent {
         type uint32;
         description
           "Packets dropped as reset packet received in SYN sent state";
       }
       leaf received-badrst-listen-state {
         type uint32;
         description
           "Packets dropped as reset packet received in listen state";
       }
       leaf option-maxsegment-length {
         type uint32;
         description
           "TCP option max segment length is invalid";
       }
       leaf option-window-length {
         type uint32;
         description
           "TCP option window length is invalid";
       }
       leaf option-timestamp-length {
         type uint32;
         description
           "TCP option timestamp length is invalid";
       }
       leaf option-md5-length {
         type uint32;
         description
           "Packets TCP option MD5 length is invalid";
       }
       leaf option-auth-length {
         type uint32;
         description
           "TCP option authentication length is invalid";
       }
       leaf option-sackpermitted-length {
         type uint32;
         description
           "TCP option sack permitted length is invalid";
       }
       leaf option-sack-length {
         type uint32;
         description
           "TCP option selective acknowledgement length is invalid";
       }
       leaf option-authoption-length {
         type uint32;
         description
           "TCP option authentication option length is invalid";
       }
     }
     container sctp {
       leaf input-packets {
         type uint64;
         description
           "Input packets";
       }
       leaf datagrams {
         type uint32;
         description
           "Datagrams";
       }
       leaf packets-that-had-data {
         type uint32;
         description
           "Packets that had data";
       }
       leaf input-sack-chunks {
         type uint32;
         description
           "Input SACK chunks";
       }
       leaf input-data-chunks {
         type uint32;
         description
           "Input DATA chunks";
       }
       leaf duplicate-data-chunks {
         type uint32;
         description
           "Duplicate DATA chunks";
       }
       leaf input-hb-chunks {
         type uint32;
         description
           "Input HB chunks";
       }
       leaf hb-ack-chunks {
         type uint32;
         description
           "HB-ACK_CHUNKS";
       }
       leaf input-ecne-chunks {
         type uint32;
         description
           "Input ECNE chunks";
       }
       leaf input-auth-chunks {
         type uint32;
         description
           "Input AUTH-chunks";
       }
       leaf chunks-missing-auth {
         type uint32;
         description
           "Chunks-missing-AUTH";
       }
       leaf invalid-hmac-ids-received {
         type uint32;
         description
           "Invalid HMAC ids received";
       }
       leaf invalid-secret-ids-received {
         type uint32;
         description
           "Invalid secrete ids received";
       }
       leaf auth-failed {
         type uint32;
         description
           "Auth failed";
       }
       leaf fast-path-receives-all-one-chunk {
         type uint32;
         description
           "Fast path receives all one chunk";
       }
       leaf fast-path-multi-part-data {
         type uint32;
         description
           "Fast path multi part data";
       }
       leaf output-packets {
         type uint64;
         description
           "Output packets";
       }
       leaf output-sacks {
         type uint32;
         description
           "Output SACKs";
       }
       leaf output-data-chunks {
         type uint32;
         description
           "Output DATA chunks";
       }
       leaf retransmitted-data-chunks {
         type uint32;
         description
           "Retransmitted DATA chunks";
       }
       leaf fast-retransmitted-data-chunks {
         type uint32;
         description
           "Fast retransmitted DATA chunks";
       }
       leaf frs-that-happened-more-than-once-to-same-chunk {
         type uint32;
         description
           "FRs that happened more than once to same chunk";
       }
       leaf output-hb-chunks {
         type uint32;
         description
           "Ouput HB chunks";
       }
       leaf output-ecne-chunks {
         type uint32;
         description
           "Output ECNE chunks";
       }
       leaf output-auth-chunks {
         type uint32;
         description
           "Output AUTH chunks";
       }
       leaf ip-output-error-counter {
         type uint32;
         description
           "Ip output error counter";
       }
       leaf packet-drop-statistics {
         type string;
         description
           "Packet drop statistics";
       }
       leaf from-middle-box {
         type uint32;
         description
           "From middle box";
       }
       leaf from-end-host {
         type uint32;
         description
           "From end host";
       }
       leaf with-data {
         type uint32;
         description
           "With data";
       }
       leaf non-data-non-endhost {
         type uint32;
         description
           "Non-data, non-endhost";
       }
       leaf non-endhost-bandwidth-rep-only {
         type uint32;
         description
           "Non-endhost, bandwidth rep only";
       }
       leaf not-enough-for-chunk-header {
         type uint32;
         description
           "Not enough for chunk header";
       }
       leaf not-enough-data-to-confirm {
         type uint32;
         description
           "Not enough data to confirm";
       }
       leaf where-process-chunk-drop-said-break {
         type uint32;
         description
           "Where process_chunk_drop said break";
       }
       leaf failed-to-find-tsn {
         type uint32;
         description
           "Failed to find TSN";
       }
       leaf attempt-reverse-tsn-lookup {
         type uint32;
         description
           "Attempt reverse TSN lookup";
       }
       leaf e-host-confirms-zero-rwnd {
         type uint32;
         description
           "E-host confirms zero-rwnd";
       }
       leaf midbox-confirms-no-space {
         type uint32;
         description
           "Midbox confirms no space";
       }
       leaf data-did-not-match-tsn {
         type uint32;
         description
           "Data did not match TSN";
       }
       leaf tsns-marked-for-fast-retran {
         type uint32;
         description
           "TSN's marked for Fast Retran";
       }
       leaf timeouts {
         type string;
         description
           "Timeouts";
       }
       leaf iterator-timers-fired {
         type uint32;
         description
           "Iterator timers fired";
       }
       leaf t3-data-time-outs {
         type uint32;
         description
           "T3 data time outs";
       }
       leaf window-probe-t3-timers-fired {
         type uint32;
         description
           "Window probe (T3) timers fired";
       }
       leaf init-timers-fired {
         type uint32;
         description
           "INIT timers fired";
       }
       leaf sack-timers-fired {
         type uint32;
         description
           "Sack timers fired";
       }
       leaf shutdown-timers-fired {
         type uint32;
         description
           "Shutdown timers fired";
       }
       leaf heartbeat-timers-fired {
         type uint32;
         description
           "Heartbeat timers fired";
       }
       leaf a-cookie-timeout-fired {
         type uint32;
         description
           "A cookie timeout fired";
       }
       leaf an-endpoint-changed-its-cookiesecret {
         type uint32;
         description
           "An endpoint changed its cookiesecret";
       }
       leaf pmtu-timers-fired {
         type uint32;
         description
           "PMTU timers fired";
       }
       leaf shutdown-ack-timers-fired {
         type uint32;
         description
           "Shutdown ack timers fired";
       }
       leaf shutdown-guard-timers-fired {
         type uint32;
         description
           "Shutdown guard timers fired";
       }
       leaf stream-reset-timers-fired {
         type uint32;
         description
           "Stream reset timers fired";
       }
       leaf early-fr-timers-fired {
         type uint32;
         description
           "Early FR timers fired";
       }
       leaf an-asconf-timer-fired {
         type uint32;
         description
           "An asconf timer fired";
       }
       leaf auto-close-timer-fired {
         type uint32;
         description
           "Auto close timer fired";
       }
       leaf asoc-free-timers-expired {
         type uint32;
         description
           "Asoc free timers expired";
       }
       leaf inp-free-timers-expired {
         type uint32;
         description
           "Inp free timers expired";
       }
       leaf packet-shorter-than-header {
         type uint32;
         description
           "Packet shorter than header";
       }
       leaf checksum-error {
         type uint32;
         description
           "Checksum error";
       }
       leaf no-endpoint-for-port {
         type uint32;
         description
           "No endpoint for port";
       }
       leaf bad-v-tag {
         type uint32;
         description
           "Bad v-tag";
       }
       leaf bad-sid {
         type uint32;
         description
           "Bad SID";
       }
       leaf no-memory {
         type uint32;
         description
           "No memory";
       }
       leaf number-of-multiple-fr-in-a-rtt-window {
         type uint32;
         description
           "Number of multiple FR in a RTT window";
       }
       leaf rfc813-allowed-sending {
         type uint32;
         description
           "RFC813 allowed sending";
       }
       leaf rfc813-does-not-allow-sending {
         type uint32;
         description
           "RFC813 does not allow sending";
       }
       leaf times-max-burst-prohibited-sending {
         type uint32;
         description
           "Times max burst prohibited sending";
       }
       leaf look-ahead-tells-us-no-memory-in-interface {
         type uint32;
         description
           "Look ahead tells us no memory in interface";
       }
       leaf numbers-of-window-probes-sent {
         type uint32;
         description
           "Numbers of window probes sent";
       }
       leaf times-an-output-error-to-clamp-down-on-next-user-send {
         type uint32;
         description
           "Times an output error to clamp down on next user send";
       }
       leaf times-sctpsenderrors-were-caused-from-a-user {
         type uint32;
         description
           "Times sctp_senderrors were caused from a user";
       }
       leaf number-of-in-data-drops-due-to-chunk-limit-reached {
         type uint32;
         description
           "Number of in data drops due to chunk limit reached";
       }
       leaf number-of-in-data-drops-due-to-rwnd-limit-reached {
         type uint32;
         description
           "Number of in data drops due to rwnd limit reached";
       }
       leaf times-a-ecn-reduced-the-cwnd {
         type uint32;
         description
           "Times a ECN reduced the cwnd";
       }
       leaf used-express-lookup-via-vtag {
         type uint32;
         description
           "Used express lookup via vtag";
       }
       leaf collision-in-express-lookup {
         type uint32;
         description
           "Collision in express lookup";
       }
       leaf times-the-sender-ran-dry-of-user-data-on-primary {
         type uint32;
         description
           "Times the sender ran dry of user data on primary";
       }
       leaf sacks-the-slow-way {
         type uint32;
         description
           "Sacks the slow way";
       }
       leaf window-update-only-sacks-sent {
         type uint32;
         description
           "Window update only sacks sent";
       }
       leaf sends-with-sinfoflags-notzero {
         type uint32;
         description
           "Sends with sinfo_flags !=0";
       }
       leaf unordered-sends {
         type uint32;
         description
           "Unordered sends";
       }
       leaf sends-with-eof-flag-set {
         type uint32;
         description
           "Sends with EOF flag set";
       }
       leaf sends-with-abort-flag-set {
         type uint32;
         description
           "Sends with ABORT flag set";
       }
       leaf sctp-aborted {
         type uint32;
         description
           "ABORTED sctps";
       }
       leaf times-protocol-drain-called {
         type uint32;
         description
           "Times protocol drain called";
       }
       leaf times-we-did-a-protocol-drain {
         type uint32;
         description
           "Times we did a protocol drain";
       }
       leaf times-recv-was-called-with-peek {
         type uint32;
         description
           "Times recv was called with peek";
       }
       leaf cached-chunks-used {
         type uint32;
         description
           "Cached chunks used";
       }
       leaf cached-stream-oqs-used {
         type uint32;
         description
           "Cached stream oq's used";
       }
       leaf unread-messages-abandonded-by-close {
         type uint32;
         description
           "Unread messages abandonded by close";
       }
       leaf send-burst-avoidance-already-max-burst-inflight-to-net {
         type uint32;
         description
           "Send burst avoidance, already max burst inflight to net";
       }
       leaf send-cwnd-full-avoidance-already-max-burst-inflight-to-net {
         type uint32;
         description
           "Send cwnd full avoidance, already max burst inflight to net";
       }
       leaf number-of-map-array-over-runs-via-fwd-tsns {
         type uint32;
         description
           "Number of map array over-runs via fwd-tsn's";
       }
       leaf same-for-above {
         type uint32;
         description
           "Same for above";
       }
     }
     container udp {
       leaf datagrams-received {
         type uint32;
         description
           "Datagrams received";
       }
       leaf datagrams-with-incomplete-header {
         type uint32;
         description
           "Datagrams with incomplete header";
       }
       leaf datagrams-with-bad-datalength-field {
         type uint32;
         description
           "Datagrams with bad data length field";
       }
       leaf datagrams-with-bad-checksum {
         type uint32;
         description
           "Datagrams with bad checksum";
       }
       leaf datagrams-dropped-due-to-no-socket {
         type uint32;
         description
           "Datagrams dropped due to no socket";
       }
       leaf broadcast-or-multicast-datagrams-dropped-due-to-no-socket {
         type uint32;
         description
           "Broadcast/multicast datagrams dropped due to no socket";
       }
       leaf datagrams-dropped-due-to-full-socket-buffers {
         type uint32;
         description
           "Datagrams dropped due to full socket buffers";
       }
       leaf datagrams-not-for-hashed-pcb {
         type uint32;
         description
           "Datagrams not for hashed pcb";
       }
       leaf datagrams-delivered {
         type uint32;
         description
           "Datagrams delivered";
       }
       leaf datagrams-output {
         type uint32;
         description
           "Datagrams output";
       }
     }
     container ip {
       leaf packets-received {
         type uint32;
         description
           "Packets received";
       }
       leaf bad-header-checksums {
         type uint32;
         description
           "Bad header checksums";
       }
       leaf packets-with-size-smaller-than-minimum {
         type uint32;
         description
           "Packets with size smaller than minimum";
       }
       leaf packets-with-data-size-less-than-datalength {
         type uint32;
         description
           "Packets with data size < data length";
       }
       leaf packets-with-header-length-less-than-data-size {
         type uint32;
         description
           "Packets with header length < data size";
       }
       leaf packets-with-data-length-less-than-headerlength {
         type uint32;
         description
           "Packets with data length < header length";
       }
       leaf packets-with-incorrect-version-number {
         type uint32;
         description
           "Packets with incorrect version number";
       }
       leaf packets-destined-to-dead-next-hop {
         type uint32;
         description
           "Packets destined to dead nexthop";
       }
       leaf fragments-received {
         type uint32;
         description
           "Fragments received";
       }
       leaf fragments-dropped-due-to-outofspace-or-dup {
         type uint32;
         description
           "Fragments dropped due to out of space/dup";
       }
       leaf fragments-dropped-due-to-queueoverflow {
         type uint32;
         description
           "Fragment sessions dropped due to queue overflow";
       }
       leaf fragments-dropped-after-timeout {
         type uint32;
         description
           "Fragments dropped after timeout";
       }
       leaf packets-reassembled-ok {
         type uint32;
         description
           "Packets reassembled ok";
       }
       leaf packets-for-this-host {
         type uint32;
         description
           "Packets-for-this-host";
       }
       leaf packets-for-unknown-or-unsupported-protocol {
         type uint32;
         description
           "Packets for unknown/unsupported protocol";
       }
       leaf packets-forwarded {
         type uint32;
         description
           "Packets forwarded";
       }
       leaf packets-not-forwardable {
         type uint32;
         description
           "Packets not forwardable";
       }
       leaf redirects-sent {
         type uint32;
         description
           "Redirects sent";
       }
       leaf packets-sent-from-this-host {
         type uint32;
         description
           "Packets sent from this host";
       }
       leaf packets-sent-with-fabricated-ip-header {
         type uint32;
         description
           "Packets sent with fabricated ip header";
       }
       leaf output-packets-dropped-due-to-no-bufs {
         type uint32;
         description
           "Output packets dropped due to no bufs";
       }
       leaf output-packets-discarded-due-to-no-route {
         type uint32;
         description
           "Output packets discarded due to no route";
       }
       leaf output-datagrams-fragmented {
         type uint32;
         description
           "Output datagrams fragmented";
       }
       leaf fragments-created {
         type uint32;
         description
           "Fragments created";
       }
       leaf datagrams-that-can-not-be-fragmented {
         type uint32;
         description
           "Datagrams that can't be fragmented";
       }
       leaf packets-with-bad-options {
         type uint32;
         description
           "Packets with bad options";
       }
       leaf packets-with-options-handled-without-error {
         type uint32;
         description
           "Packets with options handled without error";
       }
       leaf strict-source-and-record-route-options {
         type uint32;
         description
           "Strict source and record route options";
       }
       leaf loose-source-and-record-route-options {
         type uint32;
         description
           "Loose source and record route options";
       }
       leaf record-route-options {
         type uint32;
         description
           "Record route options";
       }
       leaf timestamp-options {
         type uint32;
         description
           "Timestamp options";
       }
       leaf timestamp-and-address-options {
         type uint32;
         description
           "Timestamp and address options";
       }
       leaf timestamp-and-prespecified-address-options {
         type uint32;
         description
           "Timestamp and prespecified address options";
       }
       leaf option-packets-dropped-due-to-rate-limit {
         type uint32;
         description
           "Option packets dropped due to rate limit";
       }
       leaf router-alert-options {
         type uint32;
         description
           "Router alert options";
       }
       leaf multicast-packets-dropped {
         type uint32;
         description
           "Multicast packets dropped (no iflist)";
       }
       leaf packets-dropped {
         type uint32;
         description
           "Packets dropped (src and int don't match)";
       }
       leaf transit-re-packets-dropped-on-mgmt-interface {
         type uint32;
         description
           "Transit RE packets dropped on mgmt interface";
       }
       leaf packets-used-first-nexthop-in-ecmp-unilist {
         type uint32;
         description
           "Packets used first nexthop in ecmp unilist";
       }
       leaf incoming-ttpoip-packets-received {
         type uint32;
         description
           "Incoming TTPoIP packets received";
       }
       leaf incoming-ttpoip-packets-dropped {
         type uint32;
         description
           "Incoming TTPoIP packets dropped";
       }
       leaf outgoing-ttpoip-packets-sent {
         type uint32;
         description
           "Outgoing TTPoIP packets sent";
       }
       leaf outgoing-ttpoip-packets-dropped {
         type uint32;
         description
           "Outgoing TTPoIP packets dropped";
       }
       leaf incoming-rawip-packets-dropped-no-socket-buffer {
         type uint32;
         description
           "Incoming raw ip packets dropped. No space in recv socket buffer";
       }
       leaf incoming-virtual-node-packets-delivered {
         type uint32;
         description
           "Incoming packets consumed by virtual-node processing";
       }
     }
     container icmp {
       leaf drops-due-to-rate-limit {
         type uint32;
         description
           "Drops due to rate limit";
       }
       leaf drops-at-server-ine {
         type uint32;
         description
           "Drops at server INE";
       }
       leaf calls-to-icmp-error {
         type uint32;
         description
           "Calls to icmp_error";
       }
       leaf errors-not-generated-because-old-message-was-icmp {
         type uint32;
         description
           "Errors not generated because old message was icmp";
       }
       leaf messages-with-bad-code-fields {
         type uint32;
         description
           "Messages with bad code fields";
       }
       leaf messages-less-than-the-minimum-length {
         type uint32;
         description
           "Messages less than the minimum length";
       }
       leaf messages-with-bad-checksum {
         type uint32;
         description
           "Messages with bad checksum";
       }
       leaf messages-with-bad-source-address {
         type uint32;
         description
           "Messages with bad source address";
       }
       leaf messages-with-bad-length {
         type uint32;
         description
           "Messages with bad length";
       }
       leaf echo-drops-with-broadcast-or-multicast-destinaton-address {
         type uint32;
         description
           "Echo drops with broadcast or multicast destination address";
       }
       leaf timestamp-drops-with-broadcast-or-multicast-destination-address {
         type uint32;
         description
           "Timestamp drops with broadcast or multicast destination address";
       }
       leaf message-responses-generated {
         type uint32;
         description
           "Message responses generated";
       }
       list histogram {
         key "type-of-histogram";
         leaf type-of-histogram {
           type string;
           description
             "Input/ouput histogram";
         }
         leaf icmp-echo-reply {
           type uint32;
           description
             "Echo reply";
         }
         leaf icmp-ext-echo-reply {
           type uint32;
           description
             "Extended Echo reply";
         }
         leaf destination-unreachable {
           type uint32;
           description
             "Destination unreachable";
         }
         leaf source-quench {
           type uint32;
           description
             "Source-quench";
         }
         leaf routing-redirect {
           type uint32;
           description
             "Routing redirect";
         }
         leaf alternate-host-address {
           type uint32;
           description
             "Alternate host address";
         }
         leaf icmp-echo {
           type uint32;
           description
             "Echo";
         }
         leaf icmp-ext-echo {
           type uint32;
           description
             "Extended Echo";
         }
         leaf router-advertisement {
           type uint32;
           description
             "Router advertisement";
         }
         leaf router-solicitation {
           type uint32;
           description
             "Router solicitation";
         }
         leaf time-exceeded {
           type uint32;
           description
             "Time exceeded";
         }
         leaf parameter-problem {
           type uint32;
           description
             "Parameter problem";
         }
         leaf time-stamp {
           type uint32;
           description
             "Time stamp";
         }
         leaf time-stamp-reply {
           type uint32;
           description
             "Time stamp reply";
         }
         leaf information-request {
           type uint32;
           description
             "Information request";
         }
         leaf information-request-reply {
           type uint32;
           description
             "Information request reply";
         }
         leaf address-mask-request {
           type uint32;
           description
             "Address mask request";
         }
         leaf address-mask-reply {
           type uint32;
           description
             "Address mask reply";
         }
         leaf traceroute {
           type uint32;
           description
             "Traceroute";
         }
         leaf data-conversion-error {
           type uint32;
           description
             "Data conversion error";
         }
         leaf mobile-host-redirect {
           type uint32;
           description
             "Mobile host redirect";
         }
         leaf ipv6-where-are-you {
           type uint32;
           description
             "IPv6 where-are-you";
         }
         leaf ipv6-i-am-here {
           type uint32;
           description
             "IPv6 i-am-here";
         }
         leaf mobile-registration-request {
           type uint32;
           description
             "Mobile registration request";
         }
         leaf mobile-registration-reply {
           type uint32;
           description
             "Mobile registration reply";
         }
         leaf skip {
           type uint32;
           description
             "Skip";
         }
         leaf photuris {
           type uint32;
           description
             "Photuris";
         }
       }
     }
     container igmp {
       leaf messages-received {
         type uint32;
         description
           "Messages received";
       }
       leaf messages-received-with-too-few-bytes {
         type uint32;
         description
           "Messages received with too few bytes";
       }
       leaf messages-received-with-bad-checksum {
         type uint32;
         description
           "Messages received with bad checksum";
       }
       leaf membership-queries-received {
         type uint32;
         description
           "Membership queries received";
       }
       leaf membership-queries-received-with-invalid-fields {
         type uint32;
         description
           "Membership queries received with invalid fields";
       }
       leaf membership-reports-received {
         type uint32;
         description
           "Membership reports received";
       }
       leaf membership-reports-received-with-invalid-fields {
         type uint32;
         description
           "Membership reports received with invalid fields";
       }
       leaf membership-reports-received-for-groups-to-which-we-belong {
         type uint32;
         description
           "Membership reports received for groups to which we belong";
       }
       leaf membership-reports-sent {
         type uint32;
         description
           "Membership reports sent";
       }
     }
     container ipsec {
       leaf inbound-packets-processed-successfully {
         type uint64;
         description
           "Inbound packets processed successfully";
       }
       leaf inbound-packets-violated-process-security-policy {
         type uint64;
         description
           "Inbound packets violated process security policy";
       }
       leaf inbound-packets-with-no-sa-available {
         type uint64;
         description
           "Inbound packets with no SA available";
       }
       leaf invalid-inbound-packets {
         type uint64;
         description
           "Invalid inbound packets";
       }
       leaf inbound-packets-failed-due-to-insufficient-memory {
         type uint64;
         description
           "Inbound packets failed due to insufficient memory";
       }
       leaf inbound-packets-failed-getting-spi {
         type uint64;
         description
           "Inbound packets failed getting SPI";
       }
       leaf inbound-packets-failed-on-ah-replay-check {
         type uint64;
         description
           "Inbound packets failed on AH replay check";
       }
       leaf inbound-packets-failed-on-esp-replay-check {
         type uint64;
         description
           "Inbound packets failed on ESP replay check";
       }
       leaf inbound-packets-considered-authentic {
         type uint64;
         description
           "Inbound packets considered authentic";
       }
       leaf inbound-packets-failed-on-authentication {
         type uint64;
         description
           "Inbound packets failed on authentication";
       }
       leaf inbound-esp-packets-considered-authentic {
         type uint64;
         description
           "Inbound ESP packets considered authentic";
       }
       leaf inbound-esp-packets-failed-on-authentication {
         type uint64;
         description
           "Inbound ESP packets failed on authentication";
       }
       leaf-list histogram {
         type string;
       }
       leaf ahnames-none {
         type uint64;
         description
           "AH names";
       }
       leaf ahnames-hmac-md5 {
         type uint64;
         description
           "HMAC MD5";
       }
       leaf ahnames-hmac-sha1 {
         type uint64;
         description
           "HMAC SHA1";
       }
       leaf ahnames-md5 {
         type uint64;
         description
           "MD5";
       }
       leaf ahnames-sha {
         type uint64;
         description
           "SHA";
       }
       leaf ahnames-null {
         type uint64;
         description
           "NULL AH name";
       }
       leaf ahnames-hmac-sha2-256 {
         type uint64;
         description
           "HMAC SHA2-256";
       }
       leaf ahnames-hmac-sha2-384 {
         type uint64;
         description
           "HMAC SHA2-384";
       }
       leaf ahnames-hmac-sha2-512 {
         type uint64;
         description
           "HMAC SHA2-512";
       }
       leaf ahnames-hmac-ripemd160 {
         type uint64;
         description
           "HAMC RIPEMD160";
       }
       leaf ahnames-aes-xcbc-mac {
         type uint64;
         description
           "AES XCBC MAC";
       }
       leaf espnames-none {
         type uint64;
         description
           "ESP names";
       }
       leaf espnames-des-cbc {
         type uint64;
         description
           "DES CBC";
       }
       leaf espnames-null {
         type uint64;
         description
           "NULL ESP name";
       }
       leaf espnames-cast128-cbc {
         type uint64;
         description
           "CAST128 CBC";
       }
       leaf espnames-blowfish-cbc {
         type uint64;
         description
           "BLOWFISH CBC";
       }
       leaf espnames-rijndael-cbc {
         type uint64;
         description
           "RIJDAEL CBC";
       }
       leaf espnames-aes-ctr {
         type uint64;
         description
           "AES CTR";
       }
       leaf compnames-none {
         type uint64;
         description
           "NONE COMP names";
       }
       leaf compnames-oui {
         type uint64;
         description
           "OUI";
       }
       leaf compnames-deflate {
         type uint64;
         description
           "DEFLATE";
       }
       leaf compnames-lzs {
         type uint64;
         description
           "LZS";
       }
       leaf protocol {
         type uint64;
         description
           "Protocol";
       }
       leaf outbound-packets-processed-successfully {
         type uint64;
         description
           "Outbound packets processed successfully";
       }
       leaf outbound-packets-violated-process-security-policy {
         type uint64;
         description
           "Outbound packets violated process security policy";
       }
       leaf outbound-packets-with-no-sa-available {
         type uint64;
         description
           "Outbound packets with no SA available";
       }
       leaf invalid-outbound-packets {
         type uint64;
         description
           "Invalid outbound packets";
       }
       leaf outbound-packets-failed-due-to-insufficient-memory {
         type uint64;
         description
           "Outbound packets failed due to insufficient memory";
       }
       leaf outbound-packets-with-no-route {
         type uint64;
         description
           "Outbound packets with no route";
       }
       leaf spd-cache-lookups {
         type uint64;
         description
           "SPD cache lookups";
       }
       leaf spd-cache-misses {
         type uint64;
         description
           "SPD cache misses";
       }
       leaf outbound-packets-with-bundled-sa {
         type uint64;
         description
           "Outbound packets with bundles SAs";
       }
       leaf mbuf-coalesced-during-clone {
         type uint64;
         description
           "Mbuf coleasced during clone";
       }
       leaf cluster-coalesced-during-clone {
         type uint64;
         description
           "Cluster coalesced during clone";
       }
       leaf cluster-copied-during-clone {
         type uint64;
         description
           "Cluster copied during clone";
       }
       leaf mbuf-inserted-during-makespace {
         type uint64;
         description
           "Mbuf inserted during makespace";
       }
       leaf espnames-3des-cbc {
         type uint64;
         description
           "3DES CBC";
       }
     }
     container ah {
       description
         "Authentication header";
       leaf packets-shorter-than-header-shows {
         type uint64;
         description
           "Packets shorter than header shows";
       }
       leaf packets-dropped-as-protocol-unsupported {
         type uint64;
         description
           "Packets dropped protocol unsupported";
       }
       leaf packets-dropped-due-to-no-tdb {
         type uint64;
         description
           "Packets dropped no TDB";
       }
       leaf packets-dropped-due-to-bad-kcr {
         type uint64;
         description
           "Packets dropped bad KCR";
       }
       leaf packets-dropped-due-to-queue-full {
         type uint64;
         description
           "Packets dropped queue full";
       }
       leaf packets-dropped-due-to-no-transform {
         type uint64;
         description
           "Packets dropped no transform";
       }
       leaf replay-counter-wrap {
         type uint64;
         description
           "Replay counter wrap";
       }
       leaf packets-dropped-as-bad-authentication-detected {
         type uint64;
         description
           "Packets dropped bad authentication detected";
       }
       leaf packets-dropped-due-to-bad-authentication-length {
         type uint64;
         description
           "Packets dropped bad authentication length";
       }
       leaf possible-replay-packets-detected {
         type uint64;
         description
           "Possible replay packets detected";
       }
       leaf packets-in {
         type uint64;
         description
           "Packets in";
       }
       leaf packets-out {
         type uint64;
         description
           "Packets out";
       }
       leaf packets-dropped-due-to-invalid-tdb {
         type uint64;
         description
           "Packets dropped invalid TDB";
       }
       leaf bytes-in {
         type uint64;
         description
           "Bytes in";
       }
       leaf bytes-out {
         type uint64;
         description
           "Bytes out";
       }
       leaf packets-dropped-as-larger-than-ip-maxpacket {
         type uint64;
         description
           "Packets dropped larger than maxpacket";
       }
       leaf packets-blocked-due-to-policy {
         type uint64;
         description
           "Packets blocked due to policy";
       }
       leaf crypto-processing-failure {
         type uint64;
         description
           "Crypto processing failure";
       }
       leaf tunnel-sanity-check-failures {
         type uint64;
         description
           "Tunnel sanity check failures";
       }
     }
     container esp {
       description
         "Encapsulating Security Payloads";
       leaf esp-packets-shorter-than-header-shows {
         type uint64;
         description
           "Packets shorter than header shows";
       }
       leaf esp-packets-dropped-as-protocol-not-supported {
         type uint64;
         description
           "Packets dropped protocol unsupported";
       }
       leaf esp-packets-dropped-due-to-no-tdb {
         type uint64;
         description
           "Packets dropped no TDB";
       }
       leaf esp-packets-dropped-due-to-bad-kcr {
         type uint64;
         description
           "Packets dropped bad KCR";
       }
       leaf esp-packets-dropped-due-to-queue-full {
         type uint64;
         description
           "Packets dropped queue full";
       }
       leaf esp-packets-dropped-due-to-no-transform {
         type uint64;
         description
           "Packets dropped no transform";
       }
       leaf esp-packets-dropped-as-bad-ilen {
         type uint64;
         description
           "Packets dropped bad ilen";
       }
       leaf esp-replay-counter-wrap {
         type uint64;
         description
           "Replay counter wrap";
       }
       leaf esp-packets-dropped-as-bad-encryption-detected {
         type uint64;
         description
           "Packets dropped bad encryption detected";
       }
       leaf esp-packets-dropped-as-bad-authentication-detected {
         type uint64;
         description
           "Packets dropped bad authentication detected";
       }
       leaf esp-possible-replay-packets-detected {
         type uint64;
         description
           "Possible replay packets detected";
       }
       leaf esp-packets-in {
         type uint64;
         description
           "Packets in";
       }
       leaf esp-packets-out {
         type uint64;
         description
           "Packets out";
       }
       leaf esp-packets-dropped-as-invalid-tdb {
         type uint64;
         description
           "Packets dropped invalid TDB";
       }
       leaf esp-bytes-in {
         type uint64;
         description
           "Bytes in";
       }
       leaf esp-bytes-out {
         type uint64;
         description
           "Bytes out";
       }
       leaf esp-packets-dropped-as-larger-than-ip-maxpacket {
         type uint64;
         description
           "Packets dropped larger than maxpacket";
       }
       leaf esp-packets-blocked-due-to-policy {
         type uint64;
         description
           "Packets blocked due to policy";
       }
       leaf esp-crypto-processing-failure {
         type uint64;
         description
           "Crypto processing failure";
       }
       leaf esp-tunnel-sanity-check-failures {
         type uint64;
         description
           "Tunnel sanity check failures";
       }
     }
     container ipcomp {
       description
         "IP Payload Compression Protocol";
       leaf ipcomp-packets-shorter-than-header-shows {
         type uint64;
         description
           "Packets shorter than header shows";
       }
       leaf ipcomp-packets-dropped-as-protocol-not-supported {
         type uint64;
         description
           "Packets dropped protocol unsupported";
       }
       leaf ipcomp-packets-dropped-due-to-no-tdb {
         type uint64;
         description
           "Packets dropped no TDB";
       }
       leaf ipcomp-packets-dropped-due-to-bad-kcr {
         type uint64;
         description
           "Packets dropped bad KCR";
       }
       leaf ipcomp-packets-dropped-due-to-queue-full {
         type uint64;
         description
           "Packets dropped queue full";
       }
       leaf ipcomp-packets-dropped-due-to-no-transform {
         type uint64;
         description
           "Packets dropped no transform";
       }
       leaf ipcomp-replay-counter-wrap {
         type uint64;
         description
           "Replay counter wrap";
       }
       leaf ipcomp-packets-in {
         type uint64;
         description
           "Packets in";
       }
       leaf ipcomp-packets-out {
         type uint64;
         description
           "Packets out";
       }
       leaf ipcomp-packets-dropped-as-invalid-tdb {
         type uint64;
         description
           "Packets dropped invalid TDB";
       }
       leaf ipcomp-bytes-in {
         type uint64;
         description
           "Bytes in";
       }
       leaf ipcomp-bytes-out {
         type uint64;
         description
           "Bytes out";
       }
       leaf ipcomp-packets-dropped-as-larger-than-ip-maxpacket {
         type uint64;
         description
           "Packets dropped larger than maxpacket";
       }
       leaf ipcomp-packets-blocked-due-to-policy {
         type uint64;
         description
           "Packets blocked due to policy";
       }
       leaf ipcomp-crypto-processing-failure {
         type uint64;
         description
           "Crypto processing failure";
       }
       leaf packets-sent-uncompressed-threshold {
         type uint64;
         description
           "Packets sent uncompressed threshold";
       }
       leaf packets-sent-uncompressed-useless {
         type uint64;
         description
           "Packets sent uncompressed useless";
       }
     }
     container raw-interface {
       leaf raw-packets-transmitted {
         type uint32;
         description
           "RAW packets transmitted";
       }
       leaf ppoe-packets-transmitted {
         type uint32;
         description
           "PPPOE packets transmitted";
       }
       leaf isdn-packets-transmitted {
         type uint32;
         description
           "ISDN packets transmitted";
       }
       leaf dialer-packets-transmitted {
         type uint32;
         description
           "DIALER packets transmitted";
       }
       leaf ppp-packets-transmitted-to-pppd {
         type uint32;
         description
           "PPP packets transmitted to pppd";
       }
       leaf ppp-packets-transmitted-to-jppd {
         type uint32;
         description
           "PPP packets transmitted to jppd";
       }
       leaf igmpl2-packets-transmitted {
         type uint32;
         description
           "IGMPL2 packets transmitted";
       }
       leaf mldl2-packets-transmitted {
         type uint32;
         description
           "MLDL2 packets transmitted";
       }
       leaf fibre-channel-packets-transmitted {
         type uint32;
         description
           "Fibre Channel packets transmitted";
       }
       leaf fip-packets-transmitted {
         type uint32;
         description
           "FIP packets transmitted";
       }
       leaf stp-packets-transmitted {
         type uint32;
         description
           "STP packets transmitted";
       }
       leaf lacp-packets-transmitted {
         type uint32;
         description
           "LACP packets transmitted";
       }
       leaf vccp-packets-transmitted {
         type uint32;
         description
           "VCCP packets transmitted";
       }
       leaf output-drops-due-to-transmit-error {
         type uint32;
         description
           "Output drops due to tx error";
       }
       leaf mpu-packets-transmitted {
         type uint32;
         description
           "MPU packets transmitted";
       }
       leaf faboam-packets-transmitted {
         type uint32;
         description
           "Fabric OAM packets transmitted";
       }
       leaf pppoe-packets-received {
         type uint32;
         description
           "PPPOE packets received";
       }
       leaf isdn-packets-received {
         type uint32;
         description
           "ISDN packets received";
       }
       leaf dialer-packets-received {
         type uint32;
         description
           "DIALER packets received";
       }
       leaf ppp-packets-received-from-pppd {
         type uint32;
         description
           "PPP packets received from pppd";
       }
       leaf mpu-packets-received {
         type uint32;
         description
           "MPU packets received";
       }
       leaf ppp-packets-received-from-jppd {
         type uint32;
         description
           "PPP packets received from jppd";
       }
       leaf igmpl2-packets-received {
         type uint32;
         description
           "IGMPL2 packets received";
       }
       leaf fibre-channel-packets-received {
         type uint32;
         description
           "Fibre Channel packets received";
       }
       leaf fip-packets-received {
         type uint32;
         description
           "FIP packets received";
       }
       leaf stp-packets-received {
         type uint32;
         description
           "STP packets received";
       }
       leaf lacp-packets-received {
         type uint32;
         description
           "LACP packets received";
       }
       leaf vccp-packets-received {
         type uint32;
         description
           "VCCP packets received";
       }
       leaf faboam-packets-received {
         type uint32;
         description
           "Fabric OAM packets received";
       }
       leaf fibre-channel-packets-dropped {
         type uint32;
         description
           "Fibre Channel packets dropped";
       }
       leaf fip-packets-dropped {
         type uint32;
         description
           "FIP packets dropped";
       }
       leaf stp-packets-dropped {
         type uint32;
         description
           "STP packets dropped";
       }
       leaf lacp-packets-dropped {
         type uint32;
         description
           "LACP packets dropped";
       }
       leaf vccp-packets-dropped {
         type uint32;
         description
           "VCCP packets dropped";
       }
       leaf faboam-packets-dropped {
         type uint32;
         description
           "Fabric OAM packets dropped";
       }
       leaf mldl2-packets-received {
         type uint32;
         description
           "MLDL2 packets received";
       }
       leaf input-drops-due-to-bogus-protocol {
         type uint32;
         description
           "Input drops due to bogus protocol";
       }
       leaf input-drops-due-to-no-mbufs-available {
         type uint32;
         description
           "Input drops due to no mbufs available";
       }
       leaf input-drops-due-to-no-space-in-socket {
         type uint32;
         description
           "Input drops due to no space in socket";
       }
       leaf input-drops-due-to-no-socket {
         type uint32;
         description
           "Input drops due to no socket";
       }
     }
     container arp {
       leaf datagrams-received {
         type uint32;
         description
           "Datagrams received";
       }
       leaf arp-requests-received {
         type uint32;
         description
           "ARP requests received";
       }
       leaf arp-replies-received {
         type uint32;
         description
           "ARP replies received";
       }
       leaf resolution-request-received {
         type uint32;
         description
           "Resolution request received";
       }
       leaf resolution-request-dropped {
         type uint32;
         description
           "Resolution request dropped";
       }
       leaf unrestricted-proxy-requests {
         type uint32;
         description
           "Unrestricted proxy requests";
       }
       leaf restricted-proxy-requests {
         type uint32;
         description
           "Restricted proxy requests";
       }
       leaf received-proxy-requests {
         type uint32;
         description
           "Received proxy requests";
       }
       leaf proxy-requests-not-proxied {
         type uint32;
         description
           "Unrestricted proxy requests not proxied";
       }
       leaf restricted-proxy-requests-not-proxied {
         type uint32;
         description
           "Restricted proxy requests not proxied";
       }
       leaf datagrams-with-bogus-interface {
         type uint32;
         description
           "Datagrams with bogus interface";
       }
       leaf datagrams-with-incorrect-length {
         type uint32;
         description
           "Datagrams with incorrect length";
       }
       leaf datagrams-for-non-ip-protocol {
         type uint32;
         description
           "Datagrams for non-IP protocol";
       }
       leaf datagrams-with-unsupported-opcode {
         type uint32;
         description
           "Datagrams with unsupported op code";
       }
       leaf datagrams-with-bad-protocol-address-length {
         type uint32;
         description
           "Datagrams with bad protocol address length";
       }
       leaf datagrams-with-bad-hardware-address-length {
         type uint32;
         description
           "Datagrams with bad hardware address length";
       }
       leaf datagrams-with-multicast-source-address {
         type uint32;
         description
           "Datagrams with multicast source address";
       }
       leaf datagrams-with-multicast-target-address {
         type uint32;
         description
           "Datagrams with multicast target address";
       }
       leaf datagrams-with-my-own-hardware-address {
         type uint32;
         description
           "Datagrams with my own hardware address";
       }
       leaf datagrams-for-an-address-not-on-the-interface {
         type uint32;
         description
           "Datagrams for an address not on the interface";
       }
       leaf datagrams-with-a-broadcast-source-address {
         type uint32;
         description
           "Datagrams with a broadcast source address";
       }
       leaf datagrams-with-source-address-duplicate-to-mine {
         type uint32;
         description
           "Datagrams with source address duplicate to mine";
       }
       leaf datagrams-which-were-not-for-me {
         type uint32;
         description
           "Datagrams which were not for me";
       }
       leaf packets-discarded-waiting-for-resolution {
         type uint32;
         description
           "Packets discarded waiting for resolution";
       }
       leaf packets-sent-after-waiting-for-resolution {
         type uint32;
         description
           "Packets sent after waiting for resolution";
       }
       leaf arp-requests-sent {
         type uint32;
         description
           "ARP requests sent";
       }
       leaf arp-replies-sent {
         type uint32;
         description
           "ARP replies sent";
       }
       leaf requests-for-memory-denied {
         type uint32;
         description
           "Requests for memory denied";
       }
       leaf requests-dropped-on-entry {
         type uint32;
         description
           "Requests dropped on entry";
       }
       leaf requests-dropped-during-retry {
         type uint32;
         description
           "Requests dropped during retry";
       }
       leaf requests-dropped-due-to-interface-deletion {
         type uint32;
         description
           "Requests dropped due to interface deletion";
       }
       leaf requests-on-unnumbered-interfaces {
         type uint32;
         description
           "Requests on unnumbered interfaces";
       }
       leaf new-requests-on-unnumbered-interfaces {
         type uint32;
         description
           "New requests on unnumbered interfaces";
       }
       leaf replies-from-unnumbered-interfaces {
         type uint32;
         description
           "Replies for from unnumbered interfaces";
       }
       leaf requests-on-unnumbered-interface-with-non-subnetted-donor {
         type uint32;
         description
           "Requests on unnumbered interface with non-subnetted donor";
       }
       leaf replies-from-unnumbered-interface-with-non-subnetted-donor {
         type uint32;
         description
           "Replies from unnumbered interface with non-subnetted donor";
       }
       leaf arp-packets-rejected-as-family-is-configured-with-deny-arp {
         type uint32;
         description
           "Arp packets rejected as family is configured with deny arp";
       }
       leaf arp-response-packets-are-rejected-on-mc-ae-icl-interface {
         type uint32;
         description
           "Arp response packets are rejected on mc-ae icl interface";
       }
       leaf arp-replies-are-rejected-as-source-and-destination-is-same {
         type uint32;
         description
           "Arp replies are rejected as source and destination is same";
       }
       leaf arp-probe-for-proxy-address-reachable-from-the-incoming-interface {
         type uint32;
         description
           "Arp probe for proxy address reachable from the incoming 
           interface";
       }
       leaf arp-request-discarded-for-vrrp-source-address {
         type uint32;
         description
           "Arp request discarded for vrrp source address";
       }
       leaf self-arp-request-packet-received-on-irb-interface {
         type uint32;
         description
           "Self arp request packet received on irb interface";
       }
       leaf proxy-arp-request-discarded-as-source-ip-is-a-proxy-target {
         type uint32;
         description
           "Proxy arp request discarded as source ip is a proxy target";
       }
       leaf arp-packets-are-dropped-as-nexthop-allocation-failed {
         type uint32;
         description
           "Arp packets are dropped as nexthop allocation failed";
       }
       leaf arp-packets-received-from-peer-vrrp-router-and-discarded {
         type uint32;
         description
           "Arp packets received from peer vrrp router and discarded";
       }
       leaf arp-packets-are-rejected-as-target-ip-arp-resolve-is-in-progress {
         type uint32;
         description
           "Arp packets are rejected as target ip arp resolve is in progress";
       }
       leaf grat-arp-packets-are-ignored-as-mac-address-is-not-changed {
         type uint32;
         description
           "Grat arp packets are ignored as mac address is not changed";
       }
       leaf arp-packets-are-dropped-from-peer-vrrp {
         type uint32;
         description
           "Arp packets are dropped from peer vrrp";
       }
       leaf arp-packets-are-dropped-as-driver-call-failed {
         type uint32;
         description
           "Arp packets are dropped as driver call failed";
       }
       leaf arp-packets-are-dropped-as-source-is-not-validated {
         type uint32;
         description
           "Arp packets are dropped as source is not validated";
       }
       leaf arp-system-max {
         type uint64;
         description
           "Max ARP NH system cache";
       }
       leaf arp-public-max {
         type uint64;
         description
           "Max public ARP NH cache";
       }
       leaf arp-iri-max {
         type uint64;
         description
           "Max iri ARP NH cache";
       }
       leaf arp-mgt-max {
         type uint64;
         description
           "Max mgt intf ARP NH cache";
       }
       leaf arp-unicast-nh-count {
         type uint64;
         description
           "Number of unicast Nexthop";
       }
       leaf arp-hold-nh-count {
         type uint64;
         description
           "Number of hold Nexthop";
       }
       leaf arp-public-cnt {
         type uint64;
         description
           "Current public ARP NH count";
       }
       leaf arp-iri-cnt {
         type uint64;
         description
           "Current iri ARP NH count";
       }
       leaf arp-mgt-cnt {
         type uint64;
         description
           "Current management ARP NH count";
       }
       leaf arp-system-drop {
         type uint64;
         description
           "System ARP NH drops";
       }
       leaf arp-public-drop {
         type uint64;
         description
           "Public ARP NH drops";
       }
       leaf arp-iri-drop {
         type uint64;
         description
           "IRI ARP NH drops";
       }
       leaf arp-mgt-drop {
         type uint64;
         description
           "Management intf ARP NH drops";
       }
       leaf arp-cache-count {
         type uint32;
         description
           "Number of entries present in ARP cache";
       }
     }
     container ip6 {
       leaf total-packets-received {
         type uint64;
         description
           "Total packets received";
       }
       leaf ip6-packets-with-size-smaller-than-minimum {
         type uint64;
         description
           "Ip6 packets with size smaller than minimum";
       }
       leaf packets-with-datasize-less-than-data-length {
         type uint64;
         description
           "Packets with data size < data length";
       }
       leaf ip6-packets-with-bad-options {
         type uint64;
         description
           "Ip6 packets with bad options";
       }
       leaf ip6-packets-with-incorrect-version-number {
         type uint64;
         description
           "Ip6 packets with incorrect version number";
       }
       leaf ip6-fragments-received {
         type uint64;
         description
           "Ip6 fragments received";
       }
       leaf duplicate-or-out-of-space-fragments-dropped {
         type uint64;
         description
           "Fragments dropped (dup or out of space)";
       }
       leaf ip6-fragments-dropped-after-timeout {
         type uint64;
         description
           "Ip6 fragments dropped after timeout";
       }
       leaf fragments-that-exceeded-limit {
         type uint64;
         description
           "Fragment sessions dropped due to queue overflow";
       }
       leaf ip6-packets-reassembled-ok {
         type uint64;
         description
           "Ip6 packets reassembled ok";
       }
       leaf ip6-packets-for-this-host {
         type uint64;
         description
           "Ip6 packets for this host";
       }
       leaf ip6-packets-forwarded {
         type uint64;
         description
           "Ip6 packets forwarded";
       }
       leaf ip6-packets-not-forwardable {
         type uint64;
         description
           "Ip6 packets not forwardable";
       }
       leaf ip6-redirects-sent {
         type uint64;
         description
           "Ip6 redirects sent";
       }
       leaf ip6-packets-sent-from-this-host {
         type uint64;
         description
           "Ip6 packets sent from this host";
       }
       leaf ip6-packets-sent-with-fabricated-ip-header {
         type uint64;
         description
           "Ip6 packets sent with fabricated ip header";
       }
       leaf ip6-output-packets-dropped-due-to-no-bufs {
         type uint64;
         description
           "Ip6 output packets dropped due to no bufs";
       }
       leaf ip6-output-packets-discarded-due-to-no-route {
         type uint64;
         description
           "Ip6 output packets discarded due to no route";
       }
       leaf ip6-output-datagrams-fragmented {
         type uint64;
         description
           "Ip6output datagrams fragmented";
       }
       leaf ip6-fragments-created {
         type uint64;
         description
           "Ip6 fragments created";
       }
       leaf ip6-datagrams-that-can-not-be-fragmented {
         type uint64;
         description
           "Ip6 datagrams that can not be fragmented";
       }
       leaf packets-that-violated-scope-rules {
         type uint64;
         description
           "Packets that violated scope rules";
       }
       leaf multicast-packets-which-we-do-not-join {
         type uint64;
         description
           "Multicast packets which we don't join";
       }
       leaf-list histogram {
         type string;
       }
       leaf ip6nh-hop-by-hop {
         type uint64;
         description
           "Hop by hop";
       }
       leaf ip6nh-icmp {
         type uint64;
         description
           "ICMP";
       }
       leaf ip6nh-igmp {
         type uint64;
         description
           "IGMP";
       }
       leaf ip6nh-ip {
         type uint64;
         description
           "IP";
       }
       leaf ip6nh-tcp {
         type uint64;
         description
           "TCP";
       }
       leaf ip6nh-udp {
         type uint64;
         description
           "UDP";
       }
       leaf ip6nh-idp {
         type uint64;
         description
           "IDP";
       }
       leaf ip6nh-tp {
         type uint64;
         description
           "TP";
       }
       leaf ip6nh-ip6 {
         type uint64;
         description
           "IP6";
       }
       leaf ip6nh-routing {
         type uint64;
         description
           "Routing";
       }
       leaf ip6nh-fragment {
         type uint64;
         description
           "Fragment";
       }
       leaf ip6nh-esp {
         type uint64;
         description
           "Esp";
       }
       leaf ip6nh-ah {
         type uint64;
         description
           "AH";
       }
       leaf ip6nh-icmp6 {
         type uint64;
         description
           "ICMP6";
       }
       leaf ip6nh-no-next-header {
         type uint64;
         description
           "No next header";
       }
       leaf ip6nh-destination-option {
         type uint64;
         description
           "Destination option";
       }
       leaf ip6nh-isoip {
         type uint64;
         description
           "ISOIP";
       }
       leaf ip6nh-ospf {
         type uint64;
         description
           "OSPF";
       }
       leaf ip6nh-ethernet {
         type uint64;
         description
           "Ethernet";
       }
       leaf ip6nh-pim {
         type uint64;
         description
           "PIM";
       }
       leaf mbuf-statistics {
         type string;
         description
           "Header";
       }
       leaf packets-whose-headers-are-not-continuous {
         type uint64;
         description
           "Packets whose headers are not continuous";
       }
       leaf tunneling-packets-that-can-not-find-gif {
         type uint64;
         description
           "Tunneling packets that can't find GIF";
       }
       leaf packets-discarded-due-to-too-may-headers {
         type uint64;
         description
           "Packets discarded due to too many headers";
       }
       leaf failures-of-source-address-selection {
         type uint64;
         description
           "Failures of source address selection";
       }
       leaf forward-cache-hit {
         type uint64;
         description
           "Forward cache hit";
       }
       leaf forward-cache-miss {
         type uint64;
         description
           "Forward cache miss";
       }
       leaf ip6-packets-destined-to-dead-next-hop {
         type uint64;
         description
           "Ip6 packets destined to dead next hop";
       }
       leaf ip6-option-packets-dropped-due-to-rate-limit {
         type uint64;
         description
           "Ip6 option packets dropped due to rate limit";
       }
       leaf ip6-packets-dropped {
         type uint64;
         description
           "Ip6 packets dropped";
       }
       leaf packets-dropped-due-to-bad-protocol {
         type uint64;
         description
           "Packets dropped due to bad protocol";
       }
       leaf transit-re-packet-dropped-on-mgmt-interface {
         type uint64;
         description
           "Transit re packet(null) dropped on mgmt interface";
       }
       leaf packet-used-first-nexthop-in-ecmp-unilist {
         type uint64;
         description
           "Packet(null) used first nexthop in ecmp unilist";
       }
       list header-type {
         key "header-for-source-address-selection";
         leaf header-for-source-address-selection {
           type string;
           description
             "Header";
         }
         leaf node-locals {
           type uint64;
           description
             "Node locals as source address";
         }
         leaf link-locals {
           type uint64;
           description
             "Link locals as source address";
         }
         leaf site-locals {
           type uint64;
           description
             "Site locals as source address";
         }
         leaf globals {
           type uint64;
           description
             "Globals as source address";
         }
         leaf address-scope {
           type uint64;
           description
             "Address scope";
         }
         leaf hex-value {
           type uint64;
           description
             "Hexa decimal value";
         }
       }
     }
     container icmp6 {
       leaf protocol-name {
         type string;
       }
       leaf calls-to-icmp6-error {
         type uint64;
         description
           "Calls to icmp6 error";
       }
       leaf errors-not-generated-because-old-message-was-icmp-error {
         type uint64;
         description
           "Errors not generated because old message was icmp error";
       }
       leaf errors-not-generated-because-rate-limitation {
         type uint64;
         description
           "Errors not generated because rate limitation";
       }
       leaf icmp6-messages-with-bad-code-fields {
         type uint64;
         description
           "Icmp6 messages with bad code fields";
       }
       leaf messages-less-than-minimum-length {
         type uint64;
         description
           "Messages < minimum length";
       }
       leaf bad-checksums {
         type uint64;
         description
           "Bad checksums";
       }
       leaf icmp6-messages-with-bad-length {
         type uint64;
         description
           "Icmp6 messages with bad length";
       }
       leaf histogram-of-error-messages-to-be-generated {
         type string;
         description
           "Header";
       }
       leaf no-route {
         type uint64;
         description
           "No route";
       }
       leaf administratively-prohibited {
         type uint64;
         description
           "Administratively prohibited";
       }
       leaf beyond-scope {
         type uint64;
         description
           "Beyond scope";
       }
       leaf address-unreachable {
         type uint64;
         description
           "Address unreachable";
       }
       leaf port-unreachable {
         type uint64;
         description
           "Port unreachable";
       }
       leaf time-exceed-transit {
         type uint64;
         description
           "Time exceed transit";
       }
       leaf time-exceed-reassembly {
         type uint64;
         description
           "Time exceed reassembly";
       }
       leaf time-exceed-srv6-tunneled {
         type uint64;
         description
           "Time exceed srv6 tunneled";
       }
       leaf erroneous-header-field {
         type uint64;
         description
           "Erroneous header field";
       }
       leaf unrecognized-next-header {
         type uint64;
         description
           "Unrecognized next header";
       }
       leaf unrecognized-option {
         type uint64;
         description
           "Unrecognized option";
       }
       leaf unknown {
         type uint64;
         description
           "Unknown";
       }
       leaf icmp6-message-responses-generated {
         type uint64;
         description
           "Icmp6 message responses generated";
       }
       leaf messages-with-too-many-nd-options {
         type uint64;
         description
           "Messages with too many ND options";
       }
       leaf nd-system-max {
         type uint64;
         description
           "Max ND NH system cache";
       }
       leaf nd-public-max {
         type uint64;
         description
           "Max public ND NH cache";
       }
       leaf nd-iri-max {
         type uint64;
         description
           "Max iri ND NH cache";
       }
       leaf nd-mgt-max {
         type uint64;
         description
           "Max mgt intf ND NH cache";
       }
       leaf nd-unicast-nh-count {
         type uint64;
         description
           "Number of unicast Nexthop";
       }
       leaf nd-hold-nh-count {
         type uint64;
         description
           "Number of hold Nexthop";
       }
       leaf nd-public-cnt {
         type uint64;
         description
           "Current public ND NH count";
       }
       leaf nd-iri-cnt {
         type uint64;
         description
           "Current iri ND NH count";
       }
       leaf nd-mgt-cnt {
         type uint64;
         description
           "Current management ND NH count";
       }
       leaf nd-system-drop {
         type uint64;
         description
           "System ND NH drops";
       }
       leaf nd-public-drop {
         type uint64;
         description
           "Public ND NH drops";
       }
       leaf nd-iri-drop {
         type uint64;
         description
           "IRI ND NH drops";
       }
       leaf nd-mgt-drop {
         type uint64;
         description
           "Management intf ND NH drops";
       }
       leaf nd6-requests-dropped-on-entry {
         type uint64;
         description
           "ND nexthops dropped on entry by RED mark";
       }
       leaf nd6-requests-dropped-during-retry {
         type uint64;
         description
           "ND nexthop%s dropped on timer expire by RED mark";
       }
       leaf nd6-ndp-proxy-requests {
         type uint64;
         description
           "Interface-restricted ndp proxy requests";
       }
       leaf nd6-dad-proxy-requests {
         type uint64;
         description
           "Interface-restricted dad proxy requests";
       }
       leaf nd6-ndp-proxy-responses {
         type uint64;
         description
           "Interface-restricted ndp proxy responses";
       }
       leaf nd6-dad-proxy-conflicts {
         type uint64;
         description
           "Interface-restricted dad proxy conflicts";
       }
       leaf nd6-dup-proxy-responses {
         type uint64;
         description
           "Interface-restricted dad proxy duplicates";
       }
       leaf nd6-ndp-proxy-resolve-cnt {
         type uint64;
         description
           "Interface-restricted ndp proxy resolve requests";
       }
       leaf nd6-dad-proxy-resolve-cnt {
         type uint64;
         description
           "Interface-restricted dad proxy resolve requests";
       }
       leaf nd6-dad-proxy-eqmac-drop {
         type uint64;
         description
           "Interface-restricted dad packets from same node dropped";
       }
       leaf nd6-dad-proxy-nomac-drop {
         type uint64;
         description
           "Interface-restricted proxy packets dropped with nomac";
       }
       leaf nd6-ndp-proxy-unr-requests {
         type uint64;
         description
           "Interface-unrestricted ndp proxy requests";
       }
       leaf nd6-dad-proxy-unr-requests {
         type uint64;
         description
           "Interface-unrestricted dad proxy requests";
       }
       leaf nd6-ndp-proxy-unr-responses {
         type uint64;
         description
           "Interface-unrestricted ndp proxy responses";
       }
       leaf nd6-ndp-proxy-user-rt-unr-responses {
         type uint64;
         description
           "Interface-unrestricted user route ndp proxy responses";
       }
       leaf nd6-dad-proxy-unr-conflicts {
         type uint64;
         description
           "Interface-unrestricted dad proxy conflicts";
       }
       leaf nd6-dad-proxy-unr-responses {
         type uint64;
         description
           "Interface-unrestricted dad proxy duplicates";
       }
       leaf nd6-ndp-proxy-unr-resolve-cnt {
         type uint64;
         description
           "Interface-unrestricted ndp proxy resolve requests";
       }
       leaf nd6-dad-proxy-unr-resolve-cnt {
         type uint64;
         description
           "Interface-unrestricted dad proxy resolve requests";
       }
       leaf nd6-dad-proxy-unr-eqport-drop {
         type uint64;
         description
           "Interface-unrestricted dad packets from same port dropped";
       }
       leaf nd6-dad-proxy-unr-nomac-drop {
         type uint64;
         description
           "Interface-unrestricted proxy packets dropped with nomac";
       }
       leaf nd6-dad-ns-with-enhanced-dad {
         type uint64;
         description
           "NS DAD sent with nonce option";
       }
       leaf nd6-dad-ns-enhanced-dad-looped {
         type uint64;
         description
           "NS Enhanced DAD with same nonce looped";
       }
       leaf histogram-type {
         type string;
       }
       leaf unreachable-icmp6-packets {
         type uint64;
         description
           "Unreachable icmp6 packets";
       }
       leaf packet-too-big {
         type uint64;
         description
           "Packet too big";
       }
       leaf time-exceeded-icmp6-packets {
         type uint64;
         description
           "Time exceeded icmp6 packets";
       }
       leaf parameter-problem-icmp6-packets {
         type uint64;
         description
           "Parameter problem icmp6 packets";
       }
       leaf icmp6-echo {
         type uint64;
       }
       leaf icmp6-ext-echo {
         type uint64;
       }
       leaf icmp6-echo-reply {
         type uint64;
       }
       leaf icmp6-ext-echo-reply {
         type uint64;
       }
       leaf multicast-listener-query {
         type uint64;
         description
           "Multicast listener query";
       }
       leaf multicast-listener-report {
         type uint64;
         description
           "Multicast listener report";
       }
       leaf multicast-listener-done {
         type uint64;
         description
           "Multicast listener done";
       }
       leaf router-solicitation-icmp6-packets {
         type uint64;
         description
           "Router solicitation icmp6 packets";
       }
       leaf router-advertisement-icmp6-packets {
         type uint64;
         description
           "Router advertisement icmp6 packets";
       }
       leaf neighbor-solicitation {
         type uint64;
         description
           "Neighbor solicitation";
       }
       leaf neighbor-advertisement {
         type uint64;
         description
           "Neighbor advertisement";
       }
       leaf redirect {
         type uint64;
         description
           "Redirect";
       }
       leaf router-renumbering {
         type uint64;
         description
           "Router renumbering";
       }
       leaf node-information-request {
         type uint64;
         description
           "Node information request";
       }
       leaf node-information-reply {
         type uint64;
         description
           "Node information reply";
       }
       leaf version-2-multicast-listener-report {
         type uint64;
         description
           "Version 2 Multicast Listener Report";
       }
       container output-histogram {
         leaf histogram-type {
           type string;
         }
         leaf unreachable-icmp6-packets {
           type uint64;
           description
             "Unreachable icmp6 packets";
         }
         leaf packet-too-big {
           type uint64;
           description
             "Packet too big";
         }
         leaf time-exceeded-icmp6-packets {
           type uint64;
           description
             "Time exceeded icmp6 packets";
         }
         leaf parameter-problem-icmp6-packets {
           type uint64;
           description
             "Parameter problem icmp6 packets";
         }
         leaf icmp6-echo {
           type uint64;
         }
         leaf icmp6-ext-echo {
           type uint64;
         }
         leaf icmp6-echo-reply {
           type uint64;
         }
         leaf icmp6-ext-echo-reply {
           type uint64;
         }
         leaf multicast-listener-query {
           type uint64;
           description
             "Multicast listener query";
         }
         leaf multicast-listener-report {
           type uint64;
           description
             "Multicast listener report";
         }
         leaf multicast-listener-done {
           type uint64;
           description
             "Multicast listener done";
         }
         leaf router-solicitation-icmp6-packets {
           type uint64;
           description
             "Router solicitation icmp6 packets";
         }
         leaf router-advertisement-icmp6-packets {
           type uint64;
           description
             "Router advertisement icmp6 packets";
         }
         leaf neighbor-solicitation {
           type uint64;
           description
             "Neighbor solicitation";
         }
         leaf neighbor-advertisement {
           type uint64;
           description
             "Neighbor advertisement";
         }
         leaf redirect {
           type uint64;
           description
             "Redirect";
         }
         leaf router-renumbering {
           type uint64;
           description
             "Router renumbering";
         }
         leaf node-information-request {
           type uint64;
           description
             "Node information request";
         }
         leaf node-information-reply {
           type uint64;
           description
             "Node information reply";
         }
         leaf version-2-multicast-listener-report {
           type uint64;
           description
             "Version 2 Multicast Listener Report";
         }
         leaf-list histogram {
           type string;
         }
         leaf reserved {
           type uint64;
           description
             "Reserved";
         }
         leaf getspi {
           type uint64;
           description
             "Getspi";
         }
         leaf update {
           type uint64;
           description
             "Update";
         }
         leaf add {
           type uint64;
           description
             "Add";
         }
         leaf delete {
           type uint64;
           description
             "Delete";
         }
         leaf get {
           type uint64;
           description
             "Get";
         }
         leaf acquire {
           type uint64;
           description
             "Acquire";
         }
         leaf register {
           type uint64;
           description
             "Register";
         }
         leaf expire {
           type uint64;
           description
             "Expire";
         }
         leaf flush {
           type uint64;
           description
             "Flush";
         }
         leaf dump {
           type uint64;
           description
             "Dump";
         }
         leaf x-promisc {
           type uint64;
           description
             "X_PROMISC";
         }
         leaf x-pchange {
           type uint64;
           description
             "X_PCHANGE";
         }
         leaf x-spdupdate {
           type uint64;
           description
             "X_SPDUPDATE";
         }
         leaf x-spdadd {
           type uint64;
           description
             "X_SPDADD";
         }
         leaf x-spddelete {
           type uint64;
           description
             "X_SPDDELETE";
         }
         leaf x-spdget {
           type uint64;
           description
             "X_SPDGET";
         }
         leaf x-spdacquire {
           type uint64;
           description
             "X_SPDACQUIRE";
         }
         leaf x-spddump {
           type uint64;
           description
             "X_SPDDUMP";
         }
         leaf x-spdflush {
           type uint64;
           description
             "X_SPDFLUSH";
         }
         leaf x-spdsetidx {
           type uint64;
           description
             "X_SPDSETIDX";
         }
         leaf x-spdexpire {
           type uint64;
           description
             "X_SPDEXPIRE";
         }
         leaf x-spddelete2 {
           type uint64;
           description
             "X_SPDDELETE2";
         }
       }
       container input-histogram {
         leaf histogram-type {
           type string;
         }
         leaf unreachable-icmp6-packets {
           type uint64;
           description
             "Unreachable icmp6 packets";
         }
         leaf packet-too-big {
           type uint64;
           description
             "Packet too big";
         }
         leaf time-exceeded-icmp6-packets {
           type uint64;
           description
             "Time exceeded icmp6 packets";
         }
         leaf parameter-problem-icmp6-packets {
           type uint64;
           description
             "Parameter problem icmp6 packets";
         }
         leaf icmp6-echo {
           type uint64;
         }
         leaf icmp6-ext-echo {
           type uint64;
         }
         leaf icmp6-echo-reply {
           type uint64;
         }
         leaf icmp6-ext-echo-reply {
           type uint64;
         }
         leaf multicast-listener-query {
           type uint64;
           description
             "Multicast listener query";
         }
         leaf multicast-listener-report {
           type uint64;
           description
             "Multicast listener report";
         }
         leaf multicast-listener-done {
           type uint64;
           description
             "Multicast listener done";
         }
         leaf router-solicitation-icmp6-packets {
           type uint64;
           description
             "Router solicitation icmp6 packets";
         }
         leaf router-advertisement-icmp6-packets {
           type uint64;
           description
             "Router advertisement icmp6 packets";
         }
         leaf neighbor-solicitation {
           type uint64;
           description
             "Neighbor solicitation";
         }
         leaf neighbor-advertisement {
           type uint64;
           description
             "Neighbor advertisement";
         }
         leaf redirect {
           type uint64;
           description
             "Redirect";
         }
         leaf router-renumbering {
           type uint64;
           description
             "Router renumbering";
         }
         leaf node-information-request {
           type uint64;
           description
             "Node information request";
         }
         leaf node-information-reply {
           type uint64;
           description
             "Node information reply";
         }
         leaf version-2-multicast-listener-report {
           type uint64;
           description
             "Version 2 Multicast Listener Report";
         }
         leaf-list histogram {
           type string;
         }
         leaf reserved {
           type uint64;
           description
             "Reserved";
         }
         leaf getspi {
           type uint64;
           description
             "Getspi";
         }
         leaf update {
           type uint64;
           description
             "Update";
         }
         leaf add {
           type uint64;
           description
             "Add";
         }
         leaf delete {
           type uint64;
           description
             "Delete";
         }
         leaf get {
           type uint64;
           description
             "Get";
         }
         leaf acquire {
           type uint64;
           description
             "Acquire";
         }
         leaf register {
           type uint64;
           description
             "Register";
         }
         leaf expire {
           type uint64;
           description
             "Expire";
         }
         leaf flush {
           type uint64;
           description
             "Flush";
         }
         leaf dump {
           type uint64;
           description
             "Dump";
         }
         leaf x-promisc {
           type uint64;
           description
             "X_PROMISC";
         }
         leaf x-pchange {
           type uint64;
           description
             "X_PCHANGE";
         }
         leaf x-spdupdate {
           type uint64;
           description
             "X_SPDUPDATE";
         }
         leaf x-spdadd {
           type uint64;
           description
             "X_SPDADD";
         }
         leaf x-spddelete {
           type uint64;
           description
             "X_SPDDELETE";
         }
         leaf x-spdget {
           type uint64;
           description
             "X_SPDGET";
         }
         leaf x-spdacquire {
           type uint64;
           description
             "X_SPDACQUIRE";
         }
         leaf x-spddump {
           type uint64;
           description
             "X_SPDDUMP";
         }
         leaf x-spdflush {
           type uint64;
           description
             "X_SPDFLUSH";
         }
         leaf x-spdsetidx {
           type uint64;
           description
             "X_SPDSETIDX";
         }
         leaf x-spdexpire {
           type uint64;
           description
             "X_SPDEXPIRE";
         }
         leaf x-spddelete2 {
           type uint64;
           description
             "X_SPDDELETE2";
         }
       }
     }
     container ipsec6 {
       leaf inbound-packets-processed-successfully {
         type uint64;
         description
           "Inbound packets processed successfully";
       }
       leaf inbound-packets-violated-process-security-policy {
         type uint64;
         description
           "Inbound packets violated process security policy";
       }
       leaf inbound-packets-with-no-sa-available {
         type uint64;
         description
           "Inbound packets with no SA available";
       }
       leaf invalid-inbound-packets {
         type uint64;
         description
           "Invalid inbound packets";
       }
       leaf inbound-packets-failed-due-to-insufficient-memory {
         type uint64;
         description
           "Inbound packets failed due to insufficient memory";
       }
       leaf inbound-packets-failed-getting-spi {
         type uint64;
         description
           "Inbound packets failed getting SPI";
       }
       leaf inbound-packets-failed-on-ah-replay-check {
         type uint64;
         description
           "Inbound packets failed on AH replay check";
       }
       leaf inbound-packets-failed-on-esp-replay-check {
         type uint64;
         description
           "Inbound packets failed on ESP replay check";
       }
       leaf inbound-packets-considered-authentic {
         type uint64;
         description
           "Inbound packets considered authentic";
       }
       leaf inbound-packets-failed-on-authentication {
         type uint64;
         description
           "Inbound packets failed on authentication";
       }
       leaf inbound-esp-packets-considered-authentic {
         type uint64;
         description
           "Inbound ESP packets considered authentic";
       }
       leaf inbound-esp-packets-failed-on-authentication {
         type uint64;
         description
           "Inbound ESP packets failed on authentication";
       }
       leaf-list histogram {
         type string;
       }
       leaf ahnames-none {
         type uint64;
         description
           "AH names";
       }
       leaf ahnames-hmac-md5 {
         type uint64;
         description
           "HMAC MD5";
       }
       leaf ahnames-hmac-sha1 {
         type uint64;
         description
           "HMAC SHA1";
       }
       leaf ahnames-md5 {
         type uint64;
         description
           "MD5";
       }
       leaf ahnames-sha {
         type uint64;
         description
           "SHA";
       }
       leaf ahnames-null {
         type uint64;
         description
           "NULL AH name";
       }
       leaf ahnames-hmac-sha2-256 {
         type uint64;
         description
           "HMAC SHA2-256";
       }
       leaf ahnames-hmac-sha2-384 {
         type uint64;
         description
           "HMAC SHA2-384";
       }
       leaf ahnames-hmac-sha2-512 {
         type uint64;
         description
           "HMAC SHA2-512";
       }
       leaf ahnames-hmac-ripemd160 {
         type uint64;
         description
           "HAMC RIPEMD160";
       }
       leaf ahnames-aes-xcbc-mac {
         type uint64;
         description
           "AES XCBC MAC";
       }
       leaf espnames-none {
         type uint64;
         description
           "ESP names";
       }
       leaf espnames-des-cbc {
         type uint64;
         description
           "DES CBC";
       }
       leaf espnames-null {
         type uint64;
         description
           "NULL ESP name";
       }
       leaf espnames-cast128-cbc {
         type uint64;
         description
           "CAST128 CBC";
       }
       leaf espnames-blowfish-cbc {
         type uint64;
         description
           "BLOWFISH CBC";
       }
       leaf espnames-rijndael-cbc {
         type uint64;
         description
           "RIJDAEL CBC";
       }
       leaf espnames-aes-ctr {
         type uint64;
         description
           "AES CTR";
       }
       leaf compnames-none {
         type uint64;
         description
           "NONE COMP names";
       }
       leaf compnames-oui {
         type uint64;
         description
           "OUI";
       }
       leaf compnames-deflate {
         type uint64;
         description
           "DEFLATE";
       }
       leaf compnames-lzs {
         type uint64;
         description
           "LZS";
       }
       leaf proto {
         type uint64;
       }
       leaf outbound-packets-processed-successfully {
         type uint64;
         description
           "Outbound packets processed successfully";
       }
       leaf outbound-packets-violated-process-security-policy {
         type uint64;
         description
           "Outbound packets violated process security policy";
       }
       leaf outbound-packets-with-no-sa-available {
         type uint64;
         description
           "Outbound packets with no SA available";
       }
       leaf invalid-outbound-packets {
         type uint64;
         description
           "Invalid outbound packets";
       }
       leaf outbound-packets-failed-due-to-insufficient-memory {
         type uint64;
         description
           "Outbound packets failed due to insufficient memory";
       }
       leaf outbound-packets-with-no-route {
         type uint64;
         description
           "Outbound packets with no route";
       }
       leaf spd-cache-lookups {
         type uint64;
         description
           "SPD cache lookups";
       }
       leaf spd-cache-misses {
         type uint64;
         description
           "SPD cache misses";
       }
       leaf outbound-packets-with-bundled-sa {
         type uint64;
         description
           "Outbound packets with bundles SAs";
       }
       leaf mbuf-coalesced-during-clone {
         type uint64;
         description
           "Mbuf coleasced during clone";
       }
       leaf cluster-coalesced-during-clone {
         type uint64;
         description
           "Cluster coalesced during clone";
       }
       leaf cluster-copied-during-clone {
         type uint64;
         description
           "Cluster copied during clone";
       }
       leaf mbuf-inserted-during-makespace {
         type uint64;
         description
           "Mbuf inserted during makespace";
       }
       leaf espnames-3des-cbc {
         type uint64;
         description
           "3DES CBC";
       }
     }
     container pfkey {
       leaf requests-sent-from-userland {
         type uint64;
         description
           "Requests sent from userland";
       }
       leaf bytes-sent-from-userland {
         type uint64;
         description
           "Bytes sent from userland";
       }
       leaf messages-with-invalid-length-field {
         type uint64;
         description
           "Messages with invalid length field";
       }
       leaf messages-with-invalid-version-field {
         type uint64;
         description
           "Messages with invalid version field";
       }
       leaf messages-with-invalid-message-type-field {
         type uint64;
         description
           "Messages with invalid message type field";
       }
       leaf messages-too-short {
         type uint64;
         description
           "Messages too short";
       }
       leaf outgoing-messages-with-memory-allocation-failure {
         type uint64;
         description
           "Outgoing messages with memory allocation failure";
       }
       leaf messages-with-duplicate-extension {
         type uint64;
         description
           "Messages with duplicate extension";
       }
       leaf messages-with-invalid-extension-type {
         type uint64;
         description
           "Messages with invalid extension type";
       }
       leaf messages-with-invalid-sa-type {
         type uint64;
         description
           "Messages with invalid SA type";
       }
       leaf messages-with-invalid-address-extension {
         type uint64;
         description
           "Messages with invalid address extension";
       }
       leaf requests-sent-to-userland {
         type uint64;
         description
           "Requests sent to userland";
       }
       leaf bytes-sent-to-userland {
         type uint64;
         description
           "Bytes sent to userland";
       }
       leaf messages-toward-single-socket {
         type uint64;
         description
           "Messages toward single socket";
       }
       leaf messages-toward-all-sockets {
         type uint64;
         description
           "Messages toward all sockets";
       }
       leaf messages-toward-registered-sockets {
         type uint64;
         description
           "Messages toward registered sockets";
       }
       leaf incoming-messages-with-memory-allocation-failure {
         type uint64;
         description
           "Incoming messages with memory allocation failure";
       }
       leaf reserved {
         type uint64;
         description
           "Reserved";
       }
       leaf getspi {
         type uint64;
         description
           "Getspi";
       }
       leaf update {
         type uint64;
         description
           "Update";
       }
       leaf add {
         type uint64;
         description
           "Add";
       }
       leaf delete {
         type uint64;
         description
           "Delete";
       }
       leaf get {
         type uint64;
         description
           "Get";
       }
       leaf acquire {
         type uint64;
         description
           "Acquire";
       }
       leaf register {
         type uint64;
         description
           "Register";
       }
       leaf expire {
         type uint64;
         description
           "Expire";
       }
       leaf flush {
         type uint64;
         description
           "Flush";
       }
       leaf dump {
         type uint64;
         description
           "Dump";
       }
       leaf x-promisc {
         type uint64;
         description
           "X_PROMISC";
       }
       leaf x-pchange {
         type uint64;
         description
           "X_PCHANGE";
       }
       leaf x-spdupdate {
         type uint64;
         description
           "X_SPDUPDATE";
       }
       leaf x-spdadd {
         type uint64;
         description
           "X_SPDADD";
       }
       leaf x-spddelete {
         type uint64;
         description
           "X_SPDDELETE";
       }
       leaf x-spdget {
         type uint64;
         description
           "X_SPDGET";
       }
       leaf x-spdacquire {
         type uint64;
         description
           "X_SPDACQUIRE";
       }
       leaf x-spddump {
         type uint64;
         description
           "X_SPDDUMP";
       }
       leaf x-spdflush {
         type uint64;
         description
           "X_SPDFLUSH";
       }
       leaf x-spdsetidx {
         type uint64;
         description
           "X_SPDSETIDX";
       }
       leaf x-spdexpire {
         type uint64;
         description
           "X_SPDEXPIRE";
       }
       leaf x-spddelete2 {
         type uint64;
         description
           "X_SPDDELETE2";
       }
       container output-histogram {
         leaf histogram-type {
           type string;
         }
         leaf unreachable-icmp6-packets {
           type uint64;
           description
             "Unreachable icmp6 packets";
         }
         leaf packet-too-big {
           type uint64;
           description
             "Packet too big";
         }
         leaf time-exceeded-icmp6-packets {
           type uint64;
           description
             "Time exceeded icmp6 packets";
         }
         leaf parameter-problem-icmp6-packets {
           type uint64;
           description
             "Parameter problem icmp6 packets";
         }
         leaf icmp6-echo {
           type uint64;
         }
         leaf icmp6-ext-echo {
           type uint64;
         }
         leaf icmp6-echo-reply {
           type uint64;
         }
         leaf icmp6-ext-echo-reply {
           type uint64;
         }
         leaf multicast-listener-query {
           type uint64;
           description
             "Multicast listener query";
         }
         leaf multicast-listener-report {
           type uint64;
           description
             "Multicast listener report";
         }
         leaf multicast-listener-done {
           type uint64;
           description
             "Multicast listener done";
         }
         leaf router-solicitation-icmp6-packets {
           type uint64;
           description
             "Router solicitation icmp6 packets";
         }
         leaf router-advertisement-icmp6-packets {
           type uint64;
           description
             "Router advertisement icmp6 packets";
         }
         leaf neighbor-solicitation {
           type uint64;
           description
             "Neighbor solicitation";
         }
         leaf neighbor-advertisement {
           type uint64;
           description
             "Neighbor advertisement";
         }
         leaf redirect {
           type uint64;
           description
             "Redirect";
         }
         leaf router-renumbering {
           type uint64;
           description
             "Router renumbering";
         }
         leaf node-information-request {
           type uint64;
           description
             "Node information request";
         }
         leaf node-information-reply {
           type uint64;
           description
             "Node information reply";
         }
         leaf version-2-multicast-listener-report {
           type uint64;
           description
             "Version 2 Multicast Listener Report";
         }
         leaf-list histogram {
           type string;
         }
         leaf reserved {
           type uint64;
           description
             "Reserved";
         }
         leaf getspi {
           type uint64;
           description
             "Getspi";
         }
         leaf update {
           type uint64;
           description
             "Update";
         }
         leaf add {
           type uint64;
           description
             "Add";
         }
         leaf delete {
           type uint64;
           description
             "Delete";
         }
         leaf get {
           type uint64;
           description
             "Get";
         }
         leaf acquire {
           type uint64;
           description
             "Acquire";
         }
         leaf register {
           type uint64;
           description
             "Register";
         }
         leaf expire {
           type uint64;
           description
             "Expire";
         }
         leaf flush {
           type uint64;
           description
             "Flush";
         }
         leaf dump {
           type uint64;
           description
             "Dump";
         }
         leaf x-promisc {
           type uint64;
           description
             "X_PROMISC";
         }
         leaf x-pchange {
           type uint64;
           description
             "X_PCHANGE";
         }
         leaf x-spdupdate {
           type uint64;
           description
             "X_SPDUPDATE";
         }
         leaf x-spdadd {
           type uint64;
           description
             "X_SPDADD";
         }
         leaf x-spddelete {
           type uint64;
           description
             "X_SPDDELETE";
         }
         leaf x-spdget {
           type uint64;
           description
             "X_SPDGET";
         }
         leaf x-spdacquire {
           type uint64;
           description
             "X_SPDACQUIRE";
         }
         leaf x-spddump {
           type uint64;
           description
             "X_SPDDUMP";
         }
         leaf x-spdflush {
           type uint64;
           description
             "X_SPDFLUSH";
         }
         leaf x-spdsetidx {
           type uint64;
           description
             "X_SPDSETIDX";
         }
         leaf x-spdexpire {
           type uint64;
           description
             "X_SPDEXPIRE";
         }
         leaf x-spddelete2 {
           type uint64;
           description
             "X_SPDDELETE2";
         }
       }
       container input-histogram {
         leaf histogram-type {
           type string;
         }
         leaf unreachable-icmp6-packets {
           type uint64;
           description
             "Unreachable icmp6 packets";
         }
         leaf packet-too-big {
           type uint64;
           description
             "Packet too big";
         }
         leaf time-exceeded-icmp6-packets {
           type uint64;
           description
             "Time exceeded icmp6 packets";
         }
         leaf parameter-problem-icmp6-packets {
           type uint64;
           description
             "Parameter problem icmp6 packets";
         }
         leaf icmp6-echo {
           type uint64;
         }
         leaf icmp6-ext-echo {
           type uint64;
         }
         leaf icmp6-echo-reply {
           type uint64;
         }
         leaf icmp6-ext-echo-reply {
           type uint64;
         }
         leaf multicast-listener-query {
           type uint64;
           description
             "Multicast listener query";
         }
         leaf multicast-listener-report {
           type uint64;
           description
             "Multicast listener report";
         }
         leaf multicast-listener-done {
           type uint64;
           description
             "Multicast listener done";
         }
         leaf router-solicitation-icmp6-packets {
           type uint64;
           description
             "Router solicitation icmp6 packets";
         }
         leaf router-advertisement-icmp6-packets {
           type uint64;
           description
             "Router advertisement icmp6 packets";
         }
         leaf neighbor-solicitation {
           type uint64;
           description
             "Neighbor solicitation";
         }
         leaf neighbor-advertisement {
           type uint64;
           description
             "Neighbor advertisement";
         }
         leaf redirect {
           type uint64;
           description
             "Redirect";
         }
         leaf router-renumbering {
           type uint64;
           description
             "Router renumbering";
         }
         leaf node-information-request {
           type uint64;
           description
             "Node information request";
         }
         leaf node-information-reply {
           type uint64;
           description
             "Node information reply";
         }
         leaf version-2-multicast-listener-report {
           type uint64;
           description
             "Version 2 Multicast Listener Report";
         }
         leaf-list histogram {
           type string;
         }
         leaf reserved {
           type uint64;
           description
             "Reserved";
         }
         leaf getspi {
           type uint64;
           description
             "Getspi";
         }
         leaf update {
           type uint64;
           description
             "Update";
         }
         leaf add {
           type uint64;
           description
             "Add";
         }
         leaf delete {
           type uint64;
           description
             "Delete";
         }
         leaf get {
           type uint64;
           description
             "Get";
         }
         leaf acquire {
           type uint64;
           description
             "Acquire";
         }
         leaf register {
           type uint64;
           description
             "Register";
         }
         leaf expire {
           type uint64;
           description
             "Expire";
         }
         leaf flush {
           type uint64;
           description
             "Flush";
         }
         leaf dump {
           type uint64;
           description
             "Dump";
         }
         leaf x-promisc {
           type uint64;
           description
             "X_PROMISC";
         }
         leaf x-pchange {
           type uint64;
           description
             "X_PCHANGE";
         }
         leaf x-spdupdate {
           type uint64;
           description
             "X_SPDUPDATE";
         }
         leaf x-spdadd {
           type uint64;
           description
             "X_SPDADD";
         }
         leaf x-spddelete {
           type uint64;
           description
             "X_SPDDELETE";
         }
         leaf x-spdget {
           type uint64;
           description
             "X_SPDGET";
         }
         leaf x-spdacquire {
           type uint64;
           description
             "X_SPDACQUIRE";
         }
         leaf x-spddump {
           type uint64;
           description
             "X_SPDDUMP";
         }
         leaf x-spdflush {
           type uint64;
           description
             "X_SPDFLUSH";
         }
         leaf x-spdsetidx {
           type uint64;
           description
             "X_SPDSETIDX";
         }
         leaf x-spdexpire {
           type uint64;
           description
             "X_SPDEXPIRE";
         }
         leaf x-spddelete2 {
           type uint64;
           description
             "X_SPDDELETE2";
         }
       }
     }
     container netisr {
       leaf total-drops {
         type uint32;
         description
           "Total packets dropped at netisr";
       }
       leaf queue-level-drops {
         type string;
         description
           "Netisr queue level drops";
       }
       leaf pri-level-drops {
         type string;
         description
           "Netisr priority level drops";
       }
       leaf netisr-pri-stats {
         type string;
         description
           "Netisr priority level statistics";
       }
       leaf netisr-socket-drops {
         type uint32;
         description
           "Netisr socket drops";
       }
       leaf netisr-udp-socket-drops {
         type uint32;
         description
           "Netisr udp socket drops";
       }
     }
     container clnl {
       leaf total-clnl-packets-received {
         type uint32;
         description
           "Total clnl packets received";
       }
       leaf packets-delivered {
         type uint32;
         description
           "Packets delivered";
       }
       leaf too-small-packets {
         type uint32;
         description
           "Too small packets";
       }
       leaf packets-with-bad-header-length {
         type uint32;
         description
           "Packets with bad header length";
       }
       leaf packets-with-bad-checksum {
         type uint32;
         description
           "Packets with bad checksum";
       }
       leaf bad-version-packets {
         type uint32;
         description
           "Bad version packets";
       }
       leaf unknown-or-unsupported-protocol-packets {
         type uint32;
         description
           "Unknown or unsupported protocol packets";
       }
       leaf packets-with-bogus-sdl-size {
         type uint32;
         description
           "Packets with bogus sdl size";
       }
       leaf no-free-memory-in-socket-buffer {
         type uint32;
         description
           "No free memory in socket buffer";
       }
       leaf send-packets-discarded {
         type uint32;
         description
           "Send packets discarded";
       }
       leaf sbappend-failure {
         type uint32;
         description
           "Sbappend failure";
       }
       leaf mcopy-failure {
         type uint32;
         description
           "Mcopy failure";
       }
       leaf address-fields-were-not-reasonable {
         type uint32;
         description
           "Address fields were not reasonable";
       }
       leaf segment-information-forgotten {
         type uint32;
         description
           "Segment information forgotten";
       }
       leaf forwarded-packets {
         type uint32;
         description
           "Forwarded packets";
       }
       leaf total-packets-sent {
         type uint32;
         description
           "Total packets sent";
       }
       leaf output-packets-discarded {
         type uint32;
         description
           "Output packets discarded";
       }
       leaf non-forwarded-packets {
         type uint32;
         description
           "Non-forwarded packets";
       }
       leaf packets-fragmented {
         type uint32;
         description
           "Packets fragmented";
       }
       leaf fragments-sent {
         type uint32;
         description
           "Fragments sent";
       }
       leaf fragments-discarded {
         type uint32;
         description
           "Fragments discarded";
       }
       leaf fragments-timed-out {
         type uint32;
         description
           "Fragments timed out";
       }
       leaf fragmentation-prohibited {
         type uint32;
         description
           "Fragmentation prohibited";
       }
       leaf packets-reconstructed {
         type uint32;
         description
           "Packets reconstructed";
       }
       leaf packets-destined-to-dead-nexthop {
         type uint32;
         description
           "Packets destined to dead nexthop";
       }
       leaf packets-discarded-due-to-no-route {
         type uint32;
         description
           "Packets discarded due to no route";
       }
       leaf error-pdu-rate-drops {
         type uint32;
         description
           "Error pdu rate drops";
       }
       leaf er-pdu-generation-failure {
         type uint32;
         description
           "ER pdu generation failure";
       }
     }
     container esis {
       leaf total-esis-packets-received {
         type uint32;
         description
           "Total esis packets received";
       }
       leaf total-packets-consumed-by-protocol {
         type uint32;
         description
           "Total packets consumed by protocol";
       }
       leaf pdus-received-with-bad-checksum {
         type uint32;
         description
           "PDUs received with bad checksum";
       }
       leaf pdus-received-with-bad-version-number {
         type uint32;
         description
           "PDUs received with bad version number";
       }
       leaf pdus-received-with-bad-type-field {
         type uint32;
         description
           "PDUs received with bad type field";
       }
       leaf short-pdus-received {
         type uint32;
         description
           "Short pdus received";
       }
       leaf pdus-with-bogus-sdl-size {
         type uint32;
         description
           "Pdus with bogus sdl size";
       }
       leaf pdus-with-bad-header-length {
         type uint32;
         description
           "Pdus with bad header length";
       }
       leaf pdus-with-unknown-or-unsupport-protocol {
         type uint32;
         description
           "Pdus with unknown or unsupported protocol";
       }
       leaf no-free-memory-in-socket-buffer {
         type uint32;
         description
           "No free memory in socket buffer";
       }
       leaf send-packets-discarded {
         type uint32;
         description
           "Send packets discarded";
       }
       leaf sbappend-failure {
         type uint32;
         description
           "Sbappend failure";
       }
       leaf mcopy-failure {
         type uint32;
         description
           "Mcopy failure";
       }
       leaf iso-family-not-configured {
         type uint32;
         description
           "ISO family not configured";
       }
     }
     container tnp {
       leaf unicast-packets-received {
         type uint64;
         description
           "Unicast packets received";
       }
       leaf broadcast-packets-received {
         type uint64;
         description
           "Broadcast packets received";
       }
       leaf fragmented-packets-received {
         type uint64;
         description
           "Fragmented packets received";
       }
       leaf received-hello-packets-dropped {
         type uint64;
         description
           "Hello packets dropped";
       }
       leaf received-fragments-dropped {
         type uint64;
         description
           "Fragments dropped";
       }
       leaf fragment-reassembly-queue-flushes {
         type uint64;
         description
           "Fragment reassembly queue flushes";
       }
       leaf packets-with-tnp-src-address-collision-received {
         type uint64;
         description
           "Packets with tnp src address collision received";
       }
       leaf hello-packets-received {
         type uint64;
         description
           "Hello packets received";
       }
       leaf control-packets-received {
         type uint64;
         description
           "Control packets received";
       }
       leaf rdp-packets-received {
         type uint64;
         description
           "RDP packets received";
       }
       leaf udp-packets-received {
         type uint64;
         description
           "UDP packets received";
       }
       leaf tunnel-packets-received {
         type uint64;
         description
           "Tunnel packets received";
       }
       leaf input-packets-discarded-with-no-protocol {
         type uint64;
         description
           "Input packets discarded with no protocol";
       }
       leaf packets-of-version-unspecified-received {
         type uint64;
         description
           "Packets of version unspecified received";
       }
       leaf packets-of-version1-received {
         type uint64;
         description
           "Packets of version 1 received";
       }
       leaf packets-of-version2-received {
         type uint64;
         description
           "Packets of version 2 received";
       }
       leaf packets-of-version3-received {
         type uint64;
         description
           "Packets of version 3 received";
       }
       leaf unicast-packets-sent {
         type uint64;
         description
           "Unicast packets sent";
       }
       leaf broadcast-packets-sent {
         type uint64;
         description
           "Broadcast packets sent";
       }
       leaf fragmented-packets-sent {
         type uint64;
         description
           "Fragmented packets sent";
       }
       leaf sent-hello-packets-dropped {
         type uint64;
         description
           "Hello packets dropped";
       }
       leaf sent-fragments-dropped {
         type uint64;
         description
           "Fragments dropped";
       }
       leaf hello-packets-sent {
         type uint64;
         description
           "Hello packets sent";
       }
       leaf control-packets-sent {
         type uint64;
         description
           "Control packets sent";
       }
       leaf rdp-packets-sent {
         type uint64;
         description
           "Rdp packets sent";
       }
       leaf udp-packets-sent {
         type uint64;
         description
           "Udp packets sent";
       }
       leaf tunnel-packets-sent {
         type uint64;
         description
           "Tunnel packets sent";
       }
       leaf packets-sent-with-unknown-protocol {
         type uint64;
         description
           "Packets sent with unknown protocol";
       }
       leaf packets-of-version-unspecified-sent {
         type uint64;
         description
           "Packets of version unspecified sent";
       }
       leaf packets-of-version1-sent {
         type uint64;
         description
           "Packets of version 1 sent";
       }
       leaf packets-of-version2-sent {
         type uint64;
         description
           "Packets of version 2 sent";
       }
       leaf packets-of-version3-sent {
         type uint64;
         description
           "Packets of version 3 sent";
       }
     }
     container rdp {
       leaf input-packets {
         type uint64;
         description
           "Input packets";
       }
       leaf packets-discarded-for-bad-checksum {
         type uint64;
         description
           "Packets discarded for bad checksum";
       }
       leaf packets-discarded-due-to-bad-sequence-number {
         type uint64;
         description
           "Packets discarded due to bad sequence number";
       }
       leaf refused-connections {
         type uint64;
         description
           "Refused connections";
       }
       leaf acks-received {
         type uint64;
         description
           "Acks received";
       }
       leaf packets-dropped-due-to-full-socket-buffers {
         type uint64;
         description
           "Packets dropped due to full socket buffers";
       }
       leaf retransmits {
         type uint64;
         description
           "Retransmits";
       }
       leaf output-packets {
         type uint64;
         description
           "Output packets";
       }
       leaf acks-sent {
         type uint64;
         description
           "Acks sent";
       }
       leaf connects {
         type uint64;
         description
           "Connects";
       }
       leaf closes {
         type uint64;
         description
           "Closes";
       }
       leaf keepalives-received {
         type uint64;
         description
           "Keepalives received";
       }
       leaf keepalives-sent {
         type uint64;
         description
           "Keepalives sent";
       }
       leaf packets-dropped-full-repl-sock-buf {
         type uint64;
         description
           "Packets dropped due to full replicated socket buffer";
       }
     }
     container tudp {
       leaf datagrams-received {
         type uint32;
         description
           "Datagrams received";
       }
       leaf datagrams-with-incomplete-header {
         type uint32;
         description
           "Datagrams with incomplete header";
       }
       leaf datagrams-with-bad-data-length-field {
         type uint32;
         description
           "Datagrams with bad data length field";
       }
       leaf datagrams-with-bad-checksum {
         type uint32;
         description
           "Datagrams with bad checksum";
       }
       leaf datagrams-dropped-due-to-no-socket {
         type uint32;
         description
           "Datagrams dropped due to no socket";
       }
       leaf broadcast-or-multicast-datagrams-dropped-due-to-no-socket {
         type uint32;
         description
           "Broadcast/multicast datagrams dropped due to no socket";
       }
       leaf datagrams-dropped-due-to-full-socket-buffers {
         type uint32;
         description
           "Datagrams dropped due to full socket buffers";
       }
       leaf delivered {
         type uint32;
         description
           "Delivered";
       }
       leaf datagrams-output {
         type uint32;
         description
           "Datagrams output";
       }
     }
     container ttp {
       leaf ttp-packets-sent {
         type uint64;
         description
           "Ttp packets sent";
       }
       leaf packets-sent-while-unconnected {
         type uint64;
         description
           "Packets sent while unconnected";
       }
       leaf packets-sent-while-interface-down {
         type uint64;
         description
           "Packets sent while interface down";
       }
       leaf packets-sent-could-not-get-buffer {
         type uint64;
         description
           "Packets sent couldn't get buffer";
       }
       leaf packets-sent-could-not-find-neighbor {
         type uint64;
         description
           "Packets sent could't find neighbor";
       }
       leaf packets-sent-when-transmit-disabled {
         type uint64;
         description
           "Packets sent when transmit is disabled";
       }
       leaf packets-sent-when-host-unreachable {
         type uint64;
         description
           "Packets sent when host unreachable";
       }
       leaf l3-packets-sent-could-not-get-buffer {
         type uint64;
         description
           "L3 Packets sent couldn't get buffer";
       }
       leaf l3-packets-dropped {
         type uint64;
         description
           "L3 Packets dropped";
       }
       leaf packets-sent-with-bad-ifl {
         type uint64;
         description
           "Packets sent with bad logical interface";
       }
       leaf packets-sent-with-bad-af {
         type uint64;
         description
           "Packets sent with bad address family";
       }
       leaf l2-packets-received {
         type uint64;
         description
           "L2 packets received";
       }
       leaf unknown-l3-packets-received {
         type uint64;
         description
           "Unknown L3 packets received";
       }
       leaf ipv4-l3-packets-received {
         type uint64;
         description
           "IPv4 L3 packets received";
       }
       leaf mpls-l3-packets-received {
         type uint64;
         description
           "MPLS L3 packets received";
       }
       leaf mpls-to-ipv4-l3-packets-received {
         type uint64;
         description
           "MPLS->IPV4 L3 packets received";
       }
       leaf ipv4-to-mpls-l3-packets-received {
         type uint64;
         description
           "IPv4->MPLS L3 packets received";
       }
       leaf vpls-l3-packets-received {
         type uint64;
         description
           "VPLS L3 packets received";
       }
       leaf ipv6-l3-packets-received {
         type uint64;
         description
           "IPv6 L3 packets received";
       }
       leaf arp-l3-packets-received {
         type uint64;
         description
           "ARP L3 packets received";
       }
       leaf clnp-l3-packets-received {
         type uint64;
         description
           "CLNP L3 packets received";
       }
       leaf tnp-l3-packets-received {
         type uint64;
         description
           "TNP L3 packets received";
       }
       leaf null-l3-packets-received {
         type uint64;
         description
           "NULL L3 packets received";
       }
       leaf cyclotron-cycle-l3-packets-received {
         type uint64;
         description
           "Cyclotron cycle L3 packets received";
       }
       leaf cyclotron-send-l3-packets-received {
         type uint64;
         description
           "Cyclotron send L3 packets received";
       }
       leaf openflow-packets-received {
         type uint64;
         description
           "Openflow packets received";
       }
       leaf packets-received-while-unconnected {
         type uint64;
         description
           "Packets received while unconnected";
       }
       leaf packets-received-from-unknown-ifl {
         type uint64;
         description
           "Packets received from unknown ifl";
       }
       leaf input-packets-could-not-get-buffer {
         type uint64;
         description
           "Input packets couldn't get buffer";
       }
       leaf input-packets-with-bad-type {
         type uint64;
         description
           "Input packets with bad type";
       }
       leaf input-packets-with-discard-type {
         type uint64;
         description
           "Input packets with discard type";
       }
       leaf input-packets-with-too-many-tlvs {
         type uint64;
         description
           "Input packets with too many tlvs";
       }
       leaf input-packets-with-bad-tlv-header {
         type uint64;
         description
           "Input packets with tlv header error";
       }
       leaf input-packets-with-bad-tlv-type {
         type uint64;
         description
           "Input packets with bad tlv type";
       }
       leaf input-packets-tlv-dropped {
         type uint64;
         description
           "Input packets dropped based on tlv result";
       }
       leaf input-packets-with-bad-af {
         type uint64;
         description
           "Input packets with bad address family";
       }
       leaf input-packets-for-which-route-lookup-is-bypassed {
         type uint64;
         description
           "Input packets for which route lookup is bypassed";
       }
       leaf input-packets-with-ttp-tlv-p2mp-nbr-nhid-type {
         type uint64;
         description
           "Input packets with ttp tlv of type TTP_TLV_P2MP_NBR_NHID";
       }
       leaf input-packets-with-unknown-p2mp-nbr-nhid {
         type uint64;
         description
           "Input packets with unknown p2mp_nbr_nhid value";
       }
       leaf input-packets-with-vxlan-bfd-pkts {
         type uint64;
         description
           "Input packets of type vxlan bfd";
       }
     }
     container mpls {
       leaf total-mpls-packets-received {
         type uint32;
         description
           "Total MPLS packets received";
       }
       leaf packets-forwarded {
         type uint32;
         description
           "Packets forwarded";
       }
       leaf packets-dropped {
         type uint32;
         description
           "Packets dropped (src and int don't match)";
       }
       leaf packets-with-header-too-small {
         type uint32;
         description
           "Packets with header too small";
       }
       leaf after-tagging-packets-can-not-fit-link-mtu {
         type uint32;
         description
           "After tagging, packets can't fit link MTU";
       }
       leaf packets-with-ipv4-explicit-null-tag {
         type uint32;
         description
           "Packets with IPv4 explicit NULL tag";
       }
       leaf packets-with-ipv4-explicit-null-checksum-errors {
         type uint32;
         description
           "Packets with IPv4 explicit NULL cksum errors";
       }
       leaf packets-with-router-alert-tag {
         type uint32;
         description
           "Packets with router alert tag";
       }
       leaf packets-with-ipv6-explicit-null-tag {
         type uint32;
         description
           "Packets with IPv6 explicit NULL tag";
       }
       leaf lsp-ping-packets {
         type uint32;
         description
           "LSP ping packets (ttl-expired/router alert)";
       }
       leaf packets-with-ttl-expired {
         type uint32;
         description
           "Packets with ttl expired";
       }
       leaf packets-with-tag-encoding-error {
         type uint32;
         description
           "Packets with tag encoding error";
       }
       leaf packets-discarded-due-to-no-route {
         type uint32;
         description
           "Packets discarded due to no route";
       }
       leaf packets-used-first-nexthop-in-ecmp-unilist {
         type uint32;
         description
           "Packets used first nexthop in ecmp unilist";
       }
       leaf packets-dropped-due-to-ifl-down {
         type uint32;
         description
           "Packets dropped due to ifl down";
       }
       leaf packets-dropped-at-mpls-socket-send {
         type uint32;
         description
           "Packets dropped at mpls socket send op";
       }
       leaf packets-forwarded-at-mpls-socket-send {
         type uint32;
         description
           "Packets forwarded at mpls socket send op";
       }
       leaf mpls-bfd-packets-received {
         type uint32;
         description
           "Mpls bfd packets received";
       }
       leaf mpls-cfm-packets-received {
         type uint32;
         description
           "Mpls cfm packets received";
       }
       leaf packets-dropped-at-p2mp-cnh-output {
         type uint32;
         description
           "Packets dropped, over p2mp composite nexthop";
       }
     }
     container vpls {
       leaf total-packets-received {
         type uint64;
         description
           "Total packets received";
       }
       leaf vpls-packets-with-size-smaller-than-minimum {
         type uint64;
         description
           "Vpls packets with size smaller than minimum";
       }
       leaf vpls-packets-with-incorrect-version-number {
         type uint64;
         description
           "Vpls packets with incorrect version number";
       }
       leaf vpls-packets-for-this-host {
         type uint64;
         description
           "Vpls packets for this host";
       }
       leaf packets-with-no-logical-interface {
         type uint64;
         description
           "Packets with no logical interface";
       }
       leaf packets-with-no-family {
         type uint64;
         description
           "Packets with no family";
       }
       leaf packets-with-no-route-table {
         type uint64;
         description
           "Packets with no route table";
       }
       leaf packets-with-no-auxiliary-table {
         type uint64;
         description
           "Packets with no auxiliary table";
       }
       leaf packets-with-no-corefacing-entry {
         type uint64;
         description
           "Packets with no core-facing entry";
       }
       leaf packets-with-no-ce-facing-entry {
         type uint64;
         description
           "Packets with no CE-facing entry";
       }
       leaf mac-route-learning-requests {
         type uint64;
         description
           "MAC route learning requests";
       }
       leaf mac-routes-learned {
         type uint64;
         description
           "MAC routes learnt";
       }
       leaf requests-to-learn-an-existing-route {
         type uint64;
         description
           "Requests to learn an existing route";
       }
       leaf learning-requests-while-learning-disabled-on-interface {
         type uint64;
         description
           "Learning requests while learning disabled on interface";
       }
       leaf learning-requests-over-capacity {
         type uint64;
         description
           "Learning requests over capacity";
       }
       leaf mac-routes-moved {
         type uint64;
         description
           "MAC routes moved";
       }
       leaf requests-to-move-static-route {
         type uint64;
         description
           "Requests to move static route";
       }
       leaf mac-route-aging-requests {
         type uint64;
         description
           "MAC route aging requests";
       }
       leaf mac-routes-aged {
         type uint64;
         description
           "MAC routes aged";
       }
       leaf bogus-address-in-aging-requests {
         type uint64;
         description
           "Bogus address in aging requests";
       }
       leaf requests-to-age-static-route {
         type uint64;
         description
           "Requests to age static route";
       }
       leaf requests-to-re-ageout-aged-route {
         type uint64;
         description
           "Requests to re-ageout aged route";
       }
       leaf requests-involving-multiple-peer-fes {
         type uint64;
         description
           "Requests involving multiple peer FEs";
       }
       leaf aging-acks-from-pfe {
         type uint64;
         description
           "Aging acks from PFE";
       }
       leaf aging-non-acks-from-pfe {
         type uint64;
         description
           "Aging non-acks from PFE";
       }
       leaf aging-requests-timed-out-waiting-on-fes {
         type uint64;
         description
           "Aging requests timed out waiting on FEs";
       }
       leaf aging-requests-over-max-rate {
         type uint64;
         description
           "Aging requests over max-rate";
       }
       leaf errors-finding-peer-fes {
         type uint64;
         description
           "Errors finding peer FEs";
       }
       leaf unsupported-platform {
         type uint64;
         description
           "Unsupported platform";
       }
       leaf packets-dropped-due-to-no-l3-route-table {
         type uint64;
         description
           "Packets dropped due to no l3 route table";
       }
       leaf packets-dropped-due-to-no-local-ifl {
         type uint64;
         description
           "Packets dropped due to no local ifl";
       }
       leaf packets-punted {
         type uint64;
         description
           "Packets punted";
       }
       leaf packets-dropped-due-to-no-socket {
         type uint64;
         description
           "Packets dropped due to no socket";
       }
       leaf pim-packets-received {
         type uint64;
         description
           "PIM Packets received";
       }
       leaf igmp-packets-received {
         type uint64;
         description
           "IGMP Packets received";
       }
       leaf mld-packets-received {
         type uint64;
         description
           "MLD Packets received";
       }
       leaf packets-received {
         type uint64;
         description
           "Total packets received";
       }
       leaf packets-with-size-smaller-than-minimum {
         type uint64;
         description
           "Packets with size smaller than minimum";
       }
       leaf packets-with-incorrect-version-number {
         type uint64;
         description
           "Packets with incorrect version number";
       }
       leaf packets-for-this-host {
         type uint64;
         description
           "Packets for this host";
       }
       leaf packets-with-no-core-facing-entry {
         type uint64;
         description
           "Packets with no corefacing entry";
       }
     }
     container bridge {
       leaf heading {
         type string;
         description
           "Header";
       }
       leaf bridge-packets-received {
         type uint64;
         description
           "Bridge packets received";
       }
       leaf bridge-packets-forwarded {
         type uint64;
         description
           "Bridge packets forwarded";
       }
       leaf packets-failed-to-forward {
         type uint64;
         description
           "Packets failed to forward";
       }
       leaf bridge-packets-dropped {
         type uint64;
         description
           "Bridge packets dropped";
       }
       leaf packets-with-vmember-lookup-failures {
         type uint64;
         description
           "Packets with vmember lookup failures";
       }
       leaf packets-with-vlan-lookup-failures {
         type uint64;
         description
           "Packets with VLAN lookup failures";
       }
       leaf packets-with-stp-state-lookup-failures {
         type uint64;
         description
           "Packets with STP state lookup failures";
       }
       leaf packets-dropped-due-to-stp-blocked-or-listening {
         type uint64;
         description
           "Packets dropped due to STP blocked/listening";
       }
       leaf packets-dropped-due-to-stp-learning {
         type uint64;
         description
           "Packets dropped due to STP learning";
       }
       leaf packets-with-src-mac-learning-failures {
         type uint64;
         description
           "Packets with src MAC learning failures";
       }
       leaf packets-with-input-control-processing-failures {
         type uint64;
         description
           "Packets with input control processing failures";
       }
       leaf packets-sent-successfully {
         type uint64;
         description
           "Packets sent successfully";
       }
       leaf packets-with-send-failures {
         type uint64;
         description
           "Packets with send failures";
       }
       leaf packets-forwarded-to-l3-interface {
         type uint64;
         description
           "Packets forwarded to l3 interface";
       }
       leaf packets-with-l3-send-failures {
         type uint64;
         description
           "Packets with l3 send failures";
       }
       leaf packets-discarded {
         type uint64;
         description
           "Packets discarded";
       }
       leaf packets-with-l2-ifl-store-failures {
         type uint64;
         description
           "Packets with l2ifl store failures";
       }
       leaf packets-with-ifl-mismatch-failures {
         type uint64;
         description
           "Packets with ifl mismatch failures";
       }
       leaf packets-with-packet-duplication-failures {
         type uint64;
         description
           "Packets with packet duplication failures";
       }
       leaf packets-with-tag-lookup-failures {
         type uint64;
         description
           "Packets with tag lookup failures";
       }
       leaf packets-with-no-route-for-dmac {
         type uint64;
         description
           "Packets with no route for DMAC";
       }
       leaf packets-with-no-route-table {
         type uint64;
         description
           "Packets with no route table";
       }
       leaf packets-with-no-nexthop {
         type uint64;
         description
           "Packets with no nexthop";
       }
       leaf packets-with-dead-nexthop {
         type uint64;
         description
           "Packets with dead nexthop";
       }
       leaf packets-with-eof-reached-error {
         type uint64;
         description
           "Packets with eof reached error";
       }
       leaf macs-learned {
         type uint64;
         description
           "MACs learned";
       }
       leaf packets-sent-to-l3-interface {
         type uint64;
         description
           "Packets sent to l3 interface";
       }
       leaf packets-hit-hold-queue-while-learning {
         type uint64;
         description
           "Packets hit hold queue while learning";
       }
       leaf mac-moves {
         type uint64;
         description
           "MAC moves";
       }
       leaf packets-with-no-route-for-smac {
         type uint64;
         description
           "Packets with no route for SMAC";
       }
       leaf packets-dropped-due-to-no-resolve-route {
         type uint64;
         description
           "Packets dropped due to no resolve route";
       }
       leaf packets-with-l3-ifd-lookup-failures {
         type uint64;
         description
           "Packets with l3 ifd lookup failures";
       }
       leaf packets-with-l3-ifl-lookup-failures {
         type uint64;
         description
           "Packets with l3 ifl lookup failures";
       }
       leaf packets-with-l3-invalid-rnh {
         type uint64;
         description
           "Packets with l3 invalid RNH";
       }
       leaf packets-with-no-route-for-smac-in-clone-learning {
         type uint64;
         description
           "Packets with no route for SMAC in clone learning";
       }
       leaf packets-with-no-nexthop-in-clone-learning {
         type uint64;
         description
           "Packets with no nexhop in clone learning";
       }
       leaf packets-with-dead-nexthop-in-clone-learning {
         type uint64;
         description
           "Packets with dead nexthop in clone learning";
       }
       leaf packets-dropped-due-to-no-resolve-nh-in-clone-learning {
         type uint64;
         description
           "Packets dropped due to no resolve nh in clone learning";
       }
       leaf packets-dropped-due-to-interface-down {
         type uint64;
         description
           "Packets dropped due to interface down";
       }
       leaf packets-with-dev-output-failures {
         type uint64;
         description
           "Packets with dev output failures";
       }
       leaf blocked-ifl-discards {
         type uint64;
         description
           "Blocked ifl discards";
       }
       leaf packets-with-tag-insertion-failures {
         type uint64;
         description
           "Packets with tag insertion failures";
       }
       leaf packets-with-tag-removal-failures {
         type uint64;
         description
           "Packets with tag removal failures";
       }
       leaf packets-flooded {
         type uint64;
         description
           "Packets flooded";
       }
       leaf flood-failures {
         type uint64;
         description
           "Flood failures";
       }
       leaf packets-with-mpull-failures {
         type uint64;
         description
           "Packets with mpull failures";
       }
       leaf packets-with-ifl-lookup-failures {
         type uint64;
         description
           "Packets with ifl lookup failures";
       }
       leaf bridge-packets-with-size-smaller-than-minimum {
         type uint64;
         description
           "Bridge packets with size smaller than minimum";
       }
       leaf packets-with-double-tags {
         type uint64;
         description
           "Packets with double tags";
       }
       leaf packets-with-no-ifl {
         type uint64;
       }
       leaf packets-with-no-family {
         type uint64;
         description
           "Packets with no family";
       }
       leaf packets-with-receive-failures {
         type uint64;
         description
           "Packets with receive failures";
       }
       leaf packets-received {
         type uint64;
         description
           "Total packets received";
       }
       leaf packets-with-size-smaller-than-minimum {
         type uint64;
         description
           "Packets with size smaller than minimum";
       }
       leaf packets-with-incorrect-version-number {
         type uint64;
         description
           "Packets with incorrect version number";
       }
       leaf packets-for-this-host {
         type uint64;
         description
           "Packets for this host";
       }
       leaf packets-with-no-logical-interface {
         type uint64;
         description
           "Packets with no logical interface";
       }
       leaf packets-with-no-auxiliary-table {
         type uint64;
         description
           "Packets with no auxiliary table";
       }
       leaf packets-with-no-core-facing-entry {
         type uint64;
         description
           "Packets with no corefacing entry";
       }
       leaf packets-with-no-ce-facing-entry {
         type uint64;
         description
           "Packets with no CE-facing entry";
       }
       leaf mac-route-learning-requests {
         type uint64;
         description
           "MAC route learning requests";
       }
       leaf mac-routes-learned {
         type uint64;
         description
           "MAC routes learnt";
       }
       leaf requests-to-learn-an-existing-route {
         type uint64;
         description
           "Requests to learn an existing route";
       }
       leaf learning-requests-while-learning-disabled-on-interface {
         type uint64;
         description
           "Learning requests while learning disabled on interface";
       }
       leaf learning-requests-over-capacity {
         type uint64;
         description
           "Learning requests over capacity";
       }
       leaf mac-routes-moved {
         type uint64;
         description
           "MAC routes moved";
       }
       leaf requests-to-move-static-route {
         type uint64;
         description
           "Requests to move static route";
       }
       leaf mac-route-aging-requests {
         type uint64;
         description
           "MAC route aging requests";
       }
       leaf mac-routes-aged {
         type uint64;
         description
           "MAC routes aged";
       }
       leaf bogus-address-in-aging-requests {
         type uint64;
         description
           "Bogus address in aging requests";
       }
       leaf requests-to-age-static-route {
         type uint64;
         description
           "Requests to age static route";
       }
       leaf requests-to-re-ageout-aged-route {
         type uint64;
         description
           "Requests to re-ageout aged route";
       }
       leaf requests-involving-multiple-peer-fes {
         type uint64;
         description
           "Requests involving multiple peer FEs";
       }
       leaf aging-acks-from-pfe {
         type uint64;
         description
           "Aging acks from PFE";
       }
       leaf aging-non-acks-from-pfe {
         type uint64;
         description
           "Aging non-acks from PFE";
       }
       leaf aging-requests-timed-out-waiting-on-fes {
         type uint64;
         description
           "Aging requests timed out waiting on FEs";
       }
       leaf aging-requests-over-max-rate {
         type uint64;
         description
           "Aging requests over max-rate";
       }
       leaf errors-finding-peer-fes {
         type uint64;
         description
           "Errors finding peer FEs";
       }
       leaf unsupported-platform {
         type uint64;
         description
           "Unsupported platform";
       }
       leaf packets-dropped-due-to-no-l3-route-table {
         type uint64;
         description
           "Packets dropped due to no l3 route table";
       }
       leaf packets-dropped-due-to-no-local-ifl {
         type uint64;
         description
           "Packets dropped due to no local ifl";
       }
       leaf packets-punted {
         type uint64;
         description
           "Packets punted";
       }
       leaf packets-dropped-due-to-no-socket {
         type uint64;
         description
           "Packets dropped due to no socket";
       }
       leaf pim-packets-received {
         type uint64;
         description
           "PIM Packets received";
       }
       leaf igmp-packets-received {
         type uint64;
         description
           "IGMP Packets received";
       }
       leaf mld-packets-received {
         type uint64;
         description
           "MLD Packets received";
       }
     }
     container ethoamcfm {
       leaf total-packets-received {
         type uint64;
         description
           "Total packets received";
       }
       leaf input-packets-drop-bad-interface-state {
         type uint32;
         description
           "Input packets drop due to bad interface state";
       }
       leaf received-packets-forwarded {
         type uint32;
         description
           "Received packets forwarded";
       }
       leaf total-packets-transmitted {
         type uint32;
         description
           "Total transmitted packets";
       }
       leaf packets-sent {
         type uint32;
         description
           "Packets sent";
       }
       leaf output-packets-drop-bad-interface-state {
         type uint32;
         description
           "Output packets drop due to bad interface state";
       }
       leaf flood-requests-forwarded-to-pfe {
         type uint32;
         description
           "Flood requests forwarded to PFE";
       }
       leaf flood-requests-dropped {
         type uint32;
         description
           "Flood requests dropped";
       }
     }
     container ethoamlfm {
       leaf total-packets-received {
         type uint64;
         description
           "Total packets received";
       }
       leaf input-packets-drop-bad-interface-state {
         type uint32;
         description
           "Input packets drop due to bad interface state";
       }
       leaf received-packets-forwarded {
         type uint32;
         description
           "Received packets forwarded";
       }
       leaf total-packets-transmitted {
         type uint32;
         description
           "Total transmitted packets";
       }
       leaf packets-sent {
         type uint32;
         description
           "Packets sent";
       }
       leaf output-packets-drop-bad-interface-state {
         type uint32;
         description
           "Output packets drop due to bad interface state";
       }
     }
     container jsr {
       leaf handle-info {
         type string;
       }
       leaf handles-in-use {
         type uint32;
         description
           "Handles in use";
       }
       leaf handles-allocated-so-far {
         type uint32;
         description
           "Handles allocated so far";
       }
       leaf handles-freed-so-far {
         type uint32;
         description
           "Handles freed so far";
       }
       leaf handles-in-delayed-free-state {
         type uint32;
         description
           "Handles in delayed free state";
       }
       leaf iha {
         type string;
       }
       leaf iha-invalid-subtype-messages {
         type uint32;
         description
           "Invalid subtype messages";
       }
       leaf iha-invalid-length-messages {
         type uint32;
         description
           "Invalid length messages";
       }
       leaf iha-invalid-version-messages {
         type uint32;
         description
           "Invalid version messages";
       }
       leaf iha-too-short-messages {
         type uint32;
         description
           "IHA too short messages";
       }
       leaf iha-invalid-dst-handle-messages {
         type uint32;
         description
           "IHA invalid dst handle messages";
       }
       leaf iha-invalid-src-handle-messages {
         type uint32;
         description
           "IHA invalid src handle messages";
       }
       leaf iha-unmatched-src-handle-messages {
         type uint32;
         description
           "IHA unmatched src handle messages";
       }
       leaf iha-invalid-messages-for-primary {
         type uint32;
         description
           "IHA invalid messages for primary";
       }
       leaf iha-invalid-messages-for-secondary {
         type uint32;
         description
           "IHA invalid messages for secondary";
       }
       leaf iha-invalid-messages-for-current-state {
         type uint32;
         description
           "IHA invalid messages for current state";
       }
       leaf iha-messages-sent-for-subtype-init {
         type uint32;
         description
           "IHA messages sent for subtype init";
       }
       leaf iha-messages-rcvd-for-subtype-init {
         type uint32;
         description
           "IHA messages rcvd for subytpe init";
       }
       leaf iha-messages-sent-for-subtype-ack {
         type uint32;
         description
           "IHA messages sent for subtype ack";
       }
       leaf iha-messages-rcvd-for-subtype-ack {
         type uint32;
         description
           "IHA messages rcvd for subtype ack";
       }
       leaf iha-messages-sent-for-subtype-unrepl-sec {
         type uint32;
         description
           "IHA messages sent for subtype unrepl_sec";
       }
       leaf iha-messages-rcvd-for-subtype-unrepl-sec {
         type uint32;
         description
           "IHA messages rcvd for subtype unrepl_sec";
       }
       leaf iha-messages-sent-for-subtype-unrepl-pri {
         type uint32;
         description
           "IHA messages sent for subtype unrepl_pri";
       }
       leaf iha-messages-rcvd-for-subtype-unrepl-pri {
         type uint32;
         description
           "IHA messages rcvd for subtype unrepl_pri";
       }
       leaf iha-messages-sent-for-subtype-unrepl-am-sec {
         type uint32;
         description
           "IHA messages sent for subtype unrepl_am_sec";
       }
       leaf iha-messages-rcvd-for-subtype-unrepl-am-sec {
         type uint32;
         description
           "IHA messages rcvd for subtype unrepl_am_sec";
       }
       leaf iha-message-timeouts {
         type uint32;
         description
           "IHA message timeouts";
       }
       leaf iha-socket-unreplicate-messages {
         type uint32;
         description
           "IHA socket unreplicate messages";
       }
       leaf sdrl {
         type string;
       }
       leaf sdrl-socket-teardowns {
         type uint32;
         description
           "SDRL socket teardowns";
       }
       leaf sdrl-socket-teardown-failures {
         type uint32;
         description
           "SDRL socket teardown failures";
       }
       leaf sdrl-socket-unreplicates {
         type uint32;
         description
           "SDRL socket unreplicates";
       }
       leaf sdrl-socket-unreplicate-failures {
         type uint32;
         description
           "SDRL socket unreplicate failures";
       }
       leaf sdrl-external-timeouts {
         type uint32;
         description
           "SDRL external timeouts";
       }
       leaf sdrl-internal-timeouts {
         type uint32;
         description
           "SDRL internal timeouts";
       }
       leaf sdrl-ipc-messages-sent {
         type uint32;
         description
           "SDRL ipc messages sent";
       }
       leaf sdrl-ipc-send-failures {
         type uint32;
         description
           "SDRL ipc send failures";
       }
       leaf sdrl-ipc-messages-recvd {
         type uint32;
         description
           "SDRL ipc messages recvd";
       }
       leaf sdrl-ipc-recv-failures {
         type uint32;
         description
           "SDRL ipc recv failures";
       }
       leaf sdrl-primary-replication-messages-sent {
         type uint32;
         description
           "SDRL primary replication messages sent";
       }
       leaf sdrl-primary-replication-message-send-failures {
         type uint32;
         description
           "SDRL primary replication message send failures";
       }
       leaf sdrl-primary-ack-messages-received {
         type uint32;
         description
           "SDRL primary ack messages received";
       }
       leaf sdrl-primary-ack-message-receive-failures {
         type uint32;
         description
           "SDRL primary ack message receive failures";
       }
       leaf sdrl-primary-sock-replication-inits {
         type uint32;
         description
           "SDRL primary sock replication inits";
       }
       leaf sdrl-primary-sock-replication-init-failures {
         type uint32;
         description
           "SDRL primary sock message init failures";
       }
       leaf sdrl-primary-throttle-remove-messages {
         type uint32;
         description
           "SDRL primary throttle remove messages";
       }
       leaf sdrl-primary-throttle-remove-failures {
         type uint32;
         description
           "SDRL primary throtle remove failures";
       }
       leaf sdrl-primary-init-handshake-messages {
         type uint32;
         description
           "SDRL primary init handshake messages";
       }
       leaf sdrl-primary-init-handshake-failures {
         type uint32;
         description
           "SDRL primary init handshake failures";
       }
       leaf sdrl-secondary-replication-messages-received {
         type uint32;
         description
           "SDRL secondary replication messages received";
       }
       leaf sdrl-secondary-replication-message-receive-failures {
         type uint32;
         description
           "SDRL secondary replication message receive failures";
       }
       leaf sdrl-secondary-replication-acks-sent {
         type uint32;
         description
           "SDRL secondary replication acks sent";
       }
       leaf sdrl-secondary-replication-ack-send-failures {
         type uint32;
         description
           "SDRL secondary replication ack send failures";
       }
       leaf sdrl-secondary-sock-splits {
         type uint32;
         description
           "SDRL secondary sock splits";
       }
       leaf sdrl-secondary-sock-split-failures {
         type uint32;
         description
           "SDRL secondary sock split failures";
       }
       leaf sdrl-secondary-sock-merges {
         type uint32;
         description
           "SDRL secondary sock merges";
       }
       leaf sdrl-secondary-sock-merge-failures {
         type uint32;
         description
           "SDRL secondary sock merge failures";
       }
       leaf sdrl-secondary-sockets-closed {
         type uint32;
         description
           "SDRL secondary sockets closed";
       }
       leaf sdrl-secondary-rcv-snoop-fd-close-failures {
         type uint32;
         description
           "SDRL secondary rcv snoop fd close failures";
       }
       leaf sdrl-secondary-snd-snoop-fd-close-failures {
         type uint32;
         description
           "SDRL secondary snd snoop fd close failures";
       }
       leaf sdrl-secondary-init-handshake-messages {
         type uint32;
         description
           "SDRL secondary init handshake messages";
       }
       leaf sdrl-secondary-init-handshake-failures {
         type uint32;
         description
           "SDRL secondary init handshake failures";
       }
       leaf prl {
         type string;
       }
       leaf prl-packets-enqueued {
         type uint32;
         description
           "PRL packets enqueued";
       }
       leaf prl-packets-failed-to-enqueue {
         type uint32;
         description
           "PRL packets failed to enqueue";
       }
       leaf prl-packets-dequeued {
         type uint32;
         description
           "PRL packets dequeued";
       }
       leaf prl-packets-failed-to-dequeue {
         type uint32;
         description
           "PRL packets failed to dequeue";
       }
       leaf prl-queue-entry-allocations {
         type uint32;
         description
           "PRL queue entry allocations";
       }
       leaf prl-queue-entry-frees {
         type uint32;
         description
           "PRL queue entry frees";
       }
       leaf prl-calls-to-layer4-input-handlers {
         type uint32;
         description
           "Calls to layer 4 input handlers";
       }
       leaf prl-failed-calls-to-layer4-input-handlers {
         type uint32;
         description
           "Failed calls to layer 4 input handlers";
       }
       leaf prl-queue-drains {
         type uint32;
         description
           "PRL queue drains";
       }
       leaf prl-replication-timeouts {
         type uint32;
         description
           "PRL replication timeouts";
       }
       leaf prl-replication-messages-sent {
         type uint32;
         description
           "PRL replication messages sent";
       }
       leaf prl-replication-message-send-failures {
         type uint32;
         description
           "PRL replication message send failures";
       }
       leaf prl-acknowledgement-messages-sent {
         type uint32;
         description
           "PRL acknowledgment messages sent";
       }
       leaf prl-acknowledgement-message-send-failures {
         type uint32;
         description
           "PRL acknowledgement message send failures";
       }
       leaf prl-replication-message-received {
         type uint32;
         description
           "PRL replication message received";
       }
       leaf prl-replication-message-receive-failures {
         type uint32;
         description
           "PRL replication message receive failures";
       }
       leaf prl-acknowledgement-messages-received {
         type uint32;
         description
           "PRL acknowledgement message received";
       }
       leaf prl-acknowledgement-message-receive-failures {
         type uint32;
         description
           "PRL acknowledgment message receive failures";
       }
       leaf prl-messages-with-bad-ipc-type {
         type uint32;
         description
           "PRL messages with bad IPC type";
       }
       leaf prl-messages-with-no-handler {
         type uint32;
         description
           "PRL messages with no handler";
       }
       leaf prl-global-state-initializations {
         type uint32;
         description
           "PRL global state initializations";
       }
       leaf prl-global-state-cleanups {
         type uint32;
         description
           "PRL global state cleanups";
       }
       leaf prl-per-socket-state-creations {
         type uint32;
         description
           "PRL per-socket state creations";
       }
       leaf prl-per-socket-state-creation-failures {
         type uint32;
         description
           "PRL per-socket state creation failures";
       }
       leaf prl-per-socket-state-cleanups {
         type uint32;
         description
           "PRL per-socket state cleanups";
       }
       leaf prl-socket-closes {
         type uint32;
         description
           "PRL socket closes";
       }
       leaf prl-socket-merges {
         type uint32;
         description
           "PRL socket merges";
       }
       leaf prl-socket-unreplicates {
         type uint32;
         description
           "PRL socket unreplicates";
       }
       leaf prl-primary-socket-replication-initializations {
         type uint32;
         description
           "PRL primary socket replication initializations";
       }
       leaf prl-secondary-socket-replication-initializations {
         type uint32;
         description
           "PRL secondary socket replication initializations";
       }
       leaf prl-primary-socket-replication-activations {
         type int32;
         description
           "PRL primary socket replication activations";
       }
       leaf prl-secondary-socket-replication-activations {
         type uint32;
         description
           "PRL secondary socket replication activations";
       }
       leaf prl-packets-received-from-peers {
         type uint32;
         description
           "Packets received from peers";
       }
       leaf prl-packets-receive-operations-from-peer-failed {
         type uint32;
         description
           "PRL packets receive operations from peer failed";
       }
       leaf prl-buffer-pullup-failures {
         type uint32;
         description
           "PRL buffer pullup failures";
       }
       leaf prl-new-packets-dropped-on-security-socket {
         type uint32;
         description
           "New pkts dropped on secondary socket";
       }
       leaf psrm {
         type string;
       }
       leaf psrm-replication-timeouts {
         type uint32;
         description
           "PSRM replication timeouts";
       }
       leaf psrm-replication-messages-sent {
         type uint32;
         description
           "PSRM replication messages sent";
       }
       leaf psrm-replication-message-send-failures {
         type uint32;
         description
           "PSRM replication message send failures";
       }
       leaf psrm-acknowledgement-messages-sent {
         type uint32;
         description
           "PSRM acknowledgment messages sent";
       }
       leaf psrm-acknowledgement-message-send-failures {
         type uint32;
         description
           "PSRM acknowledgement message send failures";
       }
       leaf psrm-flow-control-messages-sent {
         type uint32;
         description
           "PSRM flow control messages sent";
       }
       leaf psrm-flow-control-message-send-failures {
         type uint32;
         description
           "PSRM flow control message send failures";
       }
       leaf psrm-replication-messages-received {
         type uint32;
         description
           "PSRM replication messages received";
       }
       leaf psrm-replication-message-receive-failures {
         type uint32;
         description
           "PSRM replication message receive failures";
       }
       leaf psrm-acknowledgement-messages-received {
         type uint32;
         description
           "PSRM acknowledgment messages received";
       }
       leaf psrm-acknowledgement-message-receive-failures {
         type uint32;
         description
           "PSRM acknowledgment message receive failures";
       }
       leaf psrm-flow-control-messages-received {
         type uint32;
         description
           "PSRM flow control messages received";
       }
       leaf psrm-flow-control-message-receive-failures {
         type uint32;
         description
           "PSRM flow control message receive failures";
       }
       leaf psrm-messages-with-bad-ipc-type {
         type uint32;
         description
           "PSRM messages with bad IPC type";
       }
       leaf psrm-messages-with-no-handler {
         type uint32;
         description
           "PSRM messages with no handler";
       }
       leaf psrm-global-state-initializations {
         type uint32;
         description
           "PSRM global state initializations";
       }
       leaf psrm-global-state-cleanups {
         type uint32;
         description
           "PSRM global state cleanups";
       }
       leaf psrm-per-socket-state-creations {
         type uint32;
         description
           "PSRM per-socket state creations";
       }
       leaf psrm-per-socket-state-creation-failures {
         type uint32;
         description
           "PSRM per-socket state creation failures";
       }
       leaf psrm-per-socket-state-cleanups {
         type uint32;
         description
           "PSRM per-socket state cleanups";
       }
       leaf psrm-socket-closes {
         type uint32;
         description
           "PSRM socket closes";
       }
       leaf psrm-socket-merges {
         type uint32;
         description
           "PSRM socket merges";
       }
       leaf psrm-socket-unreplicates {
         type uint32;
         description
           "PSRM socket unreplicates";
       }
       leaf psrm-primary-socket-replication-initializations {
         type uint32;
         description
           "PSRM primary socket replication initializations";
       }
       leaf psrm-secondary-socket-replication-initializations {
         type uint32;
         description
           "PSRM secondary socket replication initializations";
       }
       leaf psrm-primary-socket-replication-activations {
         type uint32;
         description
           "PSRM primary socket replication activations";
       }
       leaf psrm-secondary-socket-replication-activations {
         type uint32;
         description
           "PSRM secondary socket replication activations";
       }
       leaf psrm-tcpcb-updates {
         type uint32;
         description
           "PSRM tcpcb updates";
       }
       leaf psrm-buffer-pullup-failures {
         type uint32;
         description
           "PSRM buffer pullup failures";
       }
       leaf psrm-tcp-timestamp-msg-recv-counters {
         type uint32;
         description
           "PSRM tcp timestamp msg recv counters";
       }
       leaf psrm-tcp-timestamp-msg-recv-failures {
         type uint32;
         description
           "PSRM tcp timestamp msg recv failures";
       }
       leaf psrm-tcp-timestamp-msg-send-counters {
         type uint32;
         description
           "PSRM tcp timestamp msg send counters";
       }
       leaf psrm-tcp-timestamp-msg-send-failures {
         type uint32;
         description
           "PSRM tcp timestamp msg send failures";
       }
       leaf tcp-field {
         type string;
       }
       leaf tcp-out-of-order-packets-on-jsr-sockets {
         type uint32;
         description
           "TCP out-of-order packets on JSR sockets";
       }
     }
     container virtual-node-statistics {
       leaf number-of-virtual-node-route-tables {
         type uint32;
         description
           "Number of route-tables marked with virtual-node";
       }
       leaf number-of-virtual-node-vlan-ids {
         type uint32;
         description
           "Number of vlan-ids on virtual-node route-tables";
       }
       leaf no-route-table-auxiliary-structure {
         type uint32;
         description
           "No helper structure found for virtual-node route-table";
       }
       leaf route-table-non-virtual-node-local-address {
         type uint32;
         description
           "IFA callbacks on non-virtual-node tables";
       }
       leaf route-table-virtual-node-local-address {
         type uint32;
         description
           "IFA callbacks on virtual-node tables";
       }
       leaf route-table-no-mbuf-tag {
         type uint32;
         description
           "Route-table mbuf tag not found in a virtual-node context";
       }
       leaf route-table-not-found {
         type uint32;
         description
           "Route-table indicated by virtual-node mbuf tag not found";
       }
       leaf route-table-non-virtual-node {
         type uint32;
         description
           "Route-table found from tag was not enabled for virtual-node";
       }
       leaf route-table-no-shared-vlan {
         type uint32;
         description
           "No shared vlan associated with virtual-node table";
       }
       leaf packets-transmitted-to-fabric {
         type uint32;
         description
           "Packets transmitted to the virtual-node fabric";
       }
       leaf packets-received-from-fabric {
         type uint32;
         description
           "Packets received from the virtual-node fabric";
       }
       leaf no-interface-for-egress-statistics {
         type uint32;
         description
           "Interface not found to update traffic statistics";
       }
       leaf duplicate-vlan-id {
         type uint32;
         description
           "Route table update attempts with duplicate vlan-id";
       }
     }
     container virtual-node-packet-record-statistics {
       leaf packet_recording_status {
         type string;
         description
           "Control packet recording status on the virtual-node";
       }
       leaf packet-records-created {
         type uint32;
         description
           "ICMP/UDP records added";
       }
       leaf packet-records-deleted {
         type uint32;
         description
           "ICMP/UDP records removed";
       }
       leaf packet-record-create-errors {
         type uint32;
         description
           "Record creations errored out";
       }
       leaf packet-record-delete-errors {
         type uint32;
         description
           "Record deletions errored out";
       }
       leaf packet-record-get-errors {
         type uint32;
         description
           "Records not found";
       }
       leaf udp-records-timed-out {
         type uint32;
         description
           "UDP packet records timed out";
       }
       leaf icmp-records-timed-out {
         type uint32;
         description
           "ICMP packet records timed out";
       }
       leaf to-fabric-dont-care-protocol {
         type uint32;
         description
           "To-fabric OAM packets, no matching reply expected";
       }
       leaf from-fabric-dont-care-protocol {
         type uint32;
         description
           "From-fabric OAM packets, no matching reply expected";
       }
       leaf to-fabric-unchecked-icmp {
         type uint32;
         description
           "To-fabric ICMP packets, with no record created";
       }
       leaf from-fabric-unchecked-icmp {
         type uint32;
         description
           "From-fabric ICMP packets, with no record consulted";
       }
       leaf to-fabric-unchecked-udp {
         type uint32;
         description
           "To-fabric UDP packets, with no record created";
       }
       leaf from-fabric-unchecked-udp {
         type uint32;
         description
           "From-fabric UDP packets, with no record consulted";
       }
       leaf from-fabric-unhandled-protocol {
         type uint32;
         description
           "From-fabric packets, protocol not handled by records";
       }
       leaf to-fabric-unhandled-protocol {
         type uint32;
         description
           "To-fabric packets, protocol not handled by records";
       }
       leaf to-fabric-drops {
         type uint32;
         description
           "Packets dropped at egress to fabric";
       }
       leaf from-fabric-drops {
         type uint32;
         description
           "Packets dropped at ingress from fabric";
       }
       leaf to-fabric-not-my-packet {
         type uint32;
         description
           "Packets re-sent to fabric due to unmatched record";
       }
       leaf to-fabric-split-horizon-suppress {
         type uint32;
         description
           "Unmatched packets not re-sent due to ingress from fabric";
       }
       leaf active-timers {
         type uint32;
         description
           "Packet timers active";
       }
       leaf requests-over-limit {
         type uint32;
         description
           "Packets not recorded due to resource constraints";
       }
     }
   }
   grouping extended-system-stats-block {
     leaf ip-systemstats-inreceives {
       type uint64;
       description
         "In Recieves";
     }
     leaf ip-systemstats-inoctets {
       type uint64;
       description
         "In Octets";
     }
     leaf ip-systemstats-inhdrerrors {
       type uint64;
       description
         "In Header Errors";
     }
     leaf ip-systemstats-innoroutes {
       type uint64;
       description
         "In No Routes";
     }
     leaf ip-systemstats-inaddrerrors {
       type uint64;
       description
         "In Address Errors";
     }
     leaf ip-systemstats-inunknownprotos {
       type uint64;
       description
         "In Unknown protocols";
     }
     leaf ip-systemstats-intruncatedpkts {
       type uint64;
       description
         "In Truncated Packets";
     }
     leaf ip-systemstats-inforwdatagrams {
       type uint64;
       description
         "In Forward Datagrams";
     }
     leaf ip-systemstats-reasmreqds {
       type uint64;
       description
         "Reassemble Reqds";
     }
     leaf ip-systemstats-reasmoks {
       type uint64;
       description
         "Reassmeble OKs";
     }
     leaf ip-systemstats-reasmfails {
       type uint64;
       description
         "Reassemble Fails";
     }
     leaf ip-systemstats-indiscards {
       type uint64;
       description
         "In Discards";
     }
     leaf ip-systemstats-indelivers {
       type uint64;
       description
         "In Delivers";
     }
     leaf ip-systemstats-outrequets {
       type uint64;
       description
         "Out Requests";
     }
     leaf ip-systemstats-outnoroutes {
       type uint64;
       description
         "OUt No Routes";
     }
     leaf ip-systemstats-outforwdatagrams {
       type uint64;
       description
         "Out Forward Datagrams";
     }
     leaf ip-systemstats-outdiscards {
       type uint64;
       description
         "Out Discards";
     }
     leaf ip-systemstats-outfragreqds {
       type uint64;
       description
         "Out Fragmentation Reqds";
     }
     leaf ip-systemstats-outfragoks {
       type uint64;
       description
         "Out Fragmentaion OK";
     }
     leaf ip-systemstats-outfragfails {
       type uint64;
       description
         "Out Fragmentation Fails";
     }
     leaf ip-systemstats-outfragcreats {
       type uint64;
       description
         "Out Fragment Creats";
     }
     leaf ip-systemstats-outtransmits {
       type uint64;
       description
         "Out Transmits";
     }
     leaf ip-systemstats-outoctets {
       type uint64;
       description
         "Out Octets";
     }
     leaf ip-systemstats-inmcastpkts {
       type uint64;
       description
         "In Multicats Packets";
     }
     leaf ip-systemstats-inmcastoctets {
       type uint64;
       description
         "In Multicast Octets";
     }
     leaf ip-systemstats-outmcastpkts {
       type uint64;
       description
         "Out Multicats Packets";
     }
     leaf ip-systemstats-outmcastoctets {
       type uint64;
       description
         "Out Multicast Octets";
     }
     leaf ip-systemstats-discontinuitytime {
       type string;
       description
         "Sysstats disconuity time";
     }
   }
   grouping icmpd-internal-statistics-block {
     leaf printable-display {
       type string;
     }
   }
   grouping kfw-statistics-block {
     leaf total-bind-add-req {
       type uint64;
     }
     leaf total-bind-del-req {
       type uint64;
     }
     leaf kernel-bind-add-req {
       type uint64;
     }
     leaf kernel-bind-del-req {
       type uint64;
     }
     leaf kernel-bind-add-success {
       type uint64;
     }
     leaf kernel-bind-del-success {
       type uint64;
     }
     leaf kernel-bind-add-install-fail {
       type uint64;
     }
     leaf kernel-bind-del-install-fail {
       type uint64;
     }
     leaf kernel-bind-add-filter-notpresent {
       type uint64;
     }
     leaf kernel-bind-del-filter-notpresent {
       type uint64;
     }
     leaf kernel-bind-add-unsupported {
       type uint64;
     }
     leaf kernel-bind-del-unsupported {
       type uint64;
     }
     leaf total-filter-add-req {
       type uint64;
     }
     leaf total-filter-chg-req {
       type uint64;
     }
     leaf total-filter-del-req {
       type uint64;
     }
     leaf kernel-filter-add-req {
       type uint64;
     }
     leaf kernel-filter-chg-req {
       type uint64;
     }
     leaf kernel-filter-del-req {
       type uint64;
     }
     leaf kernel-filter-add-success {
       type uint64;
     }
     leaf kernel-filter-chg-success {
       type uint64;
     }
     leaf kernel-filter-del-success {
       type uint64;
     }
     leaf kernel-filter-add-install-fail {
       type uint64;
     }
     leaf kernel-filter-chg-install-fail {
       type uint64;
     }
     leaf kernel-filter-del-install-fail {
       type uint64;
     }
     leaf kernel-filter-add-filter-notpresent {
       type uint64;
     }
     leaf kernel-filter-chg-filter-notpresent {
       type uint64;
     }
     leaf kernel-filter-del-filter-notpresent {
       type uint64;
     }
     leaf kernel-filter-add-unsupported {
       type uint64;
     }
     leaf kernel-filter-chg-unsupported {
       type uint64;
     }
     leaf kernel-filter-del-unsupported {
       type uint64;
     }
     leaf total-policer-add-req {
       type uint64;
     }
     leaf total-policer-del-req {
       type uint64;
     }
     leaf total-policer-chg-req {
       type uint64;
     }
     leaf kernel-policer-chg-req {
       type uint64;
     }
     leaf kernel-policer-chg-success {
       type uint64;
     }
     leaf kernel-policer-chg-install-fail {
       type uint64;
     }
     leaf kernel-policer-chg-policer-notpresent {
       type uint64;
     }
   }
   grouping system-storage-information-block {
     leaf device-size {
       type int32;
       description
         "Device size";
     }
     list filesystem {
       key "filesystem-name";
       description
         "Information about system storage";
       leaf filesystem-name {
         type string;
         description
           "Name of the filesystem";
       }
       leaf total-blocks {
         type int32;
         description
           "Number of 512 blocks";
       }
       leaf used-blocks {
         type int32;
         description
           "Used storage space";
       }
       leaf available-blocks {
         type int32;
         description
           "Available storage space";
       }
       leaf used-percent {
         type int32;
         description
           "Percent of filesystem in use";
       }
       leaf mounted-on {
         type string;
         description
           "Filesystem mounted on";
       }
     }
   }
   grouping system-storage-analysis-information-block {
     list filesystem-entry {
       key "filesystem-name";
       leaf filesystem-name {
         type string;
         description
           "Name of the filesystem";
       }
       leaf mounted-on {
         type string;
         description
           "Filesystem mounted on";
       }
       leaf total-kb {
         type string;
         description
           "Storage space total size in KB";
       }
       leaf avail-kb {
         type string;
         description
           "Storage space available in KB";
       }
       leaf used-kb {
         type string;
         description
           "Storage space in use in KB";
       }
       leaf used-percent {
         type int32;
         description
           "Percent of filesystem in use";
       }
       leaf fs-invisible-usage {
         type string;
         description
           "Invisible storage usage";
       }
       container filesystem-large-items {
         list filesystem-large-item {
           key "filesystem-large-item-info";
           leaf filesystem-large-item-size {
             type string;
             description
               "Size of the file/directory";
           }
           leaf filesystem-large-item-info {
             type string;
             description
               "Item information ";
           }
         }
       }
       container fstat-items {
         list fstat-item {
           key "fstat-item-fd";
           leaf fstat-item-sz-dv {
             type string;
             description
               "SZ DV";
           }
           leaf fstat-item-pid {
             type string;
             description
               "PID";
           }
           leaf fstat-item-fd {
             type string;
             description
               "FD";
           }
           leaf fstat-item-mode {
             type string;
             description
               "Mode";
           }
           leaf fstat-item-rw {
             type string;
             description
               "RW";
           }
           leaf fstat-item-user {
             type string;
             description
               "User";
           }
           leaf fstat-item-command {
             type string;
             description
               "Command";
           }
         }
       }
       container remount-check {
         leaf remount-check-size {
           type string;
           description
             "Size";
         }
         leaf remount-check-invisible-usage {
           type string;
           description
             "Invisible Usage";
         }
         leaf remount-check-status {
           type string;
           description
             "Status";
         }
         container remount-check-differences {
           list remount-check-difference {
             key "remount-check-difference-path";
             leaf remount-check-difference-extra-usage {
               type string;
               description
                 "Extra Usage";
             }
             leaf remount-check-difference-apparent-usage {
               type string;
               description
                 "Apparent Usage";
             }
             leaf remount-check-difference-actual-usage {
               type string;
               description
                 "Actual Usage";
             }
             leaf remount-check-difference-path {
               type string;
               description
                 "Path";
             }
           }
         }
       }
     }
     list directory-entry {
       key "directory-path";
       leaf directory-path {
         type string;
         description
           "Directory path being analyzed";
       }
       leaf directory-scope {
         type string;
         description
           "Analysis scope: all (cross-mount) or filesystem-only";
       }
       container filesystem-large-items {
         list filesystem-large-item {
           key "filesystem-large-item-info";
           leaf filesystem-large-item-size {
             type string;
             description
               "Size of the file/directory";
           }
           leaf filesystem-large-item-info {
             type string;
             description
               "Item information ";
           }
         }
       }
       container fstat-items {
         list fstat-item {
           key "fstat-item-fd";
           leaf fstat-item-sz-dv {
             type string;
             description
               "SZ DV";
           }
           leaf fstat-item-pid {
             type string;
             description
               "PID";
           }
           leaf fstat-item-fd {
             type string;
             description
               "FD";
           }
           leaf fstat-item-mode {
             type string;
             description
               "Mode";
           }
           leaf fstat-item-rw {
             type string;
             description
               "RW";
           }
           leaf fstat-item-user {
             type string;
             description
               "User";
           }
           leaf fstat-item-command {
             type string;
             description
               "Command";
           }
         }
       }
       container remount-check {
         leaf remount-check-size {
           type string;
           description
             "Size";
         }
         leaf remount-check-invisible-usage {
           type string;
           description
             "Invisible Usage";
         }
         leaf remount-check-status {
           type string;
           description
             "Status";
         }
         container remount-check-differences {
           list remount-check-difference {
             key "remount-check-difference-path";
             leaf remount-check-difference-extra-usage {
               type string;
               description
                 "Extra Usage";
             }
             leaf remount-check-difference-apparent-usage {
               type string;
               description
                 "Apparent Usage";
             }
             leaf remount-check-difference-actual-usage {
               type string;
               description
                 "Actual Usage";
             }
             leaf remount-check-difference-path {
               type string;
               description
                 "Path";
             }
           }
         }
       }
     }
   }
   grouping switchover-information-block {
     leaf switchover-state {
       type string;
     }
     leaf commit-in-progress {
       type string;
     }
     container switchover-mode {
       leaf multichassis-mode {
         type empty;
         description
           "Kernel replication for multichassis";
       }
       leaf gres-mode {
         type empty;
         description
           "Kernel replication for graceful switchover";
       }
       leaf unknown-mode {
         type empty;
         description
           "Kernel replication for unknown mode";
       }
     }
     container configuration-state {
       leaf configuration-ready {
         type empty;
         description
           "Configuration database is synchronized with master";
       }
       leaf configuration-synchronizing {
         type empty;
         description
           "Synchronizing configuration database with master";
       }
       leaf configuration-synchronize-error {
         type empty;
         description
           "Failure during configuration database synchronize";
       }
     }
     container object-database-state {
       leaf object-database-sync-state {
         type string;
         description
           "Object Database State";
       }
     }
     container node-apps-ready-state {
       leaf node-apps-ready-state-info {
         type string;
         description
           "Node Apps Ready State";
       }
     }
     container replication-state {
       leaf replication-ready {
         type empty;
         description
           "Replicated kernel state is synchronized with master";
       }
       leaf replication-synchronizing {
         type empty;
         description
           "Replicated kernel is receiving state updates from master";
       }
       leaf replication-error {
         type empty;
         description
           "Replicated and master kernels do not have identical state";
       }
       leaf replication-version-mismatch {
         type empty;
         description
           "Replicated and master kernels running incompatible versions";
       }
       leaf replication-connection-error {
         type empty;
         description
           "Master connection error";
       }
       leaf replication-reconnect-error {
         type empty;
         description
           "Reconnect to master failed";
       }
       leaf replication-init-error {
         type empty;
         description
           "Error during initialization";
       }
     }
     container platform-switchover-status {
       leaf platform-switchover-ready {
         type string;
         description
           "Platform Components Switchover State";
       }
     }
     container platform-switchover-components-status {
       leaf component-name {
         type string;
         description
           "Platform Component Name";
       }
       leaf component-state {
         type string;
         description
           "Platform Component Name";
       }
     }
     container gresreadiness-status {
       leaf switchover-status {
         type string;
       }
     }
     container fabric-ready-status {
       leaf fabric-ready-status-info {
         type string;
         description
           "Fabric Ready Status";
       }
     }
     container peer-transition-state {
       leaf peer-connected {
         type empty;
         description
           "Peer in switchover transition";
       }
       leaf peer-in-steady-state {
         type empty;
         description
           "Peer completed switchover transition";
       }
     }
   }
   grouping system-services-reverse-information-block {
     container reverse-connection {
       leaf reverse-since {
         type string;
         description
           "Connected since";
       }
       leaf reverse-method {
         type string;
         description
           "Connection method";
       }
     }
   }
   grouping outbound-ssh-service-information-block {
     list outbound-ssh-client {
       description
         "Outbound SSH application information";
       leaf outbound-ssh-client-name {
         type string;
         description
           "Outbound SSH client application identifier";
       }
       leaf outbound-ssh-server-info {
         type string;
         description
           "Outbound SSH server information in host:port format";
       }
       leaf outbound-ssh-connection-status {
         type string;
         description
           "Application connection status";
       }
       leaf outbound-ssh-connection-uptime {
         type string;
         description
           "Application connection uptime";
       }
       container outbound-ssh-proxy-info {
         leaf outbound-ssh-proxy-type {
           type string;
           description
             "Proxy type, static or DHCP";
         }
         leaf outbound-ssh-proxy-server {
           type string;
           description
             "Proxy server information in host:port format";
         }
         leaf outbound-ssh-proxy-auth {
           type string;
           description
             "Proxy authorization";
         }
       }
       leaf outbound-ssh-device-id {
         type string;
         description
           "Outbound SSH device identifier";
       }
     }
   }
   grouping system-memory-information-block {
     container system-memory-summary-information {
       leaf system-memory-total {
         type string;
         description
           "Total system memory";
       }
       leaf system-memory-total-percent {
         type string;
         description
           "Total system memory as percent of total";
       }
       leaf system-memory-reserved {
         type string;
         description
           "Reserved system memory";
       }
       leaf system-memory-reserved-percent {
         type string;
         description
           "Reserved system memory as percent of total";
       }
       leaf system-memory-wired {
         type string;
         description
           "Wired system memory";
       }
       leaf system-memory-wired-percent {
         type string;
         description
           "Wired system memory as percent of total";
       }
       leaf system-memory-active {
         type string;
         description
           "Active system memory";
       }
       leaf system-memory-active-percent {
         type string;
         description
           "Active system memory as percent of total";
       }
       leaf system-memory-inactive {
         type string;
         description
           "Inctive system memory";
       }
       leaf system-memory-inactive-percent {
         type string;
         description
           "Inctive system memory as percent of total";
       }
       leaf system-memory-cache {
         type string;
         description
           "Cache system memory";
       }
       leaf system-memory-cache-percent {
         type string;
         description
           "Cache system memory as percent of total";
       }
       leaf system-memory-used {
         type string;
         description
           "Used system memory";
       }
       leaf system-memory-used-percent {
         type string;
         description
           "Used system memory as percent of total";
       }
       leaf system-memory-free {
         type string;
         description
           "Free system memory";
       }
       leaf system-memory-free-percent {
         type string;
         description
           "Free system memory as percent of total";
       }
       leaf system-memory-buffer {
         type string;
         description
           "Buffer system memory";
       }
       leaf system-memory-buffer-percent {
         type string;
         description
           "Buffer system memory as percent of total";
       }
       leaf system-memory-swap {
         type string;
         description
           "Swap system memory";
       }
       leaf system-memory-swap-percent {
         type string;
         description
           "Swap system memory as percent of total";
       }
       leaf system-memory-available {
         type string;
         description
           "Available system memory";
       }
       leaf system-memory-available-percent {
         type string;
         description
           "Available system memory as percent of total";
       }
       leaf system-memory-cached {
         type string;
         description
           "Cached system memory";
       }
       leaf system-memory-cached-percent {
         type string;
         description
           "Cached system memory as percent of total";
       }
     }
     container memory-disk-resident-information {
       leaf resident-memory {
         type string;
       }
     }
     container pmap-brief-information {
       description
         "Memory usage brief summary of an entry (Process/map)";
       container pmap-brief-summary {
         description
           "Memory usage brief summary of an entry (Process/map)";
         leaf pid {
           type int32;
           description
             "PID of the process that generated the event";
         }
         leaf size {
           type int32;
           description
             "File size in bytes";
         }
         leaf resident {
           type uint32;
           description
             "Physical memory resident for mapping";
         }
         leaf shared {
           type uint32;
           description
             "Shared memory of mapping";
         }
         leaf private {
           type uint32;
           description
             "Private memory of mapping";
         }
         leaf process-name {
           type string;
           description
             "Process name";
         }
         leaf map-name {
           type string;
           description
             "Map name";
         }
       }
     }
     container pmap-terse-information {
       description
         "Memory usage terse summary of an entry (Process/map)";
       list pmap-terse-summary {
         description
           "Memory usage terse summary of an entry (Process/map)";
         leaf pid {
           type int32;
           description
             "PID of the process that generated the event";
         }
         leaf size {
           type int32;
           description
             "File size in bytes";
         }
         leaf size-percent {
           type string;
           description
             "Virtual size of mapping as percent of total based on limit";
         }
         leaf resident {
           type uint32;
           description
             "Physical memory resident for mapping";
         }
         leaf resident-percent {
           type string;
           description
             "Physical memory resident for mapping as percent of total";
         }
         leaf process-name {
           type string;
           description
             "Process name";
         }
         leaf map-name {
           type string;
           description
             "Map name";
         }
       }
     }
   }
   grouping system-virtual-memory-information-block {
     container vmstat-memstat-malloc {
       description
         "Kernel malloc information";
       list vmstat-memstat-info {
         leaf memstat-name {
           type string;
         }
         leaf inuse {
           type int32;
         }
         leaf memuse {
           type int32;
         }
         leaf high-use {
           type string;
         }
         leaf memstat-req {
           type int32;
         }
         leaf memstat-size {
           type string;
         }
       }
     }
     container vmstat-memstat-zone {
       list vmstat-zone-info {
         leaf zone-name {
           type string;
         }
         leaf zone-size {
           type uint32;
         }
         leaf count-limit {
           type uint32;
         }
         leaf used {
           type uint32;
         }
         leaf free {
           type uint32;
         }
         leaf zone-req {
           type uint32;
         }
       }
     }
     container vmstat-intr {
       list vmstat-intr-info {
         leaf intr-name {
           type string;
         }
         leaf intr-cnt {
           type string;
         }
         leaf intr-rate {
           type string;
         }
       }
     }
     container vmstat-sumstat {
       leaf cpu-context-switch {
         type uint32;
       }
       leaf dev-intr {
         type uint32;
       }
       leaf soft-intr {
         type uint32;
       }
       leaf traps {
         type uint32;
       }
       leaf sys-calls {
         type uint32;
       }
       leaf kernel-thrds {
         type uint32;
       }
       leaf fork-calls {
         type uint32;
       }
       leaf vfork-calls {
         type uint32;
       }
       leaf rfork-calls {
         type uint32;
       }
       leaf swap-pageins {
         type uint32;
       }
       leaf swap-pagedin {
         type uint32;
       }
       leaf swap-pageouts {
         type uint32;
       }
       leaf swap-pagedout {
         type uint32;
       }
       leaf vnode-pageins {
         type uint32;
       }
       leaf vnode-pagedin {
         type uint32;
       }
       leaf vnode-pageouts {
         type uint32;
       }
       leaf vnode-pagedout {
         type uint32;
       }
       leaf page-daemon-wakeup {
         type uint32;
       }
       leaf page-daemon-examined-pages {
         type uint32;
       }
       leaf pages-reactivated {
         type uint32;
       }
       leaf clean-page-reclamation-shortfalls {
         type uint32;
       }
       leaf pages-reactivated-by-the-page-daemon {
         type uint32;
       }
       leaf copy-on-write-faults {
         type uint32;
       }
       leaf copy-on-write-optimized-faults {
         type uint32;
       }
       leaf zero-fill-pages-zeroed {
         type uint32;
       }
       leaf zero-fill-pages-prezeroed {
         type uint32;
       }
       leaf transit-blocking-page-faults {
         type uint32;
       }
       leaf total-vm-faults {
         type uint32;
       }
       leaf page-faults-requiring-io {
         type uint32;
       }
       leaf pages-affected-by-kernel-thrd-creat {
         type uint32;
       }
       leaf pages-affected-by-fork {
         type uint32;
       }
       leaf pages-affected-by-vfork {
         type uint32;
       }
       leaf pages-affected-by-rfork {
         type uint32;
       }
       leaf pages-freed {
         type uint32;
       }
       leaf pages-freed-by-deamon {
         type uint32;
       }
       leaf pages-freed-by-exiting-proc {
         type uint32;
       }
       leaf pages-active {
         type uint32;
       }
       leaf pages-inactive {
         type uint32;
       }
       leaf pages-in-vm-cache {
         type uint32;
       }
       leaf pages-in-the-laundry-queue {
         type uint32;
       }
       leaf virtual-user-pages-wired-down {
         type uint32;
       }
       leaf pages-wired-down {
         type uint32;
       }
       leaf pages-free {
         type uint32;
       }
       leaf bytes-per-page {
         type uint32;
       }
       leaf swap-pages-used {
         type uint32;
       }
       leaf peak-swap-pages-used {
         type uint32;
       }
       leaf total-name-lookups {
         type int32;
       }
       leaf positive-cache-hits {
         type int32;
       }
       leaf negative-cache-hits {
         type int32;
       }
       leaf pass2 {
         type int32;
       }
       leaf cache-deletions {
         type int32;
       }
       leaf cache-falsehits {
         type int32;
       }
       leaf toolong {
         type int32;
       }
     }
     container vm-kernel-state {
       leaf vm-kmem-map-free {
         type string;
       }
     }
     container kernel-direct-mm-size-information {
       leaf vm-directmm-size-used {
         type string;
         description
           "Direct memory map used size in pages";
       }
       leaf vm-directmm-size-max {
         type string;
         description
           "Direct memory map max size in pages";
       }
     }
     container vmstat-fork-stat {
       leaf fork-stat {
         type uint32;
       }
       leaf fork-pages {
         type uint32;
       }
       leaf fork-average-pages-per-fork {
         type uint32;
       }
       leaf vfork-stat {
         type uint32;
       }
       leaf vfork-pages {
         type uint32;
       }
       leaf vfork-average-pages-per-vfork {
         type uint32;
       }
       leaf rfork-stat {
         type uint32;
       }
       leaf rfork-pages {
         type uint32;
       }
       leaf rfork-average-pages-per-rfork {
         type uint32;
       }
     }
     container vmstat-times {
       leaf vmstat-times-reclaims {
         type uint32;
       }
       leaf vmstat-times-reclaims-total-time {
         type uint32;
       }
       leaf vmstat-times-average-time-to-reclaim {
         type uint32;
       }
       leaf vmstat-times-pageins {
         type uint32;
       }
       leaf vmstat-times-pageins-total-time {
         type uint32;
       }
       leaf vmstat-times-average-time-to-pageins {
         type string;
       }
     }
     container meminfo {
       leaf meminfo-name {
         type string;
       }
       leaf meminfo-size {
         type string;
       }
       leaf meminfo-unit {
         type string;
       }
     }
     container interrupts {
       leaf interrupts-type {
         type string;
       }
       leaf interrupts-cpu0 {
         type string;
       }
       leaf interrupts-cpu1 {
         type string;
       }
       leaf interrupts-cpu2 {
         type string;
       }
       leaf interrupts-cpu3 {
         type string;
       }
       leaf interrupts-info {
         type string;
       }
     }
     container vmstat {
       leaf vmstat-cache {
         type string;
       }
       leaf vmstat-cache-num {
         type string;
       }
       leaf vmstat-cache-total {
         type string;
       }
       leaf vmstat-cache-size {
         type string;
       }
       leaf vmstat-cache-pages {
         type string;
       }
     }
   }
   grouping system-users-information-block {
     container uptime-information {
       description
         "System uptime details";
       leaf date-time {
         type string;
       }
       leaf up-time {
         type string;
         description
           "Uptime in ascii format";
       }
       leaf active-user-count {
         type int32;
         description
           "Number of users currently logged in";
       }
       leaf load-average-1 {
         type string;
         description
           "Load average for last 1 minute";
       }
       leaf load-average-5 {
         type string;
         description
           "Load average for last 5 minutes";
       }
       leaf load-average-15 {
         type string;
         description
           "Load average for last 15 minutes";
       }
       container user-table {
         list user-entry {
           leaf user {
             type string;
             description
               "User name executing this script";
           }
           leaf tty {
             type string;
             description
               "Name of the terminal the user is on";
           }
           leaf from {
             type string;
             description
               "Host from which the user is logged on";
           }
           leaf login-time {
             type string;
             description
               "Time the user logged on";
           }
           leaf idle-time {
             type string;
             description
               "Time since the user last typed anything";
           }
           leaf command {
             type string;
           }
         }
         container process-table {
           list process-entry {
             leaf process-id {
               type int32;
               description
                 "Process identifier";
             }
             leaf command {
               type string;
             }
           }
         }
       }
     }
     container web-management-users {
       list web-management-user {
         leaf user {
           type string;
           description
             "User name executing this script";
         }
         leaf tty {
           type string;
           description
             "Name of the terminal the user is on";
         }
         leaf from {
           type string;
           description
             "Host from which the user is logged on";
         }
         leaf login-time {
           type string;
           description
             "Time the user logged on";
         }
         leaf idle-time {
           type string;
           description
             "Time since the user last typed anything";
         }
       }
     }
   }
   grouping syslog-events-block {
     leaf syslog {
       type string;
       description
         "Syslog events in traditional format";
     }
     leaf error-message {
       type string;
       description
         "Syslog events error";
     }
     container data {
       description
         "Syslog events in structured-data format";
       leaf configuration-text {
         type string;
         description
           "System configuration, in text format";
       }
       container netconf-state {
         container schemas {
           list schema {
             leaf identifier {
               type string;
             }
             leaf version {
               type string;
               description
                 "JUNOS version";
             }
             leaf format {
               type string;
             }
             leaf namespace {
               type string;
             }
             leaf location {
               type string;
             }
           }
         }
         container capabilities {
           leaf-list capability {
             type string;
           }
         }
         container datastores {
           list datastore {
             key "name";
             leaf name {
               type string;
               description
                 "Syslog message tag name";
             }
             container locks {
               container global-lock {
                 leaf locked-by-session {
                   type uint32;
                 }
                 leaf locked-time {
                   type string;
                 }
               }
             }
           }
         }
         container sessions {
           list session {
             leaf session-id {
               type int32;
               description
                 "Id of session related to the error";
             }
             leaf transport {
               type string;
             }
             leaf user-name {
               type string;
             }
             leaf source-host {
               type string;
             }
             leaf login-time {
               type string;
               description
                 "Time the user logged on";
             }
             leaf in-rpcs {
               type uint32;
             }
             leaf in-bad-rpcs {
               type uint32;
             }
             leaf out-bad-rpcs {
               type uint32;
             }
             leaf out-notifications {
               type uint32;
             }
           }
         }
         container statistics {
           leaf netconf-start-time {
             type string;
           }
           leaf in-bad-hellos {
             type uint32;
           }
           leaf in-sessions {
             type uint32;
           }
           leaf dropped-sessions {
             type uint32;
           }
           leaf in-rpcs {
             type uint32;
           }
           leaf out-rpc-errors {
             type uint32;
           }
           leaf out-notifications {
             type uint32;
           }
         }
       }
       container netconf {
         container streams {
           list stream {
             key "name";
             leaf name {
               type string;
               description
                 "Syslog message tag name";
             }
             leaf description {
               type string;
               description
                 "Syslog message extended help information";
             }
           }
         }
       }
     }
   }
   grouping hw-resource-utilization-information-block {
     list hw-resource-utilization-info {
       leaf resource-name {
         type string;
         description
           "Resource name";
       }
       leaf size {
         type uint64;
         description
           "Maximum entries";
       }
       leaf allocated {
         type uint64;
         description
           "Current entries";
       }
       leaf utilization {
         type uint64;
         description
           "Current utilization";
       }
     }
   }
   grouping recycle-bandwidth-profile-information-block {
     leaf rcy-total-bandwidth {
       type string;
       description
         "Recycle Total Bandwidth";
     }
     list recycle-bandwidth-per-pfe {
       leaf recycle-bandwidth-pfe-no {
         type uint64;
         description
           "Recycle Bandwidth Pfe No";
       }
       list recycle-bandwidth-per-profile {
         leaf application-name {
           type string;
           description
             "Recycle Bandwidth Application Name";
         }
         leaf rcy-core {
           type uint64;
           description
             "Recycle Bandwidth Profile Each Core";
         }
         leaf bandwidth-usage {
           type uint32;
         }
         leaf port-no {
           type uint64;
           description
             "Recycle Bandwidth Application port no";
         }
         leaf voq-id {
           type uint64;
           description
             "Recycle Bandwidth port's voq-id";
         }
         leaf profilename {
           type string;
           description
             " Recycle Bandwidth profile name";
         }
       }
     }
   }
   grouping recycle-voq-information-block {
     container recycle-voq-per-fpc {
       leaf rcy-fpc-no {
         type string;
         description
           "FPC number";
       }
       list recycle-voq-per-pfe {
         leaf rcy-pfe-no {
           type string;
           description
             "PFE number";
         }
         list recycle-voq-per-queue {
           leaf rcy-queue-no {
             type string;
             description
               " Queue no";
           }
           leaf rcy-queued-packets {
             type string;
             description
               "Total Queue Packets";
           }
           leaf rcy-queued-packets-pps {
             type string;
             description
               "Rate at which packets are queued";
           }
           leaf rcy-queued-bytes {
             type string;
             description
               "Rate at which bytes are queued";
           }
           leaf rcy-queued-bytes-bps {
             type string;
             description
               "Queued Bytes bps";
           }
           leaf rcy-trans-packets {
             type string;
             description
               "Total number of transmitted packets ";
           }
           leaf rcy-trans-packets-pps {
             type string;
             description
               "Rate at which packets are transmitted";
           }
           leaf rcy-trans-bytes {
             type string;
             description
               "Total number of transmitted bytes ";
           }
           leaf rcy-trans-bytes-bps {
             type string;
             description
               "Rate at which bytes are transmitted";
           }
           leaf rcy-trans-tail-packets {
             type string;
             description
               "Number of packets dropped at the tail of the queue";
           }
           leaf rcy-trans-tail-packets-pps {
             type string;
             description
               "Rate at which packets are dropped at tail of queue";
           }
           leaf rcy-trans-tail-bytes {
             type string;
             description
               "Number of bytes dropped at the tail of the queue";
           }
           leaf rcy-trans-tail-bytes-bps {
             type string;
             description
               "Rate at which bytes are dropped at tail of queue";
           }
         }
       }
     }
   }
   grouping recycle-bandwidth-available-details-block {
     list recycle-bandwidth-info-per-pfe {
       leaf board-name {
         type string;
         description
           "Recycle Bandwidth board name";
       }
       leaf pfe-id-no {
         type uint64;
         description
           "Fpc slot pfe-id";
       }
       leaf core-no {
         type uint64;
         description
           "Pfe core number";
       }
       leaf rcy-bw-used {
         type uint64;
         description
           "Recycle Bandwidth used";
       }
       leaf rcy-bw-avail {
         type uint64;
         description
           "Recycle Bandwidth available";
       }
     }
   }
   grouping firewall-profile-summary-block {
     list firewall-profile-summary-details {
       leaf profile-category {
         type string;
         description
           "Firewall profile category name";
       }
       leaf active-profile-name {
         type string;
         description
           "Firewall active profile name";
       }
     }
   }
   grouping firewall-profile-information-block {
     list firewall-profile-details {
       leaf profile-category-name {
         type string;
         description
           "Firewall profile category name";
       }
       leaf profile-name-list {
         type string;
         description
           "Firewall profile name";
       }
       leaf config-cli {
         type string;
         description
           "Firewall profile config cli command";
       }
       leaf supported-matches {
         type string;
         description
           "Firewall profile supported match";
       }
       leaf profile-caveats {
         type string;
         description
           "Firewall profile caveats";
       }
       leaf profile-scale {
         type string;
         description
           "Firewall profile scale";
       }
       leaf profile-description {
         type string;
         description
           "Firewall profile description";
       }
     }
   }
   grouping hw-profile-information-block {
     leaf hw-profile-name {
       type string;
       description
         "Active hardware profile name";
     }
     leaf hw-profile-status {
       type string;
       description
         "Active hardware profile status";
     }
     container hw-profile-information-details {
       leaf hw-profile-name {
         type string;
         description
           "Active hardware profile name";
       }
       leaf hw-profile-status {
         type string;
         description
           "Active hardware profile status";
       }
     }
     list hw-profile-status-per-app {
       key "per-profile-name";
       leaf per-profile-name {
         type string;
         description
           "Name of profile";
       }
       leaf app-name {
         type string;
         description
           " Application name";
       }
       leaf profile-status {
         type string;
         description
           "Status of the profile";
       }
     }
   }
   grouping cntr-profile-information-block {
     leaf active-hw-profile-name {
       type string;
       description
         "Active hardware profile name";
     }
     leaf cntr-profile-name {
       type string;
       description
         "Active counter profile name";
     }
     leaf cntr-profile-status {
       type string;
       description
         "Active counter profile status";
     }
     container cntr-profile-information-details {
       leaf active-hw-profile-name {
         type string;
         description
           "Active hardware profile name";
       }
       leaf cntr-profile-name {
         type string;
         description
           "Active counter profile name";
       }
       leaf cntr-profile-status {
         type string;
         description
           "Active counter profile status";
       }
     }
     list cntr-profile-status-per-app {
       key "cntr-app-name";
       leaf cntr-app-name {
         type string;
         description
           "Name of application";
       }
       leaf cntr4k {
         type uint64;
         description
           "Counter 4K engines";
       }
       leaf cntr8k {
         type uint64;
         description
           "Counter 8K engines";
       }
       leaf cntr16k {
         type uint64;
         description
           "Counter 16K engines";
       }
       leaf cntrext {
         type uint64;
         description
           "External counter";
       }
       leaf cntr-total {
         type uint64;
         description
           "Total counter";
       }
       leaf status-per-app {
         type string;
         description
           "Status of the per app counter profile";
       }
     }
     container cntr-profile-usage-details {
       leaf tot-alloc-cntr4k {
         type string;
         description
           "Total Allocated 4k counters";
       }
       leaf tot-alloc-cntr8k {
         type string;
         description
           "Total Allocated 8k counters";
       }
       leaf tot-alloc-cntr16k {
         type string;
         description
           "Total Allocated 16k counters";
       }
       leaf tot-alloc-cntrext {
         type string;
         description
           "Total Allocated ext counters";
       }
       leaf tot-free-cntr4k {
         type string;
         description
           "Total Free 4k counters";
       }
       leaf tot-free-cntr8k {
         type string;
         description
           "Total Free 8k counters";
       }
       leaf tot-free-cntr16k {
         type string;
         description
           "Total Free 16k counters";
       }
       leaf tot-free-cntrext {
         type string;
         description
           "Total Free ext counters";
       }
       leaf tot-eng-cntr4k {
         type string;
         description
           "Total Available 4k counters";
       }
       leaf tot-eng-cntr8k {
         type string;
         description
           "Total Available 8k counters";
       }
       leaf tot-eng-cntr16k {
         type string;
         description
           "Total Available 16k counters";
       }
       leaf tot-eng-cntrext {
         type string;
         description
           "Total Available ext counters";
       }
     }
   }
   grouping resource-monitor-summary-fpc-information-block {
     leaf rsmon-enabled {
       type string;
       description
         "State of Resource Monitoring";
     }
     leaf rsmon-load-throttle-enabled {
       type string;
       description
         "State of Resource Monitor throttling based on PFE load";
     }
     leaf rsmon-ifd-usage-update-enabled {
       type string;
       description
         "State of IFD usage update based on PFE, Subscriber load";
     }
     leaf heap-memory-threshold {
       type uint32;
       description
         "Heap memory threshold used for throttling subscribers and services";
     }
     leaf rtt-threshold {
       type uint32;
       description
         "RTT threshold used for throttling subscribers and services";
     }
     leaf ifl-counter-memory-threshold {
       type uint32;
       description
         "IFL Counter memory threshold used for throttling subscribers";
     }
     leaf filter-counter-memory-threshold {
       type uint32;
       description
         "Filter counter memory threshold used for throttling services";
     }
     leaf expansion-memory-threshold {
       type uint32;
       description
         "IFL Counter memory threshold used for throttling subscribers";
     }
     leaf cos-queue-threshold {
       type uint32;
       description
         "CoS queue threshold used for throttling subscribers";
     }
     leaf mfs-threshold {
       type uint32;
       description
         "Memory file system threshold used for throttling services";
     }
     leaf mfs-used-percent {
       type uint32;
       description
         "Memory file system used capacity";
     }
     leaf mfs-used-exceeded {
       type string;
       description
         "Memory file system used capacity exceeded set threshold";
     }
     leaf fpc-slot {
       type uint32;
       description
         "Line card slot number";
     }
     leaf pfe-num {
       type uint32;
       description
         "PFE number";
     }
     leaf used-heap-mem-percent {
       type uint32;
       description
         "Used Heap memory percentage on line card";
     }
     leaf used-heap-mem-exceeded {
       type string;
       description
         "Used Heap memory exceeded threshold on line card";
     }
     leaf used-heap-mem {
       type uint64;
       description
         "Used Heap memory on line card";
     }
     leaf used-cpu {
       type uint32;
       description
         "Used CPU percentage on line card";
     }
     leaf used-cpu-exceeded {
       type string;
       description
         "Used CPU  exceeded threshold on line card";
     }
     leaf avg-rtt {
       type uint32;
       description
         "Average Round trip time on line card";
     }
     leaf avg-rtt-sample {
       type uint32;
       description
         "Number of samples for Average RTT calculated";
     }
     leaf rtt {
       type uint32;
       description
         "Last Round trip time on line card";
     }
     leaf rtt-exceeded {
       type string;
       description
         "Round trip time on line card";
     }
     leaf max-session-rate-allowed {
       type uint32;
       description
         " Maximum number of login logout allowed on line card";
     }
     leaf max-session-credit-allowed {
       type uint32;
       description
         " Maximum number of credit sessions login allowed on line card";
     }
     leaf used-filter-counter {
       type uint32;
       description
         "Used PFE Filter Counter memory on line card";
     }
     leaf used-filter-counter-percent {
       type uint32;
       description
         "Used PFE Filter Counter memory percentage on line card";
     }
     leaf used-filter-counter-exceeded {
       type string;
       description
         "Used PFE Filter Counter memory exceeded threshold on line card";
     }
     leaf used-ifl-counter {
       type uint32;
       description
         "Used PFE IFL Counter memory on line card";
     }
     leaf used-ifl-counter-percent {
       type uint32;
       description
         "Used PFE IFL Counter memory percentage on line card";
     }
     leaf used-ifl-counter-exceeded {
       type string;
       description
         "Used PFE IFL Counter memory exceeded threshold on line card";
     }
     leaf used-expansion-memory {
       type uint32;
       description
         "Used PFE IFL Counter memory on line card";
     }
     leaf used-expansion-memory-percent {
       type uint32;
       description
         "Used PFE IFL Counter memory percentage on line card";
     }
     leaf used-expansion-memory-exceeded {
       type string;
       description
         "Used PFE IFL Counter memory exceeded threshold on line card";
     }
     leaf fpc-client-session-allowed {
       type string;
       description
         "FPC Client session throttle";
     }
     leaf fpc-client-session-denied-count {
       type uint32;
       description
         "FPC Client sessions denied";
     }
     leaf load-based-client-session-denied-count {
       type uint32;
       description
         "FPC Client sessions denied";
     }
     leaf fpc-service-session-allowed {
       type string;
       description
         "FPC Service session throttle";
     }
     leaf fpc-service-session-denied-count {
       type uint32;
       description
         "FPC Service sessions denied";
     }
     leaf load-based-service-session-denied-count {
       type uint32;
       description
         "FPC Service sessions denied";
     }
     leaf fpc-ifl-denied-count {
       type uint32;
       description
         "FPC IFL denied count";
     }
     list resource-monitor-summary-fpc-information-summary {
       leaf fpc-slot {
         type uint32;
         description
           "Line card slot number";
       }
       leaf used-heap-mem {
         type uint64;
         description
           "Used Heap memory on line card";
       }
       leaf used-heap-mem-percent {
         type uint32;
         description
           "Used Heap memory percentage on line card";
       }
       leaf used-heap-mem-exceeded {
         type string;
         description
           "Used Heap memory exceeded threshold on line card";
       }
       leaf fpc-client-session-allowed {
         type string;
         description
           "FPC Client session throttle";
       }
       leaf fpc-service-session-allowed {
         type string;
         description
           "FPC Service session throttle";
       }
       leaf max-session-rate-allowed {
         type uint32;
         description
           " Maximum number of login logout allowed on line card";
       }
       leaf max-session-credit-allowed {
         type uint32;
         description
           " Maximum number of credit sessions login allowed on line card";
       }
       leaf avg-rtt {
         type uint32;
         description
           "Average Round trip time on line card";
       }
       leaf avg-rtt-sample {
         type uint32;
         description
           "Number of samples for Average RTT calculated";
       }
       leaf rtt {
         type uint32;
         description
           "Last Round trip time on line card";
       }
       leaf rtt-exceeded {
         type string;
         description
           "Round trip time on line card";
       }
       leaf fpc-client-session-denied-count {
         type uint32;
         description
           "FPC Client sessions denied";
       }
       leaf load-based-client-session-denied-count {
         type uint32;
         description
           "FPC Client sessions denied";
       }
       leaf fpc-service-session-denied-count {
         type uint32;
         description
           "FPC Service sessions denied";
       }
       leaf load-based-service-session-denied-count {
         type uint32;
         description
           "FPC Service sessions denied";
       }
       leaf fpc-ifl-denied-count {
         type uint32;
         description
           "FPC IFL denied count";
       }
       list resource-monitor-summary-pfe-information-summary {
         leaf pfe-num {
           type uint32;
           description
             "PFE number";
         }
         leaf used-filter-counter {
           type uint32;
           description
             "Used PFE Filter Counter memory on line card";
         }
         leaf used-filter-counter-percent {
           type uint32;
           description
             "Used PFE Filter Counter memory percentage on line card";
         }
         leaf used-filter-counter-exceeded {
           type string;
           description
             "Used PFE Filter Counter memory exceeded threshold on line card";
         }
         leaf used-ifl-counter {
           type uint32;
           description
             "Used PFE IFL Counter memory on line card";
         }
         leaf used-ifl-counter-percent {
           type uint32;
           description
             "Used PFE IFL Counter memory percentage on line card";
         }
         leaf used-ifl-counter-exceeded {
           type string;
           description
             "Used PFE IFL Counter memory exceeded threshold on line card";
         }
         leaf used-expansion-memory {
           type uint32;
           description
             "Used PFE IFL Counter memory on line card";
         }
         leaf used-expansion-memory-percent {
           type uint32;
           description
             "Used PFE IFL Counter memory percentage on line card";
         }
         leaf used-expansion-memory-exceeded {
           type string;
           description
             "Used PFE IFL Counter memory exceeded threshold on line card";
         }
       }
       list resource-monitor-summary-cos-queue-utilization {
         leaf pfe-num {
           type uint32;
           description
             "PFE number";
         }
         leaf sched-block {
           type uint32;
           description
             "Scheduler number";
         }
         leaf used-cos-queues {
           type uint32;
           description
             "Used PFE CoS queues on line card";
         }
         leaf used-cos-queues-percentage {
           type uint32;
           description
             "Used PFE CoS queues percentage on line card";
         }
         leaf used-cos-queues-exceeded {
           type string;
           description
             "Used PFE CoS queues exceeded threshold on line card";
         }
       }
       container resource-monitor-summary-pfe-subsystem {
         leaf subsystem {
           type string;
           description
             "PFE subsystem name";
         }
       }
     }
   }
   grouping resource-monitor-detail-fpc-information-block {
     leaf rsmon-enabled {
       type string;
       description
         "State of Resource Monitoring";
     }
     leaf rsmon-load-throttle-enabled {
       type string;
       description
         "State of Resource Monitor throttling based on PFE load";
     }
     leaf rsmon-ifd-usage-update-enabled {
       type string;
       description
         "State of IFD usage update based on PFE, Subscriber load";
     }
     leaf heap-memory-threshold {
       type uint32;
       description
         "Heap memory threshold used for throttling subscribers and services";
     }
     leaf rtt-threshold {
       type uint32;
       description
         "RTT threshold used for throttling subscribers and services";
     }
     leaf ifl-counter-memory-threshold {
       type uint32;
       description
         "IFL Counter memory threshold used for throttling subscribers";
     }
     leaf filter-counter-memory-threshold {
       type uint32;
       description
         "Filter counter memory threshold used for throttling services";
     }
     leaf expansion-memory-threshold {
       type uint32;
       description
         "IFL Counter memory threshold used for throttling subscribers";
     }
     leaf cos-queue-threshold {
       type uint32;
       description
         "CoS queue threshold used for throttling subscribers";
     }
     leaf mfs-threshold {
       type uint32;
       description
         "Memory file system threshold used for throttling services";
     }
     leaf mfs-used-percent {
       type uint32;
       description
         "Memory file system used capacity";
     }
     leaf mfs-used-exceeded {
       type string;
       description
         "Memory file system used capacity exceeded set threshold";
     }
     leaf fpc-slot {
       type uint32;
       description
         "Line card slot number";
     }
     leaf pfe-num {
       type uint32;
       description
         "PFE number";
     }
     leaf subsystem-id {
       type uint32;
       description
         "PFE subsystem number";
     }
     leaf used-heap-mem {
       type uint64;
       description
         "Used Heap memory on line card";
     }
     leaf used-heap-mem-exceeded {
       type string;
       description
         "Used Heap memory exceeded threshold on line card";
     }
     leaf used-heap-mem-percent {
       type uint32;
       description
         "Used Heap memory percentage on line card";
     }
     leaf used-cpu {
       type uint32;
       description
         "Used CPU percentage on line card";
     }
     leaf used-cpu-exceeded {
       type string;
       description
         "Used CPU  exceeded threshold on line card";
     }
     leaf avg-rtt {
       type uint32;
       description
         "Average Round trip time on line card";
     }
     leaf avg-rtt-sample {
       type uint32;
       description
         "Number of samples for Average RTT calculated";
     }
     leaf rtt {
       type uint32;
       description
         "Last Round trip time on line card";
     }
     leaf rtt-exceeded {
       type string;
       description
         "Round trip time on line card";
     }
     leaf max-session-rate-allowed {
       type uint32;
       description
         " Maximum number of login logout allowed on line card";
     }
     leaf max-session-credit-allowed {
       type uint32;
       description
         " Maximum number of credit sessions login allowed on line card";
     }
     leaf resource-name {
       type string;
       description
         "Resource name";
     }
     leaf resource-counter {
       type uint32;
       description
         "Resource counter";
     }
     leaf resource-counter-percent {
       type uint32;
       description
         "Resource counter percent";
     }
     leaf resource-counter-exceeded {
       type string;
       description
         "Resource counter exceeded";
     }
     leaf resource-counter-unit {
       type string;
       description
         "Resource counter unit";
     }
     leaf fpc-client-session-allowed {
       type string;
       description
         "FPC Client session throttle";
     }
     leaf fpc-client-session-denied-count {
       type uint32;
       description
         "FPC Client sessions denied";
     }
     leaf load-based-client-session-denied-count {
       type uint32;
       description
         "FPC Client sessions denied";
     }
     leaf fpc-service-session-allowed {
       type string;
       description
         "FPC Service session throttle";
     }
     leaf fpc-service-session-denied-count {
       type uint32;
       description
         "FPC Service sessions denied";
     }
     leaf load-based-service-session-denied-count {
       type uint32;
       description
         "FPC Service sessions denied";
     }
     leaf fpc-ifl-denied-count {
       type uint32;
       description
         "FPC IFL denied count";
     }
     list resource-monitor-detail-fpc-information-detail {
       leaf fpc-slot {
         type uint32;
         description
           "Line card slot number";
       }
       leaf used-heap-mem {
         type uint64;
         description
           "Used Heap memory on line card";
       }
       leaf used-heap-mem-percent {
         type uint32;
         description
           "Used Heap memory percentage on line card";
       }
       leaf used-heap-mem-exceeded {
         type string;
         description
           "Used Heap memory exceeded threshold on line card";
       }
       leaf fpc-client-session-allowed {
         type string;
         description
           "FPC Client session throttle";
       }
       leaf fpc-service-session-allowed {
         type string;
         description
           "FPC Service session throttle";
       }
       leaf max-session-rate-allowed {
         type uint32;
         description
           " Maximum number of login logout allowed on line card";
       }
       leaf max-session-credit-allowed {
         type uint32;
         description
           " Maximum number of credit sessions login allowed on line card";
       }
       leaf avg-rtt {
         type uint32;
         description
           "Average Round trip time on line card";
       }
       leaf avg-rtt-sample {
         type uint32;
         description
           "Number of samples for Average RTT calculated";
       }
       leaf rtt {
         type uint32;
         description
           "Last Round trip time on line card";
       }
       leaf rtt-exceeded {
         type string;
         description
           "Round trip time on line card";
       }
       leaf fpc-client-session-denied-count {
         type uint32;
         description
           "FPC Client sessions denied";
       }
       leaf load-based-client-session-denied-count {
         type uint32;
         description
           "FPC Client sessions denied";
       }
       leaf fpc-service-session-denied-count {
         type uint32;
         description
           "FPC Service sessions denied";
       }
       leaf load-based-service-session-denied-count {
         type uint32;
         description
           "FPC Service sessions denied";
       }
       leaf fpc-ifl-denied-count {
         type uint32;
         description
           "FPC IFL denied count";
       }
       list resource-monitor-detail-pfe-information-detail {
         leaf resource-name {
           type string;
           description
             "Resource name";
         }
         leaf pfe-num {
           type uint32;
           description
             "PFE number";
         }
         leaf subsystem-id {
           type uint32;
           description
             "PFE subsystem number";
         }
         leaf resource-counter {
           type uint32;
           description
             "Resource counter";
         }
         leaf resource-counter-percent {
           type uint32;
           description
             "Resource counter percent";
         }
         leaf resource-counter-exceeded {
           type string;
           description
             "Resource counter exceeded";
         }
         leaf resource-counter-unit {
           type string;
           description
             "Resource counter unit";
         }
       }
       container resource-monitor-detail-pfe-subsystem {
         leaf subsystem {
           type string;
           description
             "PFE subsystem name";
         }
       }
     }
   }
   grouping resource-monitor-fpc-information-block {
     leaf fpc-slot {
       type uint32;
       description
         "Line card slot number";
     }
     leaf pfe-num {
       type uint32;
       description
         "PFE number";
     }
     leaf free-heap-memory-watermark {
       type uint32;
       description
         "Free heap memory watermark to monitor line card resource 
         utilization";
     }
     leaf free-nh-memory-watermark {
       type uint32;
       description
         "Free NH memory watermark to monitor line card resource utilization";
     }
     leaf free-filter-memory-watermark {
       type uint32;
       description
         "Free Filter memory watermark to monitor line card resource 
         utilization";
     }
     leaf free-encap-memory-watermark {
       type uint32;
       description
         "Encap memory threshold used for throttling services";
     }
     leaf free-heap-memory-rsmon-percent {
       type uint32;
       description
         "Used Heap memory percentage on line card for rsmon";
     }
     leaf free-heap-memory-rsmon-wm-exceeded {
       type string;
       description
         "Free heap memory is below watermark on line card";
     }
     leaf free-nh-memory-rsmon-percent {
       type uint32;
       description
         "Free PFE NH memory percentage on line card";
     }
     leaf free-nh-memory-rsmon-wm-exceeded {
       type string;
       description
         "Free NH memory is below watermark on line card";
     }
     leaf free-filter-memory-rsmon-percent {
       type uint32;
       description
         "Free PFE Filter memory percentage on line card";
     }
     leaf free-filter-memory-rsmon-wm-exceeded {
       type string;
       description
         "Free filter memory is below watermark on line card";
     }
     leaf free-encap-memory-rsmon-percent {
       type string;
       description
         "Free PFE Encap memory percentage on line card";
     }
     leaf free-encap-memory-rsmon-wm-exceeded {
       type string;
       description
         "Free Encap memory is below watermark on line card";
     }
     container resource-monitor-fpc-information-header {
       leaf free-heap-memory-watermark {
         type uint32;
         description
           "Free heap memory watermark to monitor line card resource 
           utilization";
       }
       leaf free-nh-memory-watermark {
         type uint32;
         description
           "Free NH memory watermark to monitor line card resource 
           utilization";
       }
       leaf free-filter-memory-watermark {
         type uint32;
         description
           "Free Filter memory watermark to monitor line card resource 
           utilization";
       }
     }
     container resource-monitor-fpc-information-summary {
       leaf fpc-slot {
         type uint32;
         description
           "Line card slot number";
       }
       leaf free-heap-memory-rsmon-percent {
         type uint32;
         description
           "Used Heap memory percentage on line card for rsmon";
       }
       leaf free-heap-memory-rsmon-wm-exceeded {
         type string;
         description
           "Free heap memory is below watermark on line card";
       }
       leaf rtt {
         type uint32;
         description
           "Last Round trip time on line card";
       }
       leaf avg-rtt {
         type uint32;
         description
           "Average Round trip time on line card";
       }
       leaf avg-rtt-sample {
         type uint32;
         description
           "Number of samples for Average RTT calculated";
       }
       list resource-monitor-fpc-pfe-information-summary {
         leaf pfe-num {
           type uint32;
           description
             "PFE number";
         }
         leaf free-encap-memory-rsmon-percent {
           type string;
           description
             "Free PFE Encap memory percentage on line card";
         }
         leaf free-encap-memory-rsmon-wm-exceeded {
           type string;
           description
             "Free Encap memory is below watermark on line card";
         }
         leaf free-nh-memory-rsmon-percent {
           type uint32;
           description
             "Free PFE NH memory percentage on line card";
         }
         leaf free-nh-memory-rsmon-wm-exceeded {
           type string;
           description
             "Free NH memory is below watermark on line card";
         }
         leaf free-filter-memory-rsmon-percent {
           type uint32;
           description
             "Free PFE Filter memory percentage on line card";
         }
         leaf free-filter-memory-rsmon-wm-exceeded {
           type string;
           description
             "Free filter memory is below watermark on line card";
         }
       }
     }
   }
   grouping resource-monitor-fpc-slot-information-block {
     leaf free-heap-memory-watermark {
       type uint32;
       description
         "Free heap memory watermark to monitor line card resource 
         utilization";
     }
     leaf free-nh-memory-watermark {
       type uint32;
       description
         "Free NH memory watermark to monitor line card resource utilization";
     }
     leaf free-filter-memory-watermark {
       type uint32;
       description
         "Free Filter memory watermark to monitor line card resource 
         utilization";
     }
     leaf fpc-slot {
       type uint32;
       description
         "Line card slot number";
     }
     leaf pfe-num {
       type uint32;
       description
         "PFE number";
     }
     leaf free-encap-memory-watermark {
       type uint32;
       description
         "Encap memory threshold used for throttling services";
     }
     leaf free-heap-memory-rsmon-percent {
       type uint32;
       description
         "Used Heap memory percentage on line card for rsmon";
     }
     leaf free-heap-memory-rsmon-wm-exceeded {
       type string;
       description
         "Free heap memory is below watermark on line card";
     }
     leaf free-nh-memory-rsmon-percent {
       type uint32;
       description
         "Free PFE NH memory percentage on line card";
     }
     leaf free-nh-memory-rsmon-wm-exceeded {
       type string;
       description
         "Free NH memory is below watermark on line card";
     }
     leaf free-filter-memory-rsmon-percent {
       type uint32;
       description
         "Free PFE Filter memory percentage on line card";
     }
     leaf free-filter-memory-rsmon-wm-exceeded {
       type string;
       description
         "Free filter memory is below watermark on line card";
     }
     leaf free-encap-memory-rsmon-percent {
       type string;
       description
         "Free PFE Encap memory percentage on line card";
     }
     leaf free-encap-memory-rsmon-wm-exceeded {
       type string;
       description
         "Free Encap memory is below watermark on line card";
     }
     container resource-monitor-fpc-slot-information-summary {
       leaf fpc-slot {
         type uint32;
         description
           "Line card slot number";
       }
       leaf free-heap-memory-rsmon-percent {
         type uint32;
         description
           "Used Heap memory percentage on line card for rsmon";
       }
       leaf free-heap-memory-rsmon-wm-exceeded {
         type string;
         description
           "Free heap memory is below watermark on line card";
       }
       leaf rtt {
         type uint32;
         description
           "Last Round trip time on line card";
       }
       leaf avg-rtt {
         type uint32;
         description
           "Average Round trip time on line card";
       }
       leaf avg-rtt-sample {
         type uint32;
         description
           "Number of samples for Average RTT calculated";
       }
       list resource-monitor-fpc-slot-pfe-information-summary {
         leaf pfe-num {
           type uint32;
           description
             "PFE number";
         }
         leaf free-encap-memory-rsmon-percent {
           type string;
           description
             "Free PFE Encap memory percentage on line card";
         }
         leaf free-encap-memory-rsmon-wm-exceeded {
           type string;
           description
             "Free Encap memory is below watermark on line card";
         }
         leaf free-nh-memory-rsmon-percent {
           type uint32;
           description
             "Free PFE NH memory percentage on line card";
         }
         leaf free-nh-memory-rsmon-wm-exceeded {
           type string;
           description
             "Free NH memory is below watermark on line card";
         }
         leaf free-filter-memory-rsmon-percent {
           type uint32;
           description
             "Free PFE Filter memory percentage on line card";
         }
         leaf free-filter-memory-rsmon-wm-exceeded {
           type string;
           description
             "Free filter memory is below watermark on line card";
         }
       }
     }
   }
   grouping resource-monitor-ifd-mapping-information-block {
     leaf pfe-num {
       type uint32;
       description
         "PFE number";
     }
     leaf sched-block {
       type uint32;
       description
         "Scheduler number";
     }
     leaf used-cos-queues {
       type uint32;
       description
         "Used PFE CoS queues on line card";
     }
     leaf used-cos-queues-percentage {
       type uint32;
       description
         "Used PFE CoS queues percentage on line card";
     }
     leaf used-cos-queues-exceeded {
       type string;
       description
         "Used PFE CoS queues exceeded threshold on line card";
     }
     leaf ifd1 {
       type string;
       description
         "Physical interface 1";
     }
     leaf ifd2 {
       type string;
       description
         "Physical interface 2";
     }
     leaf ifd3 {
       type string;
       description
         "Physical interface 3";
     }
     container resource-monitor-generic-string-with-break {
       leaf resource-monitor-generic-string {
         type string;
       }
     }
   }
   grouping subscribers-limit-level-block {
     container sub-limit-client-type {
       leaf client-type {
         type string;
         description
           "Limiting subscribers of client type";
       }
       leaf configured-limit {
         type uint32;
         description
           "Configured max allowed subscribers";
       }
       leaf current-count {
         type uint32;
         description
           "Current subscribers count";
       }
       leaf denied-count {
         type uint32;
         description
           "Denied subscribers count";
       }
       leaf configured-oversubscription-limit {
         type uint32;
         description
           "Configured max allowed oversubscription subscribers";
       }
       leaf current-oversubscription-count {
         type uint32;
         description
           "Current oversubscription subscribers count";
       }
       leaf denied-oversubscription-count {
         type uint32;
         description
           "Denied oversubscription subscribers count";
       }
     }
     list sub-limit-chassis-ext-chassis-level {
       leaf client-type {
         type string;
         description
           "Limiting subscribers of client type";
       }
       leaf configured-limit {
         type uint32;
         description
           "Configured max allowed subscribers";
       }
       leaf current-count {
         type uint32;
         description
           "Current subscribers count";
       }
       leaf denied-count {
         type uint32;
         description
           "Denied subscribers count";
       }
     }
     list sub-limit-chassis-ext-fpc-slot {
       leaf fpc-slot {
         type uint32;
         description
           "Line card slot number";
       }
     }
     list sub-limit-chassis-ext-fpc-level {
       leaf client-type {
         type string;
         description
           "Limiting subscribers of client type";
       }
       leaf configured-limit {
         type uint32;
         description
           "Configured max allowed subscribers";
       }
       leaf current-count {
         type uint32;
         description
           "Current subscribers count";
       }
       leaf denied-count {
         type uint32;
         description
           "Denied subscribers count";
       }
       leaf configured-oversubscription-limit {
         type uint32;
         description
           "Configured max allowed oversubscription subscribers";
       }
       leaf current-oversubscription-count {
         type uint32;
         description
           "Current oversubscription subscribers count";
       }
       leaf denied-oversubscription-count {
         type uint32;
         description
           "Denied oversubscription subscribers count";
       }
     }
     list sub-limit-chassis-ext-pic-slot {
       leaf pic-slot {
         type uint32;
         description
           "Pic slot number";
       }
     }
     list sub-limit-chassis-ext-pic-level {
       leaf client-type {
         type string;
         description
           "Limiting subscribers of client type";
       }
       leaf configured-limit {
         type uint32;
         description
           "Configured max allowed subscribers";
       }
       leaf current-count {
         type uint32;
         description
           "Current subscribers count";
       }
       leaf denied-count {
         type uint32;
         description
           "Denied subscribers count";
       }
     }
     list sub-limit-chassis-ext-port {
       leaf port {
         type uint32;
         description
           "Port number";
       }
     }
     list sub-limit-chassis-ext-port-level {
       leaf client-type {
         type string;
         description
           "Limiting subscribers of client type";
       }
       leaf configured-limit {
         type uint32;
         description
           "Configured max allowed subscribers";
       }
       leaf current-count {
         type uint32;
         description
           "Current subscribers count";
       }
       leaf denied-count {
         type uint32;
         description
           "Denied subscribers count";
       }
     }
     list sub-limit-fpc-ext-fpc-level {
       leaf client-type {
         type string;
         description
           "Limiting subscribers of client type";
       }
       leaf configured-limit {
         type uint32;
         description
           "Configured max allowed subscribers";
       }
       leaf current-count {
         type uint32;
         description
           "Current subscribers count";
       }
       leaf denied-count {
         type uint32;
         description
           "Denied subscribers count";
       }
       leaf configured-oversubscription-limit {
         type uint32;
         description
           "Configured max allowed oversubscription subscribers";
       }
       leaf current-oversubscription-count {
         type uint32;
         description
           "Current oversubscription subscribers count";
       }
       leaf denied-oversubscription-count {
         type uint32;
         description
           "Denied oversubscription subscribers count";
       }
     }
     list sub-limit-fpc-ext-pic-slot {
       leaf pic-slot {
         type uint32;
         description
           "Pic slot number";
       }
     }
     list sub-limit-fpc-ext-pic-level {
       leaf client-type {
         type string;
         description
           "Limiting subscribers of client type";
       }
       leaf configured-limit {
         type uint32;
         description
           "Configured max allowed subscribers";
       }
       leaf current-count {
         type uint32;
         description
           "Current subscribers count";
       }
       leaf denied-count {
         type uint32;
         description
           "Denied subscribers count";
       }
     }
     list sub-limit-fpc-ext-port {
       leaf port {
         type uint32;
         description
           "Port number";
       }
     }
     list sub-limit-fpc-ext-port-level {
       leaf client-type {
         type string;
         description
           "Limiting subscribers of client type";
       }
       leaf configured-limit {
         type uint32;
         description
           "Configured max allowed subscribers";
       }
       leaf current-count {
         type uint32;
         description
           "Current subscribers count";
       }
       leaf denied-count {
         type uint32;
         description
           "Denied subscribers count";
       }
     }
     list sub-limit-pic-ext-pic-level {
       leaf client-type {
         type string;
         description
           "Limiting subscribers of client type";
       }
       leaf configured-limit {
         type uint32;
         description
           "Configured max allowed subscribers";
       }
       leaf current-count {
         type uint32;
         description
           "Current subscribers count";
       }
       leaf denied-count {
         type uint32;
         description
           "Denied subscribers count";
       }
     }
     list sub-limit-pic-ext-port {
       leaf port {
         type uint32;
         description
           "Port number";
       }
       list sub-limit-pic-ext-port-level {
         leaf client-type {
           type string;
           description
             "Limiting subscribers of client type";
         }
         leaf configured-limit {
           type uint32;
           description
             "Configured max allowed subscribers";
         }
         leaf current-count {
           type uint32;
           description
             "Current subscribers count";
         }
         leaf denied-count {
           type uint32;
           description
             "Denied subscribers count";
         }
       }
     }
   }
   grouping system-firmware-information-block {
     list system-firmware {
       leaf firmware-name {
         type string;
         description
           "Name of this component";
       }
       leaf firmware-type {
         type string;
         description
           "Type of this component";
       }
       leaf firmware-tag {
         type int32;
         description
           "Multiple firmware per FRU delimiter";
       }
       leaf firmware-revision {
         type string;
         description
           "Firmware version for this component";
       }
       leaf firmware-revision-available {
         type string;
         description
           "Firmware version available on disk for this component";
       }
       leaf firmware-status {
         type string;
         description
           "Firmware status for this component";
       }
       container system-module {
         leaf firmware-name {
           type string;
           description
             "Name of this component";
         }
         container firmware-state {
           description
             "Firmware status per component type";
           leaf firmware-type {
             type string;
             description
               "Type of this component";
           }
           leaf firmware-status {
             type string;
             description
               "Firmware status for this component";
           }
         }
       }
       container system-sub-module-firmware-list {
         list system-sub-module-firmware {
           description
             "Firmware sub module";
           leaf firmware-name {
             type string;
             description
               "Name of this component";
           }
           leaf firmware-type {
             type string;
             description
               "Type of this component";
           }
           leaf firmware-tag {
             type int32;
             description
               "Multiple firmware per FRU delimiter";
           }
           leaf firmware-revision {
             type string;
             description
               "Firmware version for this component";
           }
           leaf firmware-revision-available {
             type string;
             description
               "Firmware version available on disk for this component";
           }
           leaf firmware-status {
             type string;
             description
               "Firmware status for this component";
           }
         }
       }
     }
   }
   grouping cdb-advertisement-block {
     leaf cdb-instances {
       type int32;
       description
         "CDB Instances";
     }
     leaf cdb-operations {
       type string;
       description
         "CDB Background Operations";
     }
     leaf cdb-autopaging {
       type string;
       description
         "CDB Autopaging";
     }
     leaf epl-pages {
       type string;
       description
         "EPL Pages";
     }
     leaf cdb-tnack-time {
       type int32;
       description
         "CDB Tnack Time";
     }
     leaf cdb-tnack-max-time {
       type int32;
       description
         "CDB Tnack Max Time";
     }
     leaf cdb-tnack-indicator {
       type int32;
       description
         "CDB Tnack Indicator";
     }
     leaf max-twi-write {
       type int32;
       description
         "CDB Max Twi Write ";
     }
     leaf cdb-command-process {
       type string;
       description
         "CDB Command Process";
     }
     leaf fw-dw-password {
       type string;
       description
         "FW download password type";
     }
     leaf abort-h {
       type string;
       description
         "Abort h";
     }
     leaf copy-h {
       type string;
       description
         "Copy h";
     }
     leaf skip-erased {
       type string;
       description
         "Skip erased";
     }
     leaf image-readback {
       type string;
       description
         "Image readback";
     }
     leaf command-payload-size {
       type int32;
       description
         "Start command payload size";
     }
     leaf erased-bytes {
       type int32;
       description
         "Erased bytes";
     }
     leaf firmware-blocksize {
       type int32;
       description
         "Max FW download block size";
     }
     leaf write-lpl-epl {
       type string;
       description
         "Write LPL/EPL";
     }
     leaf only-lpl-supported {
       type string;
       description
         "Only LPL supported";
     }
     leaf read-back-lpl-epl {
       type string;
       description
         "Readback LPL/EPL";
     }
     leaf hitless-mode {
       type string;
       description
         "Hitless mode";
     }
     leaf cdb-start-max-time {
       type int32;
       description
         "CDB start max time (ms)";
     }
     leaf cdb-abort-max-time {
       type int32;
       description
         "CDB abort max time (ms)";
     }
     leaf cdb-write-max-time {
       type int32;
       description
         "CDB write max time (ms)";
     }
     leaf cdb-complete-max-time {
       type int32;
       description
         "CDB complete max time (ms)";
     }
     leaf cdb-copy-max-time {
       type int32;
       description
         "CDB copy max time (ms)";
     }
     leaf image-a {
       type string;
       description
         "Image A";
     }
     leaf image-b {
       type string;
       description
         "Image B";
     }
     leaf image-a-version {
       type string;
       description
         "Image A Version";
     }
     leaf image-a-build {
       type string;
       description
         "Image A Build";
     }
     leaf image-a-extra {
       type string;
       description
         "Image A Extra";
     }
     leaf image-b-version {
       type string;
       description
         "Image B Version";
     }
     leaf image-b-build {
       type string;
       description
         "Image B Build";
     }
     leaf image-b-extra {
       type string;
       description
         "Image B Extra";
     }
     leaf factory-image-version {
       type string;
       description
         "Factory Image Version";
     }
     leaf factory-image-build {
       type string;
       description
         "Factory Image Build";
     }
     leaf factory-image-extra {
       type string;
       description
         "Factory Image Extra";
     }
   }
   grouping system-golden-firmware-information-block {
     list system-golden-firmware {
       description
         "Golden firmware information";
       leaf firmware-name {
         type string;
         description
           "Name of this component";
       }
       leaf firmware-type {
         type string;
         description
           "Type of this component";
       }
       leaf golden-revision {
         type string;
         description
           "Golden firmware version for this component";
       }
       container system-sub-module-golden-firmware-list {
         list system-sub-module-golden-firmware {
           description
             "Golden Firmware";
           leaf firmware-name {
             type string;
             description
               "Name of this component";
           }
           leaf firmware-type {
             type string;
             description
               "Type of this component";
           }
           leaf golden-revision {
             type string;
             description
               "Golden firmware version for this component";
           }
         }
       }
     }
   }
   grouping system-detail-firmware-information-block {
     list system-detail-firmware {
       description
         "All firmware revision information";
       leaf firmware-detail-name {
         type string;
         description
           "Name of this component";
       }
       leaf firmware-detail-type {
         type string;
         description
           "Type of this component";
       }
       leaf firmware-detail-tag {
         type int32;
         description
           "Multiple firmware per FRU delimiter";
       }
       leaf firmware-revision-detail {
         type string;
         description
           "Firmware version for this component";
       }
       leaf firmware-revision-detail-primary {
         type string;
         description
           "Primary firmware version for this component";
       }
       leaf firmware-revision-detail-golden {
         type string;
         description
           "Golden/Recovery firmware version for this component";
       }
       leaf firmware-revision-detail-available {
         type string;
         description
           "Firmware version available on disk for this component";
       }
       container system-sub-module-detail-firmware-list {
         list system-sub-module-detail-firmware {
           description
             "All Firmware versions";
           leaf firmware-detail-name {
             type string;
             description
               "Name of this component";
           }
           leaf firmware-detail-type {
             type string;
             description
               "Type of this component";
           }
           leaf firmware-detail-tag {
             type int32;
             description
               "Multiple firmware per FRU delimiter";
           }
           leaf firmware-revision-detail {
             type string;
             description
               "Firmware version for this component";
           }
           leaf firmware-revision-detail-primary {
             type string;
             description
               "Primary firmware version for this component";
           }
           leaf firmware-revision-detail-golden {
             type string;
             description
               "Golden/Recovery firmware version for this component";
           }
           leaf firmware-revision-detail-available {
             type string;
             description
               "Firmware version available on disk for this component";
           }
         }
       }
     }
   }
   grouping fm-appstatus-information-block {
     list fm-appinfo {
       leaf fm-appname {
         type string;
       }
       leaf fm-frutype {
         type string;
       }
       leaf fm-fruslot {
         type string;
       }
       leaf fm-appstatus {
         type string;
       }
       leaf fm-appreason {
         type string;
       }
     }
   }
   grouping filesystem-encryption-status-block {
     leaf node-re-name {
       type string;
       description
         "Hostname of the Routing Engine";
     }
     leaf encryption-status {
       type string;
       description
         "Filesystem Encryption Status";
     }
   }
   grouping memory-profiling-status-block {
     leaf memory-profiling-status-results {
       type string;
       description
         "Memory profiling status";
     }
   }
   grouping system-ztp-info-block {
     leaf ztp-current-state {
       type string;
     }
     leaf ztp-intf {
       type string;
     }
     leaf ztp-dhcp-version {
       type string;
     }
     leaf ztp-host-name {
       type string;
     }
     leaf ztp-ftpserver-ip {
       type string;
     }
     leaf ztp-router-ip {
       type string;
     }
     leaf ztp-logservers-ip {
       type string;
     }
     leaf ztp-ntpservers-ip {
       type string;
     }
     leaf ztp-image-file-name {
       type string;
     }
     leaf ztp-image-file-type {
       type string;
     }
     leaf ztp-image-url {
       type string;
     }
     leaf ztp-image-status {
       type string;
     }
     leaf ztp-alt-image-file-name {
       type string;
     }
     leaf ztp-alt-image-url {
       type string;
     }
     leaf ztp-alt-image-status {
       type string;
     }
     leaf ztp-transfer-mode {
       type string;
     }
     leaf ztp-config-file-name {
       type string;
     }
     leaf ztp-config-url {
       type string;
     }
     leaf ztp-config-status {
       type string;
     }
     leaf ztp-pre-script-file-name {
       type string;
     }
     leaf ztp-pre-script-url {
       type string;
     }
     leaf ztp-pre-script-status {
       type string;
     }
     leaf ztp-ztp-retry-count {
       type string;
     }
     leaf ztp-dhcp-retry-count {
       type string;
     }
     leaf ztp-boot-file-name {
       type string;
     }
     leaf ztp-boot-file-type {
       type string;
     }
     leaf ztp-boot-file-url {
       type string;
     }
     leaf ztp-boot-file-status {
       type string;
     }
     leaf ztp-platform-default {
       type string;
     }
     leaf ztp-boot-mode {
       type string;
     }
     list ztp-state-history {
       container ztp-state-history-entry {
         leaf ztp-state-entry-timestamp {
           type string;
         }
         leaf ztp-state-entry-info {
           type string;
         }
       }
     }
   }
   grouping system-software-list-block {
     container node {
       leaf node-name {
         type string;
       }
       leaf snapshot-message {
         type string;
       }
       leaf boot-device-type {
         type string;
       }
       leaf boot-device {
         type string;
       }
       container version-list {
         leaf current-version {
           type string;
         }
         leaf current-version-timestamp {
           type string;
         }
         leaf current-version-type {
           type string;
         }
         leaf nextboot-version {
           type string;
         }
         leaf nextboot-version-timestamp {
           type string;
         }
         leaf nextboot-version-type {
           type string;
         }
         leaf rollback-version {
           type string;
         }
         leaf rollback-version-timestamp {
           type string;
         }
         leaf rollback-version-type {
           type string;
         }
         container current-version-external-package-information {
           container package-information {
             list package-item {
               leaf package-name {
                 type string;
               }
               leaf package-version {
                 type string;
               }
             }
           }
           container external-package-information {
             list external-package-item {
               leaf external-package-name {
                 type string;
               }
               leaf external-package-version {
                 type string;
               }
               list content {
                 leaf content-name {
                   type string;
                 }
                 leaf content-type {
                   type string;
                 }
               }
             }
           }
         }
         container nextboot-version-external-package-information {
           container package-information {
             list package-item {
               leaf package-name {
                 type string;
               }
               leaf package-version {
                 type string;
               }
             }
           }
           container external-package-information {
             list external-package-item {
               leaf external-package-name {
                 type string;
               }
               leaf external-package-version {
                 type string;
               }
               list content {
                 leaf content-name {
                   type string;
                 }
                 leaf content-type {
                   type string;
                 }
               }
             }
           }
         }
         container rollback-version-external-package-information {
           container package-information {
             list package-item {
               leaf package-name {
                 type string;
               }
               leaf package-version {
                 type string;
               }
             }
           }
           container external-package-information {
             list external-package-item {
               leaf external-package-name {
                 type string;
               }
               leaf external-package-version {
                 type string;
               }
               list content {
                 leaf content-name {
                   type string;
                 }
                 leaf content-type {
                   type string;
                 }
               }
             }
           }
         }
       }
       container other-versions-list {
         list version-information {
           leaf other-versions {
             type string;
           }
           leaf other-versions-timestamp {
             type string;
           }
           leaf other-versions-type {
             type string;
           }
           container package-information {
             list package-item {
               leaf package-name {
                 type string;
               }
               leaf package-version {
                 type string;
               }
             }
           }
           container external-package-information {
             list external-package-item {
               leaf external-package-name {
                 type string;
               }
               leaf external-package-version {
                 type string;
               }
               list content {
                 leaf content-name {
                   type string;
                 }
                 leaf content-type {
                   type string;
                 }
               }
             }
           }
         }
       }
     }
   }
   grouping system-add-restart-information-block {
     leaf system-add-restart-logs {
       type string;
     }
   }
   grouping system-hitless-reboot-information-block {
     leaf system-hitless-reboot-logs {
       type string;
     }
   }
   grouping system-applications-info-block {
     list system-applications-info-entry {
       key "system-application-name";
       leaf system-application-name {
         type string;
       }
       leaf system-application-node {
         type string;
       }
       leaf system-application-state {
         type string;
       }
       leaf system-application-weight {
         type uint32;
       }
       leaf system-application-zkid {
         type string;
       }
       container system-application-memory {
         leaf system-application-vmsize-kb {
           type uint64;
         }
         leaf system-application-vmrss-kb {
           type uint64;
         }
         leaf system-application-vmswap-kb {
           type uint64;
         }
       }
       container system-application-processor {
         leaf system-application-cpu-time {
           type decimal64 {
             fraction-digits 9;
           }
         }
         leaf system-application-cpu-utilization {
           type decimal64 {
             fraction-digits 9;
           }
         }
       }
       container system-application-pid-epochid-list {
         list system-application-pid-epochid {
           leaf system-application-pid {
             type string;
           }
           leaf system-application-epochid {
             type string;
           }
           leaf system-application-pid-topic {
             type string;
           }
           leaf system-application-pid-state {
             type string;
           }
         }
       }
       container system-application-config {
         leaf system-application-config-id {
           type string;
         }
         container system-application-config-meta {
           leaf system-application-binpath {
             type string;
           }
           leaf system-application-logfile {
             type string;
           }
           leaf system-application-workingdir {
             type string;
           }
           leaf system-application-productionset {
             type string;
           }
           leaf system-application-sysmanmanaged {
             type string;
           }
           leaf system-application-typeevo {
             type string;
           }
           leaf system-application-relatedapps {
             type string;
           }
         }
         container system-application-config-resource {
           leaf system-application-allnodes {
             type string;
           }
           leaf system-application-max-instances {
             type uint32;
           }
           leaf system-application-max-instances-per-node {
             type uint32;
           }
           leaf system-application-app-suite {
             type string;
           }
           leaf system-application-max-memory {
             type string;
           }
           leaf system-application-boot-priority {
             type uint32;
           }
           leaf system-application-ignore-app-ready {
             type string;
           }
           leaf system-application-run-on-startup {
             type string;
           }
           container system-application-node-attributes {
             list system-application-node-attributes-entry {
               leaf system-application-node-attribute-name {
                 type string;
               }
               leaf system-application-node-attribute-runtime-name {
                 type string;
               }
               leaf system-application-node-attributes-entry-header {
                 type empty;
               }
             }
           }
         }
         container system-application-config-app-failure {
           leaf system-application-failure-alarm-color {
             type string;
           }
           leaf system-application-failure-alarm-id {
             type uint32;
           }
           leaf system-application-failure-restart-node {
             type string;
           }
           leaf system-application-failure-mark-node-spare {
             type string;
           }
           leaf system-application-failure-exec {
             type string;
           }
         }
         container system-application-config-upgrade {
           leaf system-application-upgrade-parallely {
             type string;
           }
           leaf system-application-prepare-to-upgrade-notify {
             type string;
           }
           leaf system-application-unprepare-to-upgrade-notify {
             type string;
           }
           leaf system-application-upgrade-abort-capable {
             type string;
           }
           leaf system-application-node-upgrade-done-notify {
             type string;
           }
           leaf system-application-system-upgrade-done-notify {
             type string;
           }
           leaf system-application-upgrade-style {
             type string;
           }
           leaf system-application-upgrade-hw-sync {
             type string;
           }
           leaf system-application-upgrade-wait-for-sw-sync {
             type string;
           }
           leaf system-application-prepare-for-impact-of-other-app-upgrade {
             type string;
           }
           leaf system-application-upgrade-prepare-to-upgrade-final {
             type string;
           }
           leaf system-application-unprepare-for-impact-of-other-app-upgrade {
             type string;
           }
           leaf system-application-upgrade-exits-on-prep-final {
             type string;
           }
           leaf system-application-upgrade-weight {
             type uint32;
           }
           leaf system-application-upgrade-restart-node {
             type string;
           }
         }
         container system-application-config-app-exit {
           leaf system-application-exit-restart {
             type string;
           }
           leaf system-application-exit-restart-prevent-exit-status {
             type string;
           }
           leaf system-application-exit-restart-node {
             type string;
           }
           leaf system-application-exit-mark-node-spare {
             type string;
           }
         }
         container system-application-config-artifact {
           leaf system-application-fail-tags {
             type string;
           }
           leaf system-application-check-tags {
             type string;
           }
         }
       }
       leaf system-application-description {
         type string;
       }
       leaf system-application-loadstate {
         type string;
       }
       leaf system-application-activestate {
         type string;
       }
       leaf system-application-mainpid {
         type uint64;
       }
       leaf system-application-cmdline {
         type string;
       }
     }
   }
   grouping application-error-info-block {
     list application-error-info-entry {
       leaf node-name {
         type string;
         description
           "Name of node where error occurred";
       }
       leaf application-name {
         type string;
         description
           "Name of application";
       }
       leaf total-error-count {
         type uint32;
         description
           "Error count";
       }
       leaf error-obj-producer {
         type string;
         description
           "Name of error Producer module";
       }
       container error-object-guids {
         leaf-list error-object-guid {
           type string;
           description
             "Error object Guid";
         }
       }
       leaf error-obj-id {
         type uint32;
         description
           "Error ID";
       }
       leaf error-obj-severity {
         type string;
         description
           "Severity of error";
       }
       leaf error-obj-guid {
         type string;
         description
           "Guid of object with error";
       }
       leaf error-obj-description {
         type string;
         description
           "Human readable description of error";
       }
       leaf error-obj-module {
         type string;
         description
           "Name of error reporting module";
       }
       leaf error-obj-name {
         type string;
         description
           "Name of object which has error";
       }
       leaf error-obj-parent-name {
         type string;
         description
           "Error parent name info";
       }
       leaf error-timestamp {
         type string;
         description
           "Time at which error was reported";
       }
       leaf error-item-uri {
         type string;
         description
           "URI of error aggregation";
       }
       leaf error-item-category {
         type string;
         description
           "Category of error aggregation";
       }
       leaf error-item-scope {
         type string;
         description
           "Scope of error aggregation";
       }
     }
   }
   grouping healthz-detail-information-block {
     list healthz-info {
       description
         "Health information for each component";
       container healthz-group {
         leaf list-index {
           type int32;
           description
             "List index of unhealthy events";
         }
         leaf component-name {
           type string;
           description
             "Producer daemon for health-event";
         }
         leaf health-status {
           type string;
           description
             "Health status of a component";
         }
         leaf unhealthy-count {
           type int32;
           description
             "Number of unhealthy events";
         }
         leaf unhealthy-time {
           type uint64;
           description
             "Time of last unhealthy events";
         }
         leaf artifact-name {
           type string;
           description
             "Artifact generated for a particular component";
         }
         leaf artifact-path {
           type string;
           description
             "Artifact stored in this path";
         }
         leaf artifact-size {
           type uint64;
           description
             "File size of artifact generated";
         }
         leaf artifact-creation-time {
           type uint64;
           description
             "Time of the health-event creation";
         }
         leaf artifact-deletion-time {
           type uint64;
           description
             "Time of the health-event deletion";
         }
       }
     }
   }
   grouping kfw-information-block {
     leaf v4-matches {
       type string;
     }
     leaf v4-actions {
       type string;
     }
     leaf v6-matches {
       type string;
     }
     leaf v6-actions {
       type string;
     }
   }
   grouping system-nodes-info-block {
     list system-nodes-info-entry {
       leaf system-node-info-node-name {
         type string;
       }
       leaf system-node-info-node-id {
         type uint64;
       }
       leaf system-node-info-node-nonce {
         type uint64;
       }
       leaf system-node-info-node-status {
         type string;
       }
       leaf system-node-info-no-node-attributes {
         type empty;
       }
       container system-node-info-node-attributes-list {
         leaf-list system-node-info-node-attribute {
           type string;
         }
       }
     }
   }
   grouping system-node-attributes-info-block {
     list system-node-attributes-info-entry {
       leaf system-node-attribute-name {
         type string;
       }
       container system-node-redundancy-info-entry {
         leaf system-node-redundancy-num-active {
           type uint32;
         }
       }
       container system-node-active-node-list {
         leaf-list system-node-active-node {
           type string;
         }
       }
       container system-node-spare-node-list {
         leaf-list system-node-spare-node {
           type string;
         }
       }
     }
   }
 }
