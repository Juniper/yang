/*
 * Copyright (c) 2026 Juniper Networks, Inc.
 * All rights reserved.
 */
 module junos-rpc-subscribers {
   namespace "http://yang.juniper.net/junos/rpc/subscribers";

   prefix subscribers;

   import junos-common-types {
     prefix jt;
     revision-date 2026-01-01;
   }

   organization "Juniper Networks, Inc.";

   contact "yang-support@juniper.net";

   description "Junos RPC YANG module for subscribers command(s)";

   revision 2026-01-01 {
     description "Junos: 26.2R1.7-EVO";
   }

   rpc get-subscribers {
     description "Show subscriber information";
     input {
       leaf address {
         description "IPv4 or IPv6 address of subscriber";
         type string;
       }
       leaf interface {
         description "Interface name, or with wildcards (e.g. fe-0/0/*, fe-0/*/*)";
         type union {
           type jt:interface-wildcard;
           type string {
             pattern "<.*>|$.*";
           }
         }
       }
       leaf physical-interface {
         description "Physical Interface name";
         type union {
           type jt:interface-wildcard;
           type string {
             pattern "<.*>|$.*";
           }
         }
       }
       leaf user-name {
         description "User name of subscriber";
         type string;
       }
       leaf logical-system {
         description "Logical system where subscriber resides";
         type string;
       }
       leaf routing-instance {
         description "Routing instance where subscriber resides";
         type string;
       }
       leaf profile-name {
         description "Profile with which subscriber has been activated";
         type string {
           length "1 .. 80";
         }
       }
       leaf agent-circuit-identifier {
         description "Display summary for specified agent circuit identifier";
         type string;
       }
       leaf agent-remote-identifier {
         description "Display summary for specified agent remote identifier";
         type string;
       }
       leaf aci-interface-set-name {
         description "Display summary for specified ACI interface set";
         type string;
       }
       leaf aggregation-interface-set-name {
         description "Display summary for specified aggregation interface set";
         type string;
       }
       leaf stacked-vlan-id {
         description "Stacked VLAN identifier of subscriber";
         type union {
           type string {
             pattern "<.*>|$.*";
           }
           type uint16 {
             range "1 .. 4094";
           }
         }
       }
       leaf vlan-id {
         description "VLAN identifier of subscriber";
         type union {
           type string {
             pattern "<.*>|$.*";
           }
           type uint16 {
             range "1 .. 4094";
           }
         }
       }
       leaf vpi {
         description "ATM VPI of subscriber";
         type union {
           type string {
             pattern "<.*>|$.*";
           }
           type uint16 {
             range "0 .. 255";
           }
         }
       }
       leaf vci {
         description "ATM VCI of subscriber";
         type union {
           type string {
             pattern "<.*>|$.*";
           }
           type uint16 {
             range "0 .. 65535";
           }
         }
       }
       leaf id {
         description "Identifier of subscriber";
         type union {
           type uint64;
           type string {
             pattern "<.*>|$.*";
           }
         }
       }
       leaf accounting-statistics {
         description "Display accounting statistics for subscriber";
         type empty;
       }
       leaf mac-address {
         description "MAC address of subscriber";
         type jt:mac-addr;
       }
       leaf client-type {
         description "Client type of subscriber";
         type enumeration {
           enum "dhcp" {
             description "DHCP clients only";
           }
           enum "vlan" {
             description "VLAN clients only";
           }
           enum "ppp" {
             description "PPP clients only";
           }
           enum "pppoe" {
             description "PPPoE clients only";
           }
           enum "l2tp" {
             description "L2TP clients only";
           }
           enum "static" {
             description "Static clients only";
           }
           enum "vpls-pw" {
             description "VPLS-PW clients only";
           }
           enum "mlppp" {
             description "MLPPP clients only";
           }
           enum "xauth" {
             description "XAuth clients only";
           }
           enum "fwauth" {
             description "FwAuth clients only";
           }
           enum "dot1x" {
             description "Dot1x clients only";
           }
           enum "essm" {
             description "ESSM clients only";
           }
           enum "l2ckt-pw" {
             description "L2CKT-PW clients only";
           }
           enum "gre" {
             description "GRE clients only";
           }
           enum "vlan-extm" {
             description "VLAN externally managed clients only";
           }
           enum "vlan-oob" {
             description "VLAN out-of-band clients only";
           }
           enum "dyn-ip" {
             description "Dynamic IP clients only";
           }
           enum "hag-tunnel" {
             description "HAG tunnel clients only";
           }
           enum "hag-bundle" {
             description "HAG bundle clients only";
           }
           enum "fixed-wireless-access" {
             description "Fixed Wireless Access clients only";
           }
           enum "nat" {
             description "NAT clients only";
           }
           enum "l2bsa-extm" {
             description "L2BSA externally managed clients only";
           }
         }
       }
       leaf subscriber-state {
         description "State of subscriber";
         type enumeration {
           enum "init" {
             description "INIT state only";
           }
           enum "configured" {
             description "CONFIGURED state only";
           }
           enum "active" {
             description "ACTIVE state only";
           }
           enum "terminating" {
             description "TERMINATING state only";
           }
           enum "terminated" {
             description "TERMINATED state only";
           }
         }
       }
       leaf display {
         default "terse";
         type enumeration {
           enum "terse" {
             description "Display terse output";
           }
           enum "detail" {
             description "Display detailed output";
           }
           enum "extensive" {
             description "Display extensive output";
           }
           enum "count" {
             description "Display number of subscribers";
           }
         }
       }
     }
     output {
       choice output-tags {
         case actual-tag {
           container subscribers-information {
             uses subscribers-information-block;
           }
         }
         case multichassis-tag {
           container multi-routing-engine-results {
             list multi-routing-engine-item {
               leaf re-name {
                 type string;
               }
               choice output-tags {
                 case actual-tag {
                   container subscribers-information {
                     uses subscribers-information-block;
                   }
                 }
               }
             }
           }
         }
       }
     }
   }
   rpc get-subscriber-license-usage {
     description "Display last 48 hours License usage";
     output {
       choice output-tags {
         case actual-tag {
           container subscriber-lic-information {
             uses subscriber-lic-information-block;
           }
         }
         case multichassis-tag {
           container multi-routing-engine-results {
             list multi-routing-engine-item {
               leaf re-name {
                 type string;
               }
               choice output-tags {
                 case actual-tag {
                   container subscriber-lic-information {
                     uses subscriber-lic-information-block;
                   }
                 }
               }
             }
           }
         }
       }
     }
   }
   rpc get-subscribers-summary {
     description "Display subscriber summary";
     input {
       leaf logical-system {
         description "Display summary for specified logical system";
         type string;
       }
       leaf routing-instance {
         description "Display summary for specified routing instance";
         type string;
       }
       leaf pic {
         description "Display full subscriber pic summary";
         type empty;
       }
       leaf slot {
         description "Display full subscriber slot summary";
         type empty;
       }
       leaf all {
         description "Display full subscriber summary";
         type empty;
       }
     }
     output {
       choice output-tags {
         case actual-tag {
           container subscribers-summary-information {
             uses subscribers-summary-information-block;
           }
         }
         case multichassis-tag {
           container multi-routing-engine-results {
             list multi-routing-engine-item {
               leaf re-name {
                 type string;
               }
               choice output-tags {
                 case actual-tag {
                   container subscribers-summary-information {
                     uses subscribers-summary-information-block;
                   }
                 }
               }
             }
           }
         }
       }
     }
   }
   rpc get-subscribers-summary-physical-interface {
     description "Physical Interface name";
     input {
       leaf physical-interface-name {
         description "Physical Interface name";
         type union {
           type jt:interface-wildcard;
           type string {
             pattern "<.*>|$.*";
           }
         }
         mandatory true;
       }
     }
     output {
       choice output-tags {
         case actual-tag {
           container subscribers-summary-information {
             uses subscribers-summary-information-block;
           }
         }
         case multichassis-tag {
           container multi-routing-engine-results {
             list multi-routing-engine-item {
               leaf re-name {
                 type string;
               }
               choice output-tags {
                 case actual-tag {
                   container subscribers-summary-information {
                     uses subscribers-summary-information-block;
                   }
                 }
               }
             }
           }
         }
       }
     }
   }
   rpc get-subscribers-summary-phy-int-user-plane {
     description "Display subscriber summary per user-plane";
     input {
       leaf up-name {
         description "Name of the user plane instance";
         type string;
         mandatory true;
       }
     }
     output {
       choice output-tags {
         case actual-tag {
           container subscribers-summary-information {
             uses subscribers-summary-information-block;
           }
         }
         case multichassis-tag {
           container multi-routing-engine-results {
             list multi-routing-engine-item {
               leaf re-name {
                 type string;
               }
               choice output-tags {
                 case actual-tag {
                   container subscribers-summary-information {
                     uses subscribers-summary-information-block;
                   }
                 }
               }
             }
           }
         }
       }
     }
   }
   rpc get-subscribers-summary-phy-int-sgrp {
     description "Display subscriber summary per SGRP";
     input {
       leaf sgrp-name {
         description "Name of the subscriber group";
         type string;
         mandatory true;
       }
     }
     output {
       choice output-tags {
         case actual-tag {
           container subscribers-summary-information {
             uses subscribers-summary-information-block;
           }
         }
         case multichassis-tag {
           container multi-routing-engine-results {
             list multi-routing-engine-item {
               leaf re-name {
                 type string;
               }
               choice output-tags {
                 case actual-tag {
                   container subscribers-summary-information {
                     uses subscribers-summary-information-block;
                   }
                 }
               }
             }
           }
         }
       }
     }
   }
   rpc get-subscribers-port-summary {
     description "Display full subscriber port summary";
     input {
       leaf extensive {
         description "Display full subscriber port detail";
         type empty;
       }
       leaf port-name {
         description "Port-name in up:<up-name>:<ifd-name> format";
         type string;
         mandatory true;
       }
     }
     output {
       choice output-tags {
         case actual-tag {
           container subscribers-summary-information {
             uses subscribers-summary-information-block;
           }
         }
         case multichassis-tag {
           container multi-routing-engine-results {
             list multi-routing-engine-item {
               leaf re-name {
                 type string;
               }
               choice output-tags {
                 case actual-tag {
                   container subscribers-summary-information {
                     uses subscribers-summary-information-block;
                   }
                 }
               }
             }
           }
         }
       }
     }
   }
   rpc get-subscribers-summary-port-user-plane {
     description "Display subscriber summary per user-plane";
     input {
       leaf up-name {
         description "Name of the user plane instance";
         type string;
         mandatory true;
       }
     }
     output {
       choice output-tags {
         case actual-tag {
           container subscribers-summary-information {
             uses subscribers-summary-information-block;
           }
         }
         case multichassis-tag {
           container multi-routing-engine-results {
             list multi-routing-engine-item {
               leaf re-name {
                 type string;
               }
               choice output-tags {
                 case actual-tag {
                   container subscribers-summary-information {
                     uses subscribers-summary-information-block;
                   }
                 }
               }
             }
           }
         }
       }
     }
   }
   rpc get-subscribers-summary-port-sgrp {
     description "Display subscriber summary per SGRP";
     input {
       leaf sgrp-name {
         description "Name of the subscriber group";
         type string;
         mandatory true;
       }
     }
     output {
       choice output-tags {
         case actual-tag {
           container subscribers-summary-information {
             uses subscribers-summary-information-block;
           }
         }
         case multichassis-tag {
           container multi-routing-engine-results {
             list multi-routing-engine-item {
               leaf re-name {
                 type string;
               }
               choice output-tags {
                 case actual-tag {
                   container subscribers-summary-information {
                     uses subscribers-summary-information-block;
                   }
                 }
               }
             }
           }
         }
       }
     }
   }
   rpc get-subscribers-summary-bbdevice-user-plane {
     description "Display subscriber summary per user-plane";
     input {
       leaf up-name {
         description "Name of the user plane instance";
         type string;
         mandatory true;
       }
     }
     output {
       choice output-tags {
         case actual-tag {
           container subscribers-summary-information {
             uses subscribers-summary-information-block;
           }
         }
         case multichassis-tag {
           container multi-routing-engine-results {
             list multi-routing-engine-item {
               leaf re-name {
                 type string;
               }
               choice output-tags {
                 case actual-tag {
                   container subscribers-summary-information {
                     uses subscribers-summary-information-block;
                   }
                 }
               }
             }
           }
         }
       }
     }
   }
   rpc get-subscribers-summary-bbdevice-sgrp {
     description "Display subscriber summary per SGRP";
     input {
       leaf sgrp-name {
         description "Name of the subscriber group";
         type string;
         mandatory true;
       }
     }
     output {
       choice output-tags {
         case actual-tag {
           container subscribers-summary-information {
             uses subscribers-summary-information-block;
           }
         }
         case multichassis-tag {
           container multi-routing-engine-results {
             list multi-routing-engine-item {
               leaf re-name {
                 type string;
               }
               choice output-tags {
                 case actual-tag {
                   container subscribers-summary-information {
                     uses subscribers-summary-information-block;
                   }
                 }
               }
             }
           }
         }
       }
     }
   }
   rpc get-subscribers-summary-user-plane {
     description "Display subscriber summary per user-plane";
     input {
       leaf user-plane-name {
         description "Name of the user plane instance";
         type string;
       }
     }
     output {
       choice output-tags {
         case actual-tag {
           container subscribers-summary-information {
             uses subscribers-summary-information-block;
           }
         }
         case multichassis-tag {
           container multi-routing-engine-results {
             list multi-routing-engine-item {
               leaf re-name {
                 type string;
               }
               choice output-tags {
                 case actual-tag {
                   container subscribers-summary-information {
                     uses subscribers-summary-information-block;
                   }
                 }
               }
             }
           }
         }
       }
     }
   }
   rpc get-subscribers-summary-subscriber-group {
     description "Display subscriber summary per SGRP";
     input {
       leaf subscriber-group-name {
         description "Name of the subscriber group";
         type string;
       }
     }
     output {
       choice output-tags {
         case actual-tag {
           container subscribers-summary-information {
             uses subscribers-summary-information-block;
           }
         }
         case multichassis-tag {
           container multi-routing-engine-results {
             list multi-routing-engine-item {
               leaf re-name {
                 type string;
               }
               choice output-tags {
                 case actual-tag {
                   container subscribers-summary-information {
                     uses subscribers-summary-information-block;
                   }
                 }
               }
             }
           }
         }
       }
     }
   }
   rpc get-subscribers-summary-control-plane-instance {
     description "Display subscriber summary per control plane instance";
     input {
       leaf control-plane-name {
         description "Name of the control plane instance";
         type string;
       }
     }
     output {
       choice output-tags {
         case actual-tag {
           container subscribers-summary-information {
             uses subscribers-summary-information-block;
           }
         }
         case multichassis-tag {
           container multi-routing-engine-results {
             list multi-routing-engine-item {
               leaf re-name {
                 type string;
               }
               choice output-tags {
                 case actual-tag {
                   container subscribers-summary-information {
                     uses subscribers-summary-information-block;
                   }
                 }
               }
             }
           }
         }
       }
     }
   }
   rpc get-subscribers-sgrp-information {
     description "Display subscriber information filtered by SGRP";
     input {
       leaf sgrp-name {
         description "SGRP name of subscriber";
         type string;
         mandatory true;
       }
       leaf client-type {
         description "Client type of subscriber";
         type enumeration {
           enum "dhcp" {
             description "DHCP clients only";
           }
           enum "vlan" {
             description "VLAN clients only";
           }
           enum "ppp" {
             description "PPP clients only";
           }
           enum "pppoe" {
             description "PPPoE clients only";
           }
           enum "l2tp" {
             description "L2TP clients only";
           }
           enum "static" {
             description "Static clients only";
           }
           enum "xauth" {
             description "XAuth clients only";
           }
           enum "fwauth" {
             description "FwAuth clients only";
           }
           enum "dot1x" {
             description "Dot1x clients only";
           }
         }
       }
       leaf broadband-device {
         description "Broadband-device name";
         type string;
       }
       leaf profile-name {
         description "Profile with which subscriber has been activated";
         type string {
           length "1 .. 80";
         }
       }
       leaf routing-instance {
         description "Routing instance where subscriber resides";
         type string;
       }
       leaf stacked-vlan-id {
         description "Stacked VLAN identifier of subscriber";
         type union {
           type string {
             pattern "<.*>|$.*";
           }
           type uint16 {
             range "1 .. 4094";
           }
         }
       }
       leaf vlan-id {
         description "VLAN identifier of subscriber";
         type union {
           type string {
             pattern "<.*>|$.*";
           }
           type uint16 {
             range "1 .. 4094";
           }
         }
       }
       leaf subscriber-state {
         description "State of subscriber";
         type enumeration {
           enum "init" {
             description "INIT state only";
           }
           enum "configured" {
             description "CONFIGURED state only";
           }
           enum "active" {
             description "ACTIVE state only";
           }
           enum "terminating" {
             description "TERMINATING state only";
           }
           enum "terminated" {
             description "TERMINATED state only";
           }
         }
       }
       leaf user-name {
         description "User name of subscriber";
         type string;
       }
     }
     output {
       choice output-tags {
         case actual-tag {
           container subscribers-information {
             uses subscribers-information-block;
           }
         }
         case multichassis-tag {
           container multi-routing-engine-results {
             list multi-routing-engine-item {
               leaf re-name {
                 type string;
               }
               choice output-tags {
                 case actual-tag {
                   container subscribers-information {
                     uses subscribers-information-block;
                   }
                 }
               }
             }
           }
         }
       }
     }
   }
   rpc get-subscribers-user-plane-information {
     description "Display subscriber information filtered by user-plane";
     input {
       leaf up-name {
         description "UP name of subscriber";
         type string;
         mandatory true;
       }
       leaf client-type {
         description "Client type of subscriber";
         type enumeration {
           enum "dhcp" {
             description "DHCP clients only";
           }
           enum "vlan" {
             description "VLAN clients only";
           }
           enum "ppp" {
             description "PPP clients only";
           }
           enum "pppoe" {
             description "PPPoE clients only";
           }
           enum "l2tp" {
             description "L2TP clients only";
           }
           enum "static" {
             description "Static clients only";
           }
           enum "xauth" {
             description "XAuth clients only";
           }
           enum "fwauth" {
             description "FwAuth clients only";
           }
           enum "dot1x" {
             description "Dot1x clients only";
           }
         }
       }
       leaf interface {
         description "Interface name, or with wildcards (e.g. fe-0/0/*, fe-0/*/*)";
         type union {
           type jt:interface-wildcard;
           type string {
             pattern "<.*>|$.*";
           }
         }
       }
       leaf physical-interface {
         description "Physical Interface name";
         type union {
           type jt:interface-wildcard;
           type string {
             pattern "<.*>|$.*";
           }
         }
       }
       leaf profile-name {
         description "Profile with which subscriber has been activated";
         type string {
           length "1 .. 80";
         }
       }
       leaf routing-instance {
         description "Routing instance where subscriber resides";
         type string;
       }
       leaf stacked-vlan-id {
         description "Stacked VLAN identifier of subscriber";
         type union {
           type string {
             pattern "<.*>|$.*";
           }
           type uint16 {
             range "1 .. 4094";
           }
         }
       }
       leaf vlan-id {
         description "VLAN identifier of subscriber";
         type union {
           type string {
             pattern "<.*>|$.*";
           }
           type uint16 {
             range "1 .. 4094";
           }
         }
       }
       leaf subscriber-state {
         description "State of subscriber";
         type enumeration {
           enum "init" {
             description "INIT state only";
           }
           enum "configured" {
             description "CONFIGURED state only";
           }
           enum "active" {
             description "ACTIVE state only";
           }
           enum "terminating" {
             description "TERMINATING state only";
           }
           enum "terminated" {
             description "TERMINATED state only";
           }
         }
       }
       leaf user-name {
         description "User name of subscriber";
         type string;
       }
     }
     output {
       choice output-tags {
         case actual-tag {
           container subscribers-information {
             uses subscribers-information-block;
           }
         }
         case multichassis-tag {
           container multi-routing-engine-results {
             list multi-routing-engine-item {
               leaf re-name {
                 type string;
               }
               choice output-tags {
                 case actual-tag {
                   container subscribers-information {
                     uses subscribers-information-block;
                   }
                 }
               }
             }
           }
         }
       }
     }
   }
   rpc get-subscribers-cos-classifier-information {
     description "Show mapping of code point to forwarding class/loss priority";
     input {
       leaf classifier-name {
         description "Name of classifier";
         type string;
       }
       leaf type {
         description "Type of classifier";
         type enumeration {
           enum "dscp" {
             description "Differentiated Services code point (DSCP)";
           }
           enum "dscp-ipv6" {
             description "Differentiated Services code point (DSCP) for IPv6";
           }
           enum "exp" {
             description "MPLS experimental code point";
           }
           enum "ieee-802.1" {
             description "IEEE-802.1 code point";
           }
           enum "inet-precedence" {
             description "IPv4 precedence code point";
           }
           enum "ieee-802.1ad" {
             description "IEEE-802.1ad (DEI) code point";
           }
           enum "inet6-precedence" {
             description "IPv6 precedence code point";
           }
         }
       }
     }
     output {
       choice output-tags {
         case actual-tag {
           container cos-classifier-information {
             uses cos-classifier-information-block;
           }
         }
         case multichassis-tag {
           container multi-routing-engine-results {
             list multi-routing-engine-item {
               leaf re-name {
                 type string;
               }
               choice output-tags {
                 case actual-tag {
                   container cos-classifier-information {
                     uses cos-classifier-information-block;
                   }
                 }
               }
             }
           }
         }
       }
     }
   }
   rpc get-subscribers-cos-rewrite-information {
     description "Show mapping of forwarding class/loss priority to code point";
     input {
       leaf rewrite-rule-name {
         description "Name of rewrite rule";
         type string;
       }
       leaf type {
         description "Type of rewrite rule";
         type enumeration {
           enum "dscp" {
             description "Differentiated Services code point (DSCP)";
           }
           enum "dscp-ipv6" {
             description "Differentiated Services code point (DSCP) for IPv6";
           }
           enum "exp" {
             description "MPLS experimental code point";
           }
           enum "ieee-802.1" {
             description "IEEE-802.1 code point";
           }
           enum "inet-precedence" {
             description "IPv4 precedence code point";
           }
           enum "frame-relay-de" {
             description "Frame relay discard eligible bit code point";
           }
           enum "ieee-802.1ad" {
             description "IEEE-802.1ad (DEI) code point";
           }
           enum "inet6-precedence" {
             description "IPv6 precedence code point";
           }
         }
       }
     }
     output {
       choice output-tags {
         case actual-tag {
           container cos-rewrite-information {
             uses cos-rewrite-information-block;
           }
         }
         case multichassis-tag {
           container multi-routing-engine-results {
             list multi-routing-engine-item {
               leaf re-name {
                 type string;
               }
               choice output-tags {
                 case actual-tag {
                   container cos-rewrite-information {
                     uses cos-rewrite-information-block;
                   }
                 }
               }
             }
           }
         }
       }
     }
   }
   rpc get-subscribers-cos-scheduler-map-information {
     description "Show mapping of forwarding classes to schedulers";
     input {
       leaf scheduler-map-name {
         description "Name of scheduler map";
         type string;
       }
     }
     output {
       choice output-tags {
         case actual-tag {
           container cos-scheduler-map-information {
             uses cos-scheduler-map-information-block;
           }
         }
         case multichassis-tag {
           container multi-routing-engine-results {
             list multi-routing-engine-item {
               leaf re-name {
                 type string;
               }
               choice output-tags {
                 case actual-tag {
                   container cos-scheduler-map-information {
                     uses cos-scheduler-map-information-block;
                   }
                 }
               }
             }
           }
         }
       }
     }
   }
   rpc get-subscribers-cos-tc-profile-information {
     description "Show traffic control profiles";
     input {
       leaf traffic-control-profile-name {
         description "Name of traffic control profile";
         type string;
       }
     }
     output {
       choice output-tags {
         case actual-tag {
           container cos-traffic-control-profile-information {
             uses cos-traffic-control-profile-information-block;
           }
         }
         case multichassis-tag {
           container multi-routing-engine-results {
             list multi-routing-engine-item {
               leaf re-name {
                 type string;
               }
               choice output-tags {
                 case actual-tag {
                   container cos-traffic-control-profile-information {
                     uses cos-traffic-control-profile-information-block;
                   }
                 }
               }
             }
           }
         }
       }
     }
   }
   rpc get-subscribers-cos-interface-information {
     description "Show mapping of CoS objects to interfaces";
     input {
       leaf interface-name {
         description "Name of interface";
         type string;
       }
       leaf level {
         type enumeration {
           enum "detail" {
             description "Show interface information, filter, policer and CoS object names";
           }
         }
       }
     }
     output {
       choice output-tags {
         case actual-tag {
           container cos-interface-information {
             uses cos-interface-information-block;
           }
         }
         case multichassis-tag {
           container multi-routing-engine-results {
             list multi-routing-engine-item {
               leaf re-name {
                 type string;
               }
               choice output-tags {
                 case actual-tag {
                   container cos-interface-information {
                     uses cos-interface-information-block;
                   }
                 }
               }
             }
           }
         }
       }
     }
   }
   rpc get-subscribers-cos-interface-set-information {
     description "Show mapping of CoS objects to interface-set";
     input {
       leaf interface-set-name {
         description "Name of interface set";
         type string;
       }
     }
     output {
       choice output-tags {
         case actual-tag {
           container cos-interface-set-information {
             uses cos-interface-set-information-block;
           }
         }
         case multichassis-tag {
           container multi-routing-engine-results {
             list multi-routing-engine-item {
               leaf re-name {
                 type string;
               }
               choice output-tags {
                 case actual-tag {
                   container cos-interface-set-information {
                     uses cos-interface-set-information-block;
                   }
                 }
               }
             }
           }
         }
       }
     }
   }
   rpc get-subscribers-physical-interfaces-information {
     description "Show interfaces information";
     input {
       leaf physical-interface-name {
         description "Name of the physical interface";
         type string;
       }
     }
     output {
       choice output-tags {
         case actual-tag {
           container subscribers-physical-interfaces-information {
             uses subscribers-physical-interfaces-information-block;
           }
         }
         case multichassis-tag {
           container multi-routing-engine-results {
             list multi-routing-engine-item {
               leaf re-name {
                 type string;
               }
               choice output-tags {
                 case actual-tag {
                   container subscribers-physical-interfaces-information {
                     uses subscribers-physical-interfaces-information-block;
                   }
                 }
               }
             }
           }
         }
       }
     }
   }
   rpc get-subscribers-interfaces-information {
     description "Show logical interface information";
     input {
       leaf interface-name {
         description "Name of the interface";
         type string;
         mandatory true;
       }
       leaf level {
         type enumeration {
           enum "detail" {
             description "Display extensive output";
           }
           enum "brief" {
             description "Display brief output";
           }
           enum "terse" {
             description "Display terse output";
           }
         }
       }
     }
     output {
       choice output-tags {
         case actual-tag {
           container subscribers-interfaces-information {
             uses subscribers-interfaces-information-block;
           }
         }
         case multichassis-tag {
           container multi-routing-engine-results {
             list multi-routing-engine-item {
               leaf re-name {
                 type string;
               }
               choice output-tags {
                 case actual-tag {
                   container subscribers-interfaces-information {
                     uses subscribers-interfaces-information-block;
                   }
                 }
               }
             }
           }
         }
       }
     }
   }
   rpc get-subscribers-interfaces-queue-information {
     description "Show queue statistics for this interface";
     input {
       leaf interface-name {
         description "Name of the interface";
         type string;
         mandatory true;
       }
       leaf forwarding-class {
         description "Name of forwarding class";
         type string;
       }
     }
     output {
       choice output-tags {
         case actual-tag {
           container subscribers-interfaces-queue-information {
             uses subscribers-interfaces-queue-information-block;
           }
         }
         case multichassis-tag {
           container multi-routing-engine-results {
             list multi-routing-engine-item {
               leaf re-name {
                 type string;
               }
               choice output-tags {
                 case actual-tag {
                   container subscribers-interfaces-queue-information {
                     uses subscribers-interfaces-queue-information-block;
                   }
                 }
               }
             }
           }
         }
       }
     }
   }
   rpc get-subscribers-interface-set-information {
     description "Show interface-set information";
     input {
       leaf interface-set-name {
         description "Name of the interface-set";
         type string;
         mandatory true;
       }
     }
     output {
       choice output-tags {
         case actual-tag {
           container subscribers-interfaces-information {
             uses subscribers-interfaces-information-block;
           }
         }
         case multichassis-tag {
           container multi-routing-engine-results {
             list multi-routing-engine-item {
               leaf re-name {
                 type string;
               }
               choice output-tags {
                 case actual-tag {
                   container subscribers-interfaces-information {
                     uses subscribers-interfaces-information-block;
                   }
                 }
               }
             }
           }
         }
       }
     }
   }
   rpc get-subscribers-interface-set-queue-information {
     description "Show queue statistics for this interface-set";
     input {
       leaf interface-set-name {
         description "Name of the interface-set";
         type string;
         mandatory true;
       }
     }
     output {
       choice output-tags {
         case actual-tag {
           container subscribers-interface-set-queue-information {
             uses subscribers-interface-set-queue-information-block;
           }
         }
         case multichassis-tag {
           container multi-routing-engine-results {
             list multi-routing-engine-item {
               leaf re-name {
                 type string;
               }
               choice output-tags {
                 case actual-tag {
                   container subscribers-interface-set-queue-information {
                     uses subscribers-interface-set-queue-information-block;
                   }
                 }
               }
             }
           }
         }
       }
     }
   }
   rpc get-subscribers-firewall-information {
     description "Show subscribers firewall information";
     input {
       uses command-forwarding;
       leaf terse {
         description "Show filter names only";
         type empty;
       }
       leaf detail {
         description "Show filter statistics with enhanced policer statistics";
         type empty;
       }
     }
     output {
       choice output-tags {
         case actual-tag {
           container firewall-information {
             uses firewall-information-block;
           }
         }
         case multichassis-tag {
           container multi-routing-engine-results {
             list multi-routing-engine-item {
               leaf re-name {
                 type string;
               }
               choice output-tags {
                 case actual-tag {
                   container firewall-information {
                     uses firewall-information-block;
                   }
                 }
               }
             }
           }
         }
       }
     }
   }
   rpc get-subscribers-firewall-counter-information {
     description "Counter name";
     input {
       uses command-forwarding;
       leaf countername {
         description "Counter name";
         type string;
         mandatory true;
       }
       leaf filter {
         description "Filter name";
         type string;
         mandatory true;
       }
       leaf detail {
         description "Show filter statistics with enhanced policer statistics";
         type empty;
       }
     }
     output {
       choice output-tags {
         case actual-tag {
           container firewall-information {
             uses firewall-information-block;
           }
         }
         case multichassis-tag {
           container multi-routing-engine-results {
             list multi-routing-engine-item {
               leaf re-name {
                 type string;
               }
               choice output-tags {
                 case actual-tag {
                   container firewall-information {
                     uses firewall-information-block;
                   }
                 }
               }
             }
           }
         }
       }
     }
   }
   rpc get-subscribers-firewall-filter-information {
     description "Filter name";
     input {
       uses command-forwarding;
       leaf filtername {
         description "Filter name";
         type string;
         mandatory true;
       }
       leaf counter {
         description "Counter name";
         type string;
       }
       leaf detail {
         description "Show filter statistics with enhanced policer statistics";
         type empty;
       }
     }
     output {
       choice output-tags {
         case actual-tag {
           container firewall-information {
             uses firewall-information-block;
           }
         }
         case multichassis-tag {
           container multi-routing-engine-results {
             list multi-routing-engine-item {
               leaf re-name {
                 type string;
               }
               choice output-tags {
                 case actual-tag {
                   container firewall-information {
                     uses firewall-information-block;
                   }
                 }
               }
             }
           }
         }
       }
     }
   }
   rpc get-subscribers-filter-version {
     description "Show filter version installed";
     input {
       leaf filtername {
         description "Filter name";
         type string;
       }
     }
     output {
       choice output-tags {
         case actual-tag {
           container firewall-information {
             uses firewall-information-block;
           }
         }
         case multichassis-tag {
           container multi-routing-engine-results {
             list multi-routing-engine-item {
               leaf re-name {
                 type string;
               }
               choice output-tags {
                 case actual-tag {
                   container firewall-information {
                     uses firewall-information-block;
                   }
                 }
               }
             }
           }
         }
       }
     }
   }
   rpc get-subs-firewall-filter-regex-information {
     description "Show filter using regular expression";
     input {
       leaf filtername {
         description "Regular expression of filter names";
         type jt:regular-expression;
       }
     }
     output {
       choice output-tags {
         case actual-tag {
           container firewall-information {
             uses firewall-information-block;
           }
         }
         case multichassis-tag {
           container multi-routing-engine-results {
             list multi-routing-engine-item {
               leaf re-name {
                 type string;
               }
               choice output-tags {
                 case actual-tag {
                   container firewall-information {
                     uses firewall-information-block;
                   }
                 }
               }
             }
           }
         }
       }
     }
   }
   rpc get-subscribers-firewall-log-information {
     description "Show log entries for firewall activity";
     input {
       leaf get-subs-firewall-log-detailed-information {
         description "Display detailed output";
         type empty;
       }
     }
     output {
       choice output-tags {
         case actual-tag {
           container firewall-log-information {
             uses firewall-log-information-block;
           }
         }
         case multichassis-tag {
           container multi-routing-engine-results {
             list multi-routing-engine-item {
               leaf re-name {
                 type string;
               }
               choice output-tags {
                 case actual-tag {
                   container firewall-log-information {
                     uses firewall-log-information-block;
                   }
                 }
               }
             }
           }
         }
       }
     }
   }
   rpc get-subs-firewall-prefix-action-information {
     description "Show prefix-action statistics for a filter";
     input {
       leaf filter {
         description "Filter name";
         type string;
         mandatory true;
       }
       leaf prefix-action {
         description "Prefix-action name";
         type string;
         mandatory true;
       }
       leaf from {
         description "Starting counter or policer";
         default "0";
         type union {
           type string {
             pattern "<.*>|$.*";
           }
           type uint32 {
             range "0 .. 65535";
           }
         }
       }
       leaf to {
         description "Ending counter or policer";
         default "65535";
         type union {
           type string {
             pattern "<.*>|$.*";
           }
           type uint32 {
             range "0 .. 65535";
           }
         }
       }
     }
     output {
       choice output-tags {
         case actual-tag {
           container firewall-prefix-action-information {
             uses firewall-prefix-action-information-block;
           }
         }
         case multichassis-tag {
           container multi-routing-engine-results {
             list multi-routing-engine-item {
               leaf re-name {
                 type string;
               }
               choice output-tags {
                 case actual-tag {
                   container firewall-prefix-action-information {
                     uses firewall-prefix-action-information-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping subscribers-information-block {
     list subscriber {
       description
         "Active subscriber";
       leaf interface {
         type string;
         description
           "Interface name of subscriber";
       }
       leaf ip-address {
         type string;
         description
           "IP address of subscriber";
       }
       leaf ipv6-address {
         type string;
         description
           "IPv6 address of subscriber";
       }
       leaf stacked-vlan-id {
         type int32;
         description
           "Stacked VLAN identifier";
       }
       leaf vlan-id {
         type int32;
         description
           "VLAN identifier";
       }
       leaf user-name {
         type string;
         description
           "User name of subscriber";
       }
       leaf logical-system {
         type string;
         description
           "Logical system where the subscriber resides";
       }
       leaf routing-instance {
         type string;
         description
           "Routing instance where the subscriber resides";
       }
       leaf len {
         type int32;
         description
           "Dhcp length";
       }
       leaf actual-data-rate-upstream {
         type int32;
         description
           "Actual upstream data rate";
       }
       leaf actual-data-rate-downstream {
         type int32;
         description
           "Actual downstream data rate";
       }
       leaf minimum-data-rate-upstream {
         type int32;
         description
           "Minimum upstream data rate";
       }
       leaf minimum-data-rate-downstream {
         type int32;
         description
           "Minimum downstream data rate";
       }
       leaf attainable-data-rate-upstream {
         type int32;
         description
           "Attainable upstream data rate";
       }
       leaf attainable-data-rate-downstream {
         type int32;
         description
           "Attainable downstream data rate";
       }
       leaf maximum-data-rate-upstream {
         type int32;
         description
           "Maximum upstream data rate";
       }
       leaf maximum-data-rate-downstream {
         type int32;
         description
           "Maximum downstream data rate";
       }
       leaf minimum-net-low-power-data-rate-upstream {
         type int32;
         description
           "Minimum net low power upstream data rate";
       }
       leaf minimum-net-low-power-data-rate-downstream {
         type int32;
         description
           "Minimum net low power downstream data rate";
       }
       leaf maximum-interleaving-delay-upstream {
         type int32;
         description
           "Maximum interleaving upstream delay";
       }
       leaf maximum-interleaving-delay-downstream {
         type int32;
         description
           "Maximum interleaving downstream delay";
       }
       leaf actual-interleaving-delay-upstream {
         type int32;
         description
           "Actual interleaving upstream delay";
       }
       leaf actual-interleaving-delay-downstream {
         type int32;
         description
           "Actual interleaving downstream delay";
       }
       leaf dsl-line-state {
         type string;
         description
           "DSL line state";
       }
       leaf access-loop-encapsulation {
         type string;
         description
           "Access loop encapsulation";
       }
       leaf ont-onu-average-data-rate-downstream {
         type int32;
         description
           "ONT/ONU average downstream data rate";
       }
       leaf ont-onu-peak-data-rate-downstream {
         type int32;
         description
           "ONT/ONU peak downstream data rate";
       }
       leaf ont-onu-max-data-rate-upstream {
         type int32;
         description
           "ONT/ONU maximum upstream data rate";
       }
       leaf ont-onu-assured-data-rate-upstream {
         type int32;
         description
           "ONT/ONU assured upstream data rate";
       }
       leaf pon-tree-max-data-rate-upstream {
         type int32;
         description
           "PON tree maximum upstream data rate";
       }
       leaf pon-tree-max-data-rate-downstream {
         type int32;
         description
           "PON tree maximum downstream data rate";
       }
       leaf expected-throughput-upstream {
         type int32;
         description
           "Expected throughput upstream";
       }
       leaf expected-throughput-downstream {
         type int32;
         description
           "Expected throughput downstream";
       }
       leaf attainable-expected-throughput-upstream {
         type int32;
         description
           "Attainable expected throughput upstream";
       }
       leaf attainable-expected-throughput-downstream {
         type int32;
         description
           "Attainable expected throughput downstream";
       }
       leaf gamma-throughput-upstream {
         type int32;
         description
           "Gamma data rate upstream";
       }
       leaf gamma-throughput-downstream {
         type int32;
         description
           "Gamma data rate downstream";
       }
       leaf attainable-gamma-throughput-upstream {
         type int32;
         description
           "Attainable gamma data rate upstream";
       }
       leaf attainable-gamma-throughput-downstream {
         type int32;
         description
           "Attainable gamma data rate downstream";
       }
       leaf interworking-function {
         type int32;
         description
           "Interworking Function";
       }
       leaf access-aggregation-circuit-id {
         type string;
         description
           "Access Aggregation Circuit ID";
       }
       leaf access-aggregation-circuit-id-binary {
         type string;
         description
           "Access Aggregation Circuit ID Binary";
       }
       container dhcp-options {
         leaf len {
           type int32;
           description
             "Dhcp length";
         }
         leaf-list hex-data {
           type string;
           description
             "Hex data";
         }
       }
       container server-dhcp-options {
         leaf len {
           type int32;
           description
             "Dhcp length";
         }
         leaf-list hex-data {
           type string;
           description
             "Hex data";
         }
       }
       container dhcpv6-options {
         leaf len {
           type int32;
           description
             "Dhcp length";
         }
         leaf-list hex-data {
           type string;
           description
             "Hex data";
         }
       }
       container server-dhcpv6-options {
         leaf len {
           type int32;
           description
             "Dhcp length";
         }
         leaf-list hex-data {
           type string;
           description
             "Hex data";
         }
       }
       container dhcp-header {
         leaf len {
           type int32;
           description
             "Dhcp length";
         }
         leaf-list hex-data {
           type string;
           description
             "Hex data";
         }
       }
       container dhcpv6-header {
         leaf len {
           type int32;
           description
             "Dhcp length";
         }
         leaf-list hex-data {
           type string;
           description
             "Hex data";
         }
       }
       container access-line-attributes {
         leaf agent-circuit-id {
           type string;
           description
             "Agent CID for this subscriber";
         }
         leaf agent-remote-id {
           type string;
           description
             "Agent RID for this subscriber";
         }
         leaf access-aggregation-circuit-id {
           type string;
           description
             "Access Aggregation Circuit ID";
         }
         leaf access-aggregation-circuit-id-binary {
           type string;
           description
             "Access Aggregation Circuit ID Binary";
         }
         leaf actual-data-rate-upstream {
           type int32;
           description
             "Actual upstream data rate";
         }
         leaf actual-data-rate-downstream {
           type int32;
           description
             "Actual downstream data rate";
         }
         leaf minimum-data-rate-upstream {
           type int32;
           description
             "Minimum upstream data rate";
         }
         leaf minimum-data-rate-downstream {
           type int32;
           description
             "Minimum downstream data rate";
         }
         leaf attainable-data-rate-upstream {
           type int32;
           description
             "Attainable upstream data rate";
         }
         leaf attainable-data-rate-downstream {
           type int32;
           description
             "Attainable downstream data rate";
         }
         leaf maximum-data-rate-upstream {
           type int32;
           description
             "Maximum upstream data rate";
         }
         leaf maximum-data-rate-downstream {
           type int32;
           description
             "Maximum downstream data rate";
         }
         leaf minimum-net-low-power-data-rate-upstream {
           type int32;
           description
             "Minimum net low power upstream data rate";
         }
         leaf minimum-net-low-power-data-rate-downstream {
           type int32;
           description
             "Minimum net low power downstream data rate";
         }
         leaf maximum-interleaving-delay-upstream {
           type int32;
           description
             "Maximum interleaving upstream delay";
         }
         leaf maximum-interleaving-delay-downstream {
           type int32;
           description
             "Maximum interleaving downstream delay";
         }
         leaf actual-interleaving-delay-upstream {
           type int32;
           description
             "Actual interleaving upstream delay";
         }
         leaf actual-interleaving-delay-downstream {
           type int32;
           description
             "Actual interleaving downstream delay";
         }
         leaf dsl-line-state {
           type string;
           description
             "DSL line state";
         }
         leaf access-loop-encapsulation {
           type string;
           description
             "Access loop encapsulation";
         }
         leaf dsl-type {
           type int32;
           description
             "DSL type";
         }
         leaf pon-type {
           type int32;
           description
             "PON type";
         }
         leaf ont-onu-average-data-rate-downstream {
           type int32;
           description
             "ONT/ONU average downstream data rate";
         }
         leaf ont-onu-peak-data-rate-downstream {
           type int32;
           description
             "ONT/ONU peak downstream data rate";
         }
         leaf ont-onu-max-data-rate-upstream {
           type int32;
           description
             "ONT/ONU maximum upstream data rate";
         }
         leaf ont-onu-assured-data-rate-upstream {
           type int32;
           description
             "ONT/ONU assured upstream data rate";
         }
         leaf pon-tree-max-data-rate-upstream {
           type int32;
           description
             "PON tree maximum upstream data rate";
         }
         leaf pon-tree-max-data-rate-downstream {
           type int32;
           description
             "PON tree maximum downstream data rate";
         }
         leaf expected-throughput-upstream {
           type int32;
           description
             "Expected throughput upstream";
         }
         leaf expected-throughput-downstream {
           type int32;
           description
             "Expected throughput downstream";
         }
         leaf attainable-expected-throughput-upstream {
           type int32;
           description
             "Attainable expected throughput upstream";
         }
         leaf attainable-expected-throughput-downstream {
           type int32;
           description
             "Attainable expected throughput downstream";
         }
         leaf gamma-throughput-upstream {
           type int32;
           description
             "Gamma data rate upstream";
         }
         leaf gamma-throughput-downstream {
           type int32;
           description
             "Gamma data rate downstream";
         }
         leaf attainable-gamma-throughput-upstream {
           type int32;
           description
             "Attainable gamma data rate upstream";
         }
         leaf attainable-gamma-throughput-downstream {
           type int32;
           description
             "Attainable gamma data rate downstream";
         }
         leaf interworking-function {
           type int32;
           description
             "Interworking Function";
         }
         container access-line-attribute {
           leaf attribute-type {
             type string;
             description
               "Attribute type";
           }
           leaf attribute-length {
             type int32;
             description
               "Attribute length";
           }
           leaf-list hex-data {
             type string;
             description
               "Hex data";
           }
         }
       }
       leaf session-id {
         type string;
         description
           "Session ID";
       }
       leaf control-plane-instance {
         type string;
         description
           "Control Plane instance";
       }
       leaf sgrp-name {
         type string;
         description
           "Subscriber group name";
       }
       leaf up-ports {
         type string;
         description
           "User Plane/Port names";
       }
       leaf bb-device-id {
         type string;
         description
           "Broadband device identifier";
       }
       leaf subscriber-resiliency-state {
         type string;
         description
           "Resiliency State of Subscriber";
       }
       leaf-list no-attributes {
         type string;
       }
       leaf access-type {
         type string;
         description
           "Access type of subscriber";
       }
       leaf session-type {
         type string;
         description
           "Session type of subscriber";
       }
       leaf parent-session-id {
         type string;
         description
           "Parent sesssion Id of subscriber";
       }
       leaf ip-netmask {
         type string;
         description
           "IP netmask of subscriber";
       }
       leaf ipv6-prefix {
         type string;
         description
           "IPv6 prefix of subscriber";
       }
       leaf primary-dns-address {
         type string;
         description
           "Primary DNS address of subscriber";
       }
       leaf secondary-dns-address {
         type string;
         description
           "Secondary DNS address of subscriber";
       }
       leaf domain-name-server-inet {
         type string;
         description
           "Domain name server inet";
       }
       leaf domain-name-server-inet6 {
         type string;
         description
           "Domain name server inet6";
       }
       leaf primary-wins-address {
         type string;
         description
           "Primary WINS address of subscriber";
       }
       leaf secondary-wins-address {
         type string;
         description
           "Secondary WINS address of subscriber";
       }
       leaf ipv6-primary-dns-address {
         type string;
         description
           "IPV6 primary DNS address of subscriber";
       }
       leaf ipv6-secondary-dns-address {
         type string;
         description
           "IPV6 secondary DNS address of subscriber";
       }
       leaf ipv6-ndra-prefix {
         type string;
         description
           "IPv6 ndra prefix of subscriber";
       }
       leaf ipv6-user-prefix {
         type string;
         description
           "IPv6 prefix of subscriber";
       }
       leaf active-up-name-port {
         type string;
         description
           "Active User Plane/Port name";
       }
       leaf backup-up-name-port {
         type string;
         description
           "Backup User Plane/Port name";
       }
       leaf up-id {
         type int32;
         description
           "User Plane identifier";
       }
       leaf sgrp-id {
         type int32;
         description
           "Subscriber resiliency group identifier";
       }
       leaf tenant-name {
         type string;
         description
           "Tenant name of subscriber";
       }
       leaf interface-tag {
         type string;
         description
           "Interface tag of subscriber";
       }
       leaf interface-type {
         type string;
         description
           "Type of Interface subscriber is on";
       }
       leaf physical-interface {
         type string;
         description
           "Physical Interface name of subscriber";
       }
       leaf stacked-interface-set-name {
         type string;
         description
           "Stacked interface set which the subscriber is part of";
       }
       leaf interface-set-name {
         type string;
         description
           "Interface set which the subscriber is part of";
       }
       leaf underlying-interface {
         type string;
         description
           "Underlying Interface";
       }
       leaf interface-description {
         type string;
         description
           "Interface description";
       }
       leaf core-ifl-name {
         type string;
         description
           "Core Facing Interface Name";
       }
       leaf vlan-map-id {
         type int32;
         description
           "VLAN Map identifier for identifying trunk-vlan on core-ifl";
       }
       leaf inner-vlan-map-id {
         type int32;
         description
           "Inner VLAN Map identifier for core-ifl";
       }
       leaf tag-protocol-id {
         type int32;
         description
           "VLAN tag protocol id";
       }
       leaf inner-vlan-tag-protocol-id {
         type int32;
         description
           "Inner VLAN tag protocol id";
       }
       leaf profile {
         type string;
         description
           "Dynamic profile with which subscriber is activated";
       }
       leaf version-alias {
         type string;
         description
           "Dynamic profile version alias, transmitted to RADIUS during 
           authentication";
       }
       leaf profile-version {
         type int32;
         description
           "Dynamic profile version";
       }
       leaf mac-address {
         type string;
         description
           "MAC address of subscriber";
       }
       leaf agf-mode {
         type string;
         description
           "AGF Mode";
       }
       leaf gtpu-local-teid {
         type int32;
         description
           "GTPU Local TEID";
       }
       leaf gtpc-local-teid {
         type int32;
         description
           "GTPC Local TEID";
       }
       leaf gtpu-remote-teid {
         type int32;
         description
           "GTPU Remote TEID";
       }
       leaf gtpc-remote-teid {
         type int32;
         description
           "GTPC Remote TEID";
       }
       leaf gtpu-tunnel-remote-ip-address {
         type string;
         description
           "GTPU Tunnel Remote IP Address";
       }
       leaf gtpu-tunnel-local-ip-address {
         type string;
         description
           "GTPU Tunnel Local IP Address";
       }
       leaf gtpc-remote-ip-address {
         type string;
         description
           "GTPC Remote IP Address";
       }
       leaf gtpc-local-ip-address {
         type string;
         description
           "GTPC Local IP Address";
       }
       leaf fiveg-qos-flow-identifier {
         type int32;
         description
           "5G-QFI";
       }
       leaf access-point-name {
         type string;
         description
           "Access Point Name";
       }
       leaf gtpc-ebi {
         type int32;
         description
           "GTPC EBI";
       }
       leaf state {
         type string;
         description
           "State of subscriber";
       }
       leaf ppp-state {
         type string;
         description
           "PPP protocol state";
       }
       leaf l2tp-state {
         type string;
         description
           "L2TP protocol state";
       }
       leaf l2tp-tunnel-switch-profile-name {
         type string;
         description
           "Tunnel switch profile used by subscriber";
       }
       leaf local-ip-address {
         type jt:ipaddr;
         description
           "Local IP address of tunneled subscriber";
       }
       leaf remote-ip-address {
         type jt:ipaddr;
         description
           "Remote IP address of tunneled subscriber";
       }
       leaf gw-address {
         type string;
         description
           "DHCP Gateway IP address of subscriber";
       }
       leaf radius-accounting-id {
         type string;
         description
           "Radius Accounting ID of subscriber";
       }
       leaf underlying-session-id {
         type string;
         description
           "Underlying Session ID of DHCPv6 session over PPPoe";
       }
       leaf bundle-session-id {
         type string;
         description
           "Bundle Session ID of MLPPP member subscriber";
       }
       leaf pfe-flow-id {
         type int32;
         description
           "PFE Flow ID";
       }
       leaf hag-session-id {
         type int32;
         description
           "HAG Session ID";
       }
       leaf hag-tunnel-type {
         type string;
         description
           "HAG Tunnel Type";
       }
       leaf session-timeout {
         type int32;
         description
           "Session longevity of subscriber";
       }
       leaf idle-timeout {
         type int32;
         description
           "Session idle timeout of subscriber";
       }
       leaf idle-timeout-ingress-only {
         type string;
         description
           "Session idle timeout of subscriber is ingress only";
       }
       leaf idle-timeout-egress-only {
         type string;
         description
           "Session idle timeout of subscriber is egress only";
       }
       leaf reauthentication-capable {
         type string;
         description
           "Subscriber has re-authentication capability enabled";
       }
       leaf login-time {
         type string;
         description
           "Login time of subscriber";
       }
       leaf agent-circuit-id {
         type string;
         description
           "Agent CID for this subscriber";
       }
       leaf agent-remote-id {
         type string;
         description
           "Agent RID for this subscriber";
       }
       leaf aggregation-interface-set-name {
         type string;
         description
           "Aggregation interface set name";
       }
       leaf-list hex-data {
         type string;
         description
           "Hex data";
       }
       leaf number-of-service-sessions {
         type int32;
         description
           "Number of service sessions for this subscriber";
       }
       leaf on-demand-ip-address {
         type string;
         description
           "On-Demand IP address status for this session";
       }
       leaf service-group-name {
         type string;
         description
           "Service group AVP from access-accept";
       }
       leaf nat-ip-pool {
         type string;
         description
           "NAT Pool Name";
       }
       leaf nat-public-ip-address {
         type string;
         description
           "NAT Public IP Address";
       }
       leaf nat-port-block {
         type string;
         description
           "NAT Port Block";
       }
       leaf napt-portblock-allocation-time {
         type string;
         description
           "NAPT Port Block Allocation Time";
       }
       leaf napt-portblock-free-time {
         type string;
         description
           "NAPT Port Block Free Time";
       }
       leaf vpws-service-id-local {
         type uint32;
         description
           "Local EVPN VPWS service id";
       }
       leaf vpws-service-id-remote {
         type uint32;
         description
           "Remote EVPN VPWS service id";
       }
       leaf ipv4-input-filter-name {
         type string;
         description
           "IPv4 input filter name for this session";
       }
       leaf ipv4-output-filter-name {
         type string;
         description
           "IPv4 output filter name for this session";
       }
       leaf ipv6-input-filter-name {
         type string;
         description
           "IPv6 input filter name for this session";
       }
       leaf ipv6-output-filter-name {
         type string;
         description
           "IPv6 output filter name for this session";
       }
       leaf ifl-input-filter-name {
         type string;
         description
           "IFL input filter name for this session";
       }
       leaf ifl-output-filter-name {
         type string;
         description
           "IFL output filter name for this session";
       }
       leaf adfv4-input-filter-name {
         type string;
         description
           "ADF IPv4 input filter name for this session";
       }
       leaf adfv4-input-rule {
         type string;
         description
           "ADF IPv4 input rule for this session";
       }
       leaf adfv4-input-rule-decoded {
         type string;
         description
           "Decoded ADF IPv4 input rule for this session";
       }
       leaf adfv4-output-filter-name {
         type string;
         description
           "ADF IPv4 output filter name for this session";
       }
       leaf adfv4-output-rule {
         type string;
         description
           "ADF IPv4 output rule for this session";
       }
       leaf adfv4-output-rule-decoded {
         type string;
         description
           "Decoded ADF IPv4 output rule for this session";
       }
       leaf adfv6-input-filter-name {
         type string;
         description
           "ADF IPv6 input filter name for this session";
       }
       leaf adfv6-input-rule {
         type string;
         description
           "ADF IPv6 input rule for this session";
       }
       leaf adfv6-input-rule-decoded {
         type string;
         description
           "Decoded ADF IPv6 input rule for this session";
       }
       leaf adfv6-output-filter-name {
         type string;
         description
           "ADF IPv6 output filter name for this session";
       }
       leaf adfv6-output-rule {
         type string;
         description
           "ADF IPv6 output rule for this session";
       }
       leaf adfv6-output-rule-decoded {
         type string;
         description
           "Decoded ADF IPv6 output rule for this session";
       }
       leaf vpls-input-filter-name {
         type string;
         description
           "Vpls input filter name for this session";
       }
       leaf vpls-output-filter-name {
         type string;
         description
           "Vpls output filter name for this session";
       }
       leaf l2pol-input-filter-name {
         type string;
         description
           "L2 Policer input filter name for this session";
       }
       leaf l2pol-output-filter-name {
         type string;
         description
           "L2 Policer output filter name for this session";
       }
       leaf ipv4-rpf-check-fail-filter-name {
         type string;
         description
           "IPv4 rpf-check Fail Filter Name";
       }
       leaf ipv6-rpf-check-fail-filter-name {
         type string;
         description
           "IPv6 rpf-check Fail Filter Name";
       }
       leaf sgrp-refcnt {
         type int32;
         description
           "Subscriber resiliency group refcnt";
       }
       leaf session-generation {
         type int32;
         description
           "Subscriber resiliency session generation";
       }
       leaf ip-address-pool {
         type string;
         description
           "IP address pool name";
       }
       leaf ipv6-delegated-pool {
         type string;
         description
           "IPv6 delegated address pool name";
       }
       leaf ipv6-address-pool {
         type string;
         description
           "IPv6 address pool name";
       }
       leaf ipv6-interface-address {
         type string;
         description
           "IPv6 interface address of subscriber";
       }
       leaf ipv6-framed-interface-id {
         type string;
         description
           "IPv6 framed interface id";
       }
       leaf effective-shaping-rate {
         type uint32;
         description
           "Effective shaping-rate for this subscriber";
       }
       leaf accounting-interval {
         type int32;
         description
           "Accounting interval";
       }
       leaf ipv4-input-service-set {
         type string;
         description
           "IPv4 input service set for this session";
       }
       leaf ipv4-output-service-set {
         type string;
         description
           "IPv4 output service set for this session";
       }
       leaf ipv6-input-service-set {
         type string;
         description
           "IPv6 input service set for this session";
       }
       leaf ipv6-output-service-set {
         type string;
         description
           "IPv6 output service set for this session";
       }
       leaf pcef-profile {
         type string;
         description
           "PCEF profile for this session";
       }
       leaf pcef-rule {
         type string;
         description
           "PCEF rule or rulebase for this session";
       }
       leaf dsl-type {
         type int32;
         description
           "DSL type";
       }
       leaf pon-type {
         type int32;
         description
           "PON type";
       }
       leaf calculated-data-rate-upstream {
         type int32;
         description
           "Calculated upstream data rate";
       }
       leaf calculated-data-rate-downstream {
         type int32;
         description
           "Calculated downstream data rate";
       }
       leaf adjusted-data-rate-downstream {
         type int32;
         description
           "Adjusted downstream data rate";
       }
       leaf adjusted-aggregation-data-rate-downstream {
         type int32;
         description
           "Adjusted aggregation downstream data rate";
       }
       leaf overhead-accounting-mode {
         type string;
         description
           "Overhead accounting mode";
       }
       leaf overhead-accounting-bytes {
         type int32;
         description
           "Overhead accounting bytes";
       }
       leaf next-hop-mac-address {
         type string;
         description
           "Next Hop MAC address";
       }
       leaf next-hop-ipv6-mac-address {
         type string;
         description
           "Next Hop Ipv6 MAC address";
       }
       leaf service-session-id {
         type string;
         description
           "Session ID of service";
       }
       leaf service-session-name {
         type string;
         description
           "Name of service session";
       }
       leaf extensible-service-name {
         type string;
         description
           "Name of extensible service";
       }
       leaf service-session-version {
         type int32;
         description
           "Version of service session";
       }
       leaf service-session-type {
         type string;
         description
           "Session type of service";
       }
       leaf service-session-family {
         type string;
         description
           "Address family enabled on service session";
       }
       leaf service-activation-time {
         type string;
         description
           "Service Activation time";
       }
       leaf accounting-interval-service {
         type int32;
         description
           "Accounting interval";
       }
       leaf subscriber-id {
         type string;
         description
           "Session ID of subscriber";
       }
       leaf service-session-ids {
         type string;
         description
           "List of service session IDs for subscriber";
       }
       leaf private-data {
         type string;
         description
           "Private data";
       }
       leaf number-of-subscribers {
         type int32;
         description
           "Number of subscribers that match with search criteria";
       }
       leaf number-of-active-subscribers {
         type int32;
         description
           "Number of active subscribers that match with search criteria";
       }
       leaf acc-input-bytes {
         type int32;
         description
           "Input bytes for the subscriber";
       }
       leaf acc-output-bytes {
         type int32;
         description
           "Ouput bytes for the subscriber";
       }
       leaf acc-input-packets {
         type int32;
         description
           "Input packets for the subscriber";
       }
       leaf acc-output-packets {
         type int32;
         description
           "Output packets for the subscriber";
       }
     }
     container error {
       leaf pcef-input-error-message {
         type string;
         description
           "Input error message";
       }
       leaf pcef-error-message {
         type string;
         description
           "Error message";
       }
       leaf input-error-message {
         type string;
         description
           "Input error message";
       }
     }
     container status {
       leaf db-status-message {
         type string;
         description
           "Database status message";
       }
     }
   }
   grouping subscriber-lic-information-block {
     list subscriber-license-hourly-usage {
       description
         "Hourly license usage count for last 48 hours";
       list subscriber-license-type {
         description
           "Subscriber license type";
         leaf subscriber-license {
           type string;
           description
             "Subscriber License name";
         }
       }
       list subscriber-license-time-and-usage {
         description
           "Hourly license usage count and time when it was collected";
         leaf subscriber-usage-at-time {
           type string;
           description
             "Subscriber License Usage at time";
         }
         leaf subscriber-usage {
           type uint32;
           description
             "Subscriber License Usage at time";
         }
       }
     }
   }
   grouping subscribers-summary-information-block {
     list counters {
       description
         "Session Summary";
       leaf session-subsystem-agf {
         type int32;
         description
           "Total AGF sessions";
       }
       leaf session-subsystem-bng {
         type int32;
         description
           "Total BNG sessions";
       }
       leaf session-subsystem-total {
         type int32;
         description
           "Total subsystem sessions";
       }
       leaf session-total {
         type int32;
         description
           "Total sessions";
       }
       leaf session-state-init {
         type int32;
         description
           "Total init-state sessions";
       }
       leaf session-state-configured {
         type int32;
         description
           "Total configured-state sessions";
       }
       leaf session-state-active {
         type int32;
         description
           "Total active-state sessions";
       }
       leaf session-state-terminating {
         type int32;
         description
           "Total terminating-state sessions";
       }
       leaf session-state-terminated {
         type int32;
         description
           "Total terminated-state sessions";
       }
       leaf session-state-unknown {
         type int32;
         description
           "Total unknown-state sessions";
       }
       leaf session-state-total {
         type int32;
         description
           "Total state sessions";
       }
       leaf resiliency-state-active {
         type int32;
         description
           "Active resiliency state sessions";
       }
       leaf resiliency-state-backup {
         type int32;
         description
           "Backup resiliency state sessions";
       }
       leaf resiliency-state-total {
         type int32;
         description
           "Total resiliency state sessions";
       }
       leaf port-name {
         type string;
         description
           "Port name of subscriber";
       }
       leaf port-count {
         type int32;
         description
           "Number of subscribers in this port";
       }
       leaf session-type-none {
         type int32;
         description
           "Total none-type sessions";
       }
       leaf session-type-dhcp {
         type int32;
         description
           "Total dhcp-type sessions";
       }
       leaf session-type-vlan {
         type int32;
         description
           "Total vlan-type sessions";
       }
       leaf session-type-vlan-oob {
         type int32;
         description
           "Total out-of-band vlan type sessions";
       }
       leaf session-type-vlan-extm {
         type int32;
         description
           "Total externally managed vlan sessions";
       }
       leaf session-type-generic {
         type int32;
         description
           "Total generic-type sessions";
       }
       leaf session-type-mobileip {
         type int32;
         description
           "Total mobileip-type sessions";
       }
       leaf session-type-vpls-pw {
         type int32;
         description
           "Total vpls-pw-type sessions";
       }
       leaf session-type-ppp {
         type int32;
         description
           "Total ppp-type sessions";
       }
       leaf session-type-pppoe {
         type int32;
         description
           "Total pppoe-type sessions";
       }
       leaf session-type-l2tp {
         type int32;
         description
           "Total l2tp-type sessions";
       }
       leaf session-type-static {
         type int32;
         description
           "Total static-type sessions";
       }
       leaf session-type-mlppp {
         type int32;
         description
           "Total mlppp-type sessions";
       }
       leaf session-type-xauth {
         type int32;
         description
           "Total xauth-type sessions";
       }
       leaf session-type-fwauth {
         type int32;
         description
           "Total fwauth-type sessions";
       }
       leaf session-type-dot1x {
         type int32;
         description
           "Total fwauth-type sessions";
       }
       leaf session-type-essm {
         type int32;
         description
           "Total essm-type sessions";
       }
       leaf session-type-hag-bundle {
         type int32;
         description
           "Total hag-bundle-type sessions";
       }
       leaf session-type-hag-tunnel {
         type int32;
         description
           "Total hag-tunnel-type sessions";
       }
       leaf session-type-fixed-wireless-access {
         type int32;
         description
           "Total fixed wireless access sessions";
       }
       leaf session-type-nat {
         type int32;
         description
           "Total nat sessions";
       }
       leaf session-type-unknown {
         type int32;
         description
           "Total unknown-type sessions";
       }
       leaf session-type-total {
         type int32;
         description
           "Total type sessions";
       }
       leaf session-type-l2bsa-extm {
         type int32;
         description
           "Total externally managed l2bsa sessions";
       }
       leaf tunneled-count {
         type int32;
         description
           "Total tunneled sessions";
       }
       leaf terminated-count {
         type int32;
         description
           "Total terminated sessions";
       }
       leaf cross-connected-count {
         type int32;
         description
           "Total cross-connected sessions";
       }
       leaf session-type-l2ckt-pw {
         type int32;
         description
           "Total l2ckt-pw-type sessions";
       }
       leaf session-type-gre {
         type int32;
         description
           "Total gre-type sessions";
       }
       leaf session-type-dyn-ip {
         type int32;
         description
           "Total dyn-ip type sessions";
       }
       leaf ifl-type-none {
         type int32;
         description
           "Total none type ifl";
       }
       leaf ifl-type-static {
         type int32;
         description
           "Total static type ifl";
       }
       leaf ifl-type-dynamic {
         type int32;
         description
           "Total dynamic type ifl";
       }
       leaf ifl-type-unknown {
         type int32;
         description
           "Total unknown type ifl";
       }
       leaf config-bit-interface {
         type int32;
         description
           "Total interface config bit";
       }
       leaf config-bit-inet {
         type int32;
         description
           "Total inet config bit";
       }
       leaf config-bit-inet-filter {
         type int32;
         description
           "Total inet filter config bit";
       }
       leaf config-bit-inet-service {
         type int32;
         description
           "Total inet service config bit";
       }
       leaf config-bit-routing-instance {
         type int32;
         description
           "Total routing instance config bit";
       }
       leaf config-bit-routing-options {
         type int32;
         description
           "Total routing options config bit";
       }
       leaf config-bit-igmp {
         type int32;
         description
           "Total IGMP config bit";
       }
       leaf config-bit-cos {
         type int32;
         description
           "Total COS config bit";
       }
       leaf config-bit-inet6 {
         type int32;
         description
           "Total inet6 config bit";
       }
       leaf config-bit-inet6-filter {
         type int32;
         description
           "Total inet6 filter config bit";
       }
       leaf config-bit-inet6-service {
         type int32;
         description
           "Total inet6 service config bit";
       }
       leaf config-bit-mld {
         type int32;
         description
           "Total MLD config bit";
       }
       leaf config-bit-li {
         type int32;
         description
           "Total LI config bit";
       }
       leaf config-bit-ra {
         type int32;
         description
           "Total RA config bit";
       }
       leaf config-bit-ifl-filter {
         type int32;
         description
           "Total IFL filter config bit";
       }
       leaf config-bit-access-internal {
         type int32;
         description
           "Total access internal config bit";
       }
       leaf config-bit-iflset {
         type int32;
         description
           "Total iflset config bit";
       }
       leaf config-bit-vpls {
         type int32;
         description
           "Total vpls config bit";
       }
       leaf config-bit-unknown {
         type int32;
         description
           "Total unknown config bit";
       }
       leaf lsri-name {
         type string;
         description
           "LS:RI";
       }
       leaf lsri-count {
         type int32;
         description
           "Number of subscribers in this LS:RI";
       }
       leaf lsri-total {
         type int32;
         description
           "Total sessions in LS:RIs";
       }
       leaf port-total {
         type int32;
         description
           "Total sessions in port";
       }
       leaf bb-device-name {
         type string;
         description
           "Broadband device name of subscriber";
       }
       leaf physical-intf-name {
         type string;
         description
           "Physical Interface name of subscriber";
       }
     }
   }
   grouping cos-classifier-information-block {
     list classifier {
       description
         "Class-of-service code point classifier";
       leaf classifier-name {
         type string;
         description
           "Class-of-service classifier name";
       }
       leaf code-point-type {
         type string;
         description
           "Class-of-service code point type";
       }
       leaf table-index {
         type uint32;
         description
           "Table index";
       }
       container classifier-map {
         list classifier-map-item {
           leaf code-point {
             type string;
             description
               "Class-of-service code point alias name or bits";
           }
           leaf fc-name {
             type string;
             description
               "Class-of-service forwarding class name";
           }
           leaf loss-priority {
             type string;
             description
               "Class-of-service loss priority";
           }
           leaf cntag-present {
             type string;
             description
               "Class-of-service cntag present";
           }
         }
       }
     }
   }
   grouping cos-rewrite-information-block {
     list rewrite {
       description
         "Class-of-service drop profile";
       leaf rewrite-name {
         type string;
         description
           "Class-of-service rewrite rule name";
       }
       leaf code-point-type {
         type string;
         description
           "Class-of-service code point type";
       }
       leaf table-index {
         type uint32;
         description
           "Table index";
       }
       container rewrite-map {
         list rewrite-map-item {
           leaf fc-name {
             type string;
             description
               "Class-of-service forwarding class name";
           }
           leaf loss-priority {
             type string;
             description
               "Class-of-service loss priority";
           }
           leaf code-point {
             type string;
             description
               "Class-of-service code point alias name or bits";
           }
         }
       }
     }
   }
   grouping cos-scheduler-map-information-block {
     list scheduler-map {
       description
         "Class-of-service scheduler map";
       leaf scheduler-map-name {
         type string;
         description
           "Class-of-service scheduler map name";
       }
       leaf scheduler-map-index {
         type uint64;
         description
           "Class-of-service scheduler map index";
       }
       leaf user-plane-name {
         type string;
         description
           "Class-of-service user-plane name for XDA";
       }
       list scheduler {
         leaf scheduler-name {
           type string;
           description
             "Class-of-service scheduler name";
         }
         leaf fc-name {
           type string;
           description
             "Class-of-service forwarding class name";
         }
         leaf scheduler-index {
           type uint64;
           description
             "Class of service scheduler index";
         }
         leaf scheduler-tx-rate {
           type string;
           description
             "Class-of-service scheduler transmit rate";
         }
         leaf scheduler-tx-limit {
           type string;
           description
             "Class-of-service scheduler transmit limit";
         }
         leaf scheduler-buffer-size {
           type string;
           description
             "Class-of-service scheduler buffer size";
         }
         leaf scheduler-buffer-multicast-share {
           type uint32;
           description
             "Class-of-service scheduler multicast buffer share";
         }
         leaf scheduler-buffer-limit {
           type string;
           description
             "Class-of-service scheduler buffer limit";
         }
         leaf scheduler-buffer-rate {
           type string;
           description
             "Class-of-service scheduler buffer rate";
         }
         leaf scheduler-shared-buffer-maximum-percentage {
           type uint32;
           description
             "Shared Buffer maximum percentage";
         }
         leaf scheduler-shared-buffer-multicast-maximum-percentage {
           type uint32;
           description
             "Shared Buffer multicast maximum percentage";
         }
         leaf scheduler-buffer-dynamic-threshold {
           type uint32;
           description
             "Queue shared-buffer dynamic threshold";
         }
         leaf scheduler-priority {
           type string;
           description
             "Class-of-service scheduler priority";
         }
         leaf scheduler-shaping-rate {
           type string;
           description
             "Class-of-service scheduler shaping rate";
         }
         leaf scheduler-shaping-rate-burst {
           type string;
           description
             "Class-of-service scheduler shaping rate burst";
         }
         leaf scheduler-adjust-minimum {
           type int32;
           description
             "Class-of-service scheduler adjustment minimum rate";
         }
         leaf scheduler-adjust-percent {
           type int32;
           description
             "Class-of-service scheduler percent adjustment for a queue";
         }
         leaf scheduler-excess-priority {
           type string;
           description
             "Class-of-service scheduler excess priority";
         }
         leaf scheduler-excess-rate {
           type string;
           description
             "Class-of-service scheduler excess rate";
         }
         leaf scheduler-explicit-congestion-notification {
           type string;
           description
             "Class-of-service ECN status of queue";
         }
         leaf scheduler-ecn-rtlog-rate-limit {
           type uint32;
           description
             "Class-of-service ECN Security Log Rate Limit";
         }
         leaf scheduler-ecn-no-pfc-assist {
           type string;
           description
             "Class-of-service ECN no pfc assist";
         }
         leaf scheduler-latency-ecn {
           type string;
           description
             "Latency based ECN";
         }
         leaf scheduler-latency-ecn-threshold {
           type uint32;
           description
             "Latency threshold";
         }
         leaf scheduler-queue-monitoring {
           type string;
           description
             "Class-of-service queue depth monitoring of queue";
         }
         leaf scheduler-drop-profile-ln-index {
           type uint32;
           description
             "Class-of-service scheduler drop profile index low, non-TCP";
         }
         leaf scheduler-drop-profile-ln {
           type string;
           description
             "Class-of-service scheduler drop profile low, non-TCP";
         }
         leaf scheduler-drop-profile-lt-index {
           type uint32;
           description
             "Class-of-service scheduler drop profile index low, TCP";
         }
         leaf scheduler-drop-profile-lt {
           type string;
           description
             "Class-of-service scheduler drop profile low, TCP";
         }
         leaf scheduler-drop-profile-hn-index {
           type uint32;
           description
             "Class-of-service scheduler drop profile index high, non-TCP";
         }
         leaf scheduler-drop-profile-hn {
           type string;
           description
             "Class-of-service scheduler drop profile high, non-TCP";
         }
         leaf scheduler-drop-profile-ht-index {
           type uint32;
           description
             "Class-of-service scheduler drop profile index high, TCP";
         }
         leaf scheduler-drop-profile-ht {
           type string;
           description
             "Class-of-service scheduler drop profile high, TCP";
         }
         leaf scheduler-drop-profile-la-index {
           type uint32;
           description
             "Class-of-service scheduler drop profile index low";
         }
         leaf scheduler-drop-profile-la {
           type string;
           description
             "Class-of-service scheduler drop profile low";
         }
         leaf scheduler-drop-profile-ma-index {
           type uint32;
           description
             "Class-of-service scheduler drop profile index medium";
         }
         leaf scheduler-drop-profile-ma {
           type string;
           description
             "Class-of-service scheduler drop profile medium";
         }
         leaf scheduler-drop-profile-mla-index {
           type uint32;
           description
             "Class-of-service scheduler drop profile index medium-low";
         }
         leaf scheduler-drop-profile-mla {
           type string;
           description
             "Class-of-service scheduler drop profile medium-low";
         }
         leaf scheduler-drop-profile-mha-index {
           type uint32;
           description
             "Class-of-service scheduler drop profile index medium-high";
         }
         leaf scheduler-drop-profile-mha {
           type string;
           description
             "Class-of-service scheduler drop profile medium-high";
         }
         leaf scheduler-drop-profile-ha-index {
           type uint32;
           description
             "Class-of-service scheduler drop profile index high";
         }
         leaf scheduler-drop-profile-ha {
           type string;
           description
             "Class-of-service scheduler drop profile high";
         }
       }
     }
   }
   grouping cos-traffic-control-profile-information-block {
     list traffic-control-profile {
       description
         "Information about one or more traffic control profiles";
       leaf traffic-control-profile-name {
         type string;
         description
           "Class-of-service traffic control profile name";
       }
       leaf traffic-control-profile-index {
         type uint64;
         description
           "Index number for Class-of-service traffic control profile";
       }
       leaf user-plane-name {
         type string;
         description
           "Class-of-service user-plane name for XDA";
       }
       leaf scheduler-map-name {
         type string;
         description
           "Class-of-service scheduler map name";
       }
       leaf atm-service {
         type string;
         description
           "Class-of-service traffic control profile atm service";
       }
       leaf shaping-rate {
         type uint64;
         description
           "Class-of-service shaping rate";
       }
       leaf shaping-rate-burst {
         type uint32;
         description
           "Class-of-service shaping rate burst, in bytes";
       }
       leaf low-granularity {
         type uint32;
         description
           "Class-of-service low-granularity mode support";
       }
       leaf queue-mode-4q {
         type uint32;
         description
           "Class-of-service tcp-voq-mode(4Q) mode support";
       }
       leaf shaping-rate-priority-strict-high {
         type uint64;
         description
           "Class-of-service shaping rate for priority strict high";
       }
       leaf shaping-rate-priority-strict-high-burst {
         type uint32;
         description
           "Class-of-service shaping rate burst for priority strict-high";
       }
       leaf shaping-rate-priority-high {
         type uint64;
         description
           "Class-of-service shaping rate for priority high";
       }
       leaf shaping-rate-priority-high-burst {
         type uint32;
         description
           "Class-of-service shaping rate for priority high burst";
       }
       leaf shaping-rate-priority-medium {
         type uint64;
         description
           "Class-of-service shaping rate for priority medium";
       }
       leaf shaping-rate-priority-medium-burst {
         type uint32;
         description
           "Class-of-service shaping rate for priority medium burst";
       }
       leaf shaping-rate-priority-medium-low {
         type uint64;
         description
           "Class-of-service shaping rate for priority medium-low";
       }
       leaf shaping-rate-priority-medium-low-burst {
         type uint32;
         description
           "Class-of-service shaping rate burst for priority medium-low";
       }
       leaf shaping-rate-priority-low {
         type uint64;
         description
           "Class-of-service shaping rate for priority low";
       }
       leaf shaping-rate-priority-low-burst {
         type uint32;
         description
           "Class-of-service shaping rate for priority low burst";
       }
       leaf shaping-rate-excess-high {
         type uint64;
         description
           "Class-of-service shaping rate for excess high";
       }
       leaf shaping-rate-excess-high-burst {
         type uint32;
         description
           "Class-of-service shaping rate for excess high burst";
       }
       leaf shaping-rate-excess-medium-high {
         type uint64;
         description
           "Class-of-service shaping rate for excess medium-high";
       }
       leaf shaping-rate-excess-medium-high-burst {
         type uint32;
         description
           "Class-of-service shaping rate burst for excess medium-high";
       }
       leaf shaping-rate-excess-medium-low {
         type uint64;
         description
           "Class-of-service shaping rate for excess medium-low";
       }
       leaf shaping-rate-excess-medium-low-burst {
         type uint32;
         description
           "Class-of-service shaping rate burst for excess medium-low";
       }
       leaf shaping-rate-excess-low {
         type uint64;
         description
           "Class-of-service shaping rate for excess low";
       }
       leaf shaping-rate-excess-low-burst {
         type uint32;
         description
           "Class-of-service shaping rate for excess low burst";
       }
       leaf guaranteed-rate {
         type uint64;
         description
           "Class-of-service guaranteed rate";
       }
       leaf guaranteed-rate-burst {
         type uint32;
         description
           "Class-of-service guaranteed rate burst, in bytes";
       }
       leaf delay-buffer-rate {
         type uint64;
         description
           "Class-of-service delay buffer rate";
       }
       leaf excess-rate {
         type uint32;
         description
           "Class-of-service excess rate";
       }
       leaf excess-rate-high {
         type uint32;
         description
           "Class-of-service excess rate for excess-high priority traffic";
       }
       leaf excess-rate-medium-high {
         type uint32;
         description
           "Class-of-service excess rate for excess-medium-high priority 
           traffic";
       }
       leaf excess-rate-medium-low {
         type uint32;
         description
           "Class-of-service excess rate for excess-medium-low priority 
           traffic";
       }
       leaf excess-rate-low {
         type uint32;
         description
           "Class-of-service excess rate for excess-low priority traffic";
       }
       leaf adjust-minimum {
         type uint64;
         description
           "Class-of-service adjustment minimum rate";
       }
       leaf overhead-bytes {
         type int32;
         description
           "Class-of-service Overhead bytes";
       }
       leaf frame-mode-bytes {
         type int32;
         description
           "Class-of-service overhead bytes when in frame-mode";
       }
       leaf cell-mode-bytes {
         type int32;
         description
           "Class-of-service overhead bytes when in cell-mode";
       }
       leaf overhead-accounting-mode {
         type string;
         description
           "Class-of-service Overhead Accounting Mode";
       }
       list traffic-control-profile-instance {
         description
           "Class-of-service traffic control profile instance";
         leaf traffic-control-profile-instance-name {
           type string;
           description
             "Class-of-service traffic control profile instance";
         }
         leaf traffic-control-profile-instance-index {
           type uint32;
           description
             "Index number for Class-of-service traffic control profile 
             instance";
         }
         leaf instance-reference-count {
           type uint32;
           description
             "Instance reference count";
         }
       }
     }
   }
   grouping cos-interface-information-block {
     list interface-information {
       list physical-interface {
         key "name";
         description
           "Information about a single physical interface";
         leaf cascade-port-satellite-device-slot-identifier {
           type int32;
           description
             "Slot id of a Satellite Device on a Cascade Port";
         }
         leaf lcp-state {
           type string;
           description
             "State of the Line Control Protocol";
         }
         leaf chap-state {
           type string;
           description
             "State of the Challenge Handshake Authentication Protocol";
         }
         leaf pap-state {
           type string;
           description
             "State of the Password Authentication Protocol";
         }
         leaf name {
           type string;
           description
             "Name of this item";
         }
         leaf mc-ae-status {
           type string;
         }
         leaf admin-status {
           type string;
           description
             "Desired state of the interface";
         }
         leaf oper-status {
           type string;
           description
             "Current operational state of the interface";
         }
         leaf extended-port-multi-homed {
           type string;
           description
             "EP Mutli-homed information";
         }
         leaf local-index {
           type int32;
           description
             "Local kernel index for this interface";
         }
         leaf snmp-index {
           type int32;
           description
             "SNMP ifIndex for this interface";
         }
         leaf generation {
           type int32;
           description
             "Generation number used to distinguish between successive 
             instances of this interface";
         }
         leaf description {
           type string;
           description
             "Description of this interface";
         }
         leaf if-type {
           type string;
         }
         leaf link-level-type {
           type string;
           description
             "Encapsulation being used on the physical interface";
         }
         leaf link-media-type {
           type string;
           description
             "PHY Medium type on the physical interface";
         }
         leaf mtu {
           type string;
           description
             "MTU size on this interface";
         }
         leaf mru {
           type string;
           description
             "MRU size on this interface";
         }
         leaf clocking {
           type string;
           description
             "Reference clock source";
         }
         leaf max-speed {
           type string;
           description
             "Maximum speed at which interface can run";
         }
         leaf sonet-mode {
           type string;
           description
             "Whether the interface is in SDH or SONET mode";
         }
         leaf physical-mode {
           type string;
           description
             "Physical mode";
         }
         leaf l2circuit-mode {
           type string;
           description
             "Indicates if the interface is in L2 circuit AAL5 or Cell mode";
         }
         leaf ifd-cell-bundle-size {
           type string;
           description
             "Cell bundle size for physical interface";
         }
         leaf ifd-cell-bundle-timeout {
           type string;
           description
             "Cell bundle timeout for physical interface";
         }
         leaf link-mode {
           type string;
           description
             "Link mode of the interface";
         }
         leaf mac-mode {
           type string;
           description
             "MAC Mode of the interface";
         }
         leaf speed {
           type string;
           description
             "Speed at which the interface is running";
         }
         leaf duplex {
           type string;
           description
             "Duplex at which the interface is running";
         }
         leaf if-unidirectional {
           type string;
         }
         leaf bpdu-error {
           type string;
         }
         leaf ld-pdu-error {
           type string;
         }
         leaf eth-switch-error {
           type string;
         }
         leaf l2pt-error {
           type string;
         }
         leaf loopback {
           type string;
           description
             "Whether loopback is enabled and the type of loopback";
         }
         leaf optics-loopback {
           type string;
           description
             "Whether optical loopback is enabled";
         }
         leaf sonet-loopback {
           type string;
           description
             "SONET loopback setting on channelized OC12 interface";
         }
         leaf crc {
           type string;
           description
             "Frame checksum on the interface (either 16 or 32)";
         }
         leaf payload-scrambler {
           type string;
           description
             "Whether payload scrambling is enabled";
         }
         leaf source-filtering {
           type string;
           description
             "Whether source filtering is enabled or disabled";
         }
         leaf if-flow-control {
           type string;
         }
         leaf if-speed-cfg {
           type string;
         }
         leaf if-configured-flow-control-rx-buffers {
           type string;
         }
         leaf if-configured-flow-control-tx-buffers {
           type string;
         }
         leaf if-auto-negotiation {
           type string;
           description
             "Status of auto-negotiation";
         }
         leaf if-remote-fault {
           type string;
           description
             "Status of remote fault";
         }
         leaf if-media-type {
           type string;
           description
             "Media-type copper or fiber";
         }
         leaf if-speed-auto-negotiation {
           type string;
           description
             "Status of Speed auto-negotiation";
         }
         leaf ieee-802-3az-eee {
           type string;
           description
             "IEEE 802.3az Energy Efficient Ethernet";
         }
         leaf if-auto-mdix {
           type string;
           description
             "Status of Auto MDIX";
         }
         leaf ingress-rate-limit {
           type int32;
           description
             "Layer 2 rate limit on ingress traffic for the port";
         }
         leaf minimum-links-in-aggregate {
           type int32;
           description
             "Minimum number of links needed for the bundle to be up";
         }
         leaf minimum-bandwidth-in-aggregate {
           type int32;
           description
             "Minimum bandwidth needed for the bundle to be up";
         }
         leaf ds3-mode {
           type string;
         }
         leaf ds3-long-buildout {
           type string;
         }
         leaf e3-framing {
           type string;
         }
         leaf ds1-framing {
           type string;
         }
         leaf atm-line-build-out {
           type int32;
           description
             "Line buildout";
         }
         leaf atm-encapsulation {
           type string;
           description
             "Type of ATM encapsulation";
         }
         leaf atm-e3-framing {
           type string;
           description
             "Type of framing";
         }
         leaf ih-parent {
           type string;
           description
             "Controller parent";
         }
         leaf physical-information {
           type string;
         }
         leaf link-type {
           type string;
         }
         leaf up-hold-time {
           type int32;
           description
             "Up hold-time for this interface (milliseconds)";
         }
         leaf down-hold-time {
           type int32;
           description
             "Down hold-time for this interface (milliseconds)";
         }
         leaf damp-half-life {
           type int32;
           description
             "Dampening half-life time for this interface (seconds)";
         }
         leaf damp-max-suppress {
           type int32;
           description
             "Dampening max suppress time for this interface (seconds)";
         }
         leaf damp-reuse-level {
           type int32;
           description
             "Reuse threshold";
         }
         leaf damp-suppress-level {
           type int32;
           description
             "Suppress threshold";
         }
         leaf damp-suppress-state {
           type string;
           description
             "Suppress state";
         }
         leaf current-physical-address {
           type string;
           description
             "Configured physical address for this interface";
         }
         leaf hardware-physical-address {
           type string;
           description
             "Hardware physical address for this interface";
         }
         leaf esi-value {
           type string;
           description
             "Ethernet segment identifier for this interface";
         }
         leaf esi-mode {
           type string;
           description
             "Ethernet segment mode for this interface";
         }
         leaf alternate-physical-address {
           type string;
           description
             "Alternate physical address for this interface";
         }
         leaf input-error-count {
           type int32;
           description
             "Sum of all input errors on this interface";
         }
         leaf output-error-count {
           type int32;
           description
             "Sum of all output errors on this interface";
         }
         leaf interface-flapped {
           type string;
           description
             "Time when the interface last flapped";
         }
         leaf statistics-cleared {
           type string;
           description
             "Time when statistics were last cleared";
         }
         leaf fec-mode {
           type string;
           description
             "Optics FEC mode";
         }
         leaf laser-enable {
           type string;
           description
             "Optics laser status";
         }
         leaf high-polarization {
           type string;
           description
             "Optics high polarization";
         }
         leaf interface-transmit-statistics {
           type string;
           description
             "Interface statistics based on transmitted packets";
         }
         leaf pad-to-minimum-frame-size {
           type string;
           description
             "Pad Tx vlan tagged frame to minimum of 68 bytes";
         }
         leaf preserve-interface {
           type string;
           description
             "Whether interface preservation is enabled or disabled";
         }
         leaf sonet-rx-overhead {
           type string;
         }
         leaf sonet-tx-overhead {
           type string;
         }
         leaf sonet-rx-path-trace {
           type string;
           description
             "Received SONET path trace";
         }
         leaf sonet-tx-path-trace {
           type string;
           description
             "Transmitted SONET path trace";
         }
         leaf otn-rx-overhead {
           type string;
         }
         leaf otn-tx-overhead {
           type string;
         }
         leaf otn-stats-counter {
           type string;
         }
         leaf otn-rx-tti {
           type string;
         }
         leaf otn-tx-tti {
           type string;
         }
         leaf port-forwarding-mode {
           type string;
           description
             "Port forwarding mode";
         }
         leaf cos-header {
           type empty;
         }
         leaf precl-header {
           type empty;
         }
         leaf esi-source-bmac {
           type jt:mac-addr;
           description
             "Ethernet segment source B-MAC for this interface";
         }
         leaf sonet-payload-pointer-curptr {
           type string;
           description
             "Value of the SONET/SDH payload pointer, derived from the H1 
             and H2 overhead bytes";
         }
         leaf sonet-payload-pointer-ptrinc-count {
           type string;
           description
             "Number of times the value of the SONET/SDH payload pointer had
             positive justification";
         }
         leaf sonet-payload-pointer-ptrdec-count {
           type string;
           description
             "Number of times the value of the SONET/SDH payload pointer had
             negative justification";
         }
         leaf sonet-payload-pointer-newptr-ndf-count {
           type string;
           description
             "Number of times a new payload pointer was created with the New
             Data Found flag set";
         }
         leaf link-partner-status {
           type string;
           description
             "Auto-negotiation status of link partner";
         }
         container if-device-flags {
           leaf ifdf-none {
             type empty;
           }
           leaf ifdf-present {
             type empty;
           }
           leaf ifdf-running {
             type empty;
           }
           leaf ifdf-duplex {
             type empty;
           }
           leaf ifdf-down {
             type empty;
           }
           leaf ifdf-no-carrier {
             type empty;
           }
           leaf ifdf-error1 {
             type empty;
           }
           leaf ifdf-error2 {
             type empty;
           }
           leaf ifdf-no-multicast {
             type empty;
           }
           leaf ifdf-loopback {
             type empty;
           }
           leaf ifdf-quench {
             type empty;
           }
           leaf ifdf-recv-all-multicasts {
             type empty;
           }
           leaf ifdf-promiscuous {
             type empty;
           }
           leaf ifdf-link-layer-down {
             type empty;
           }
           leaf ifdf-loop-detected {
             type empty;
           }
           leaf ifdf-pfe-gone {
             type empty;
           }
           leaf generic-value {
             type int32;
             description
               "Hexadecimal value of unknown flag bits";
           }
         }
         container if-config-flags {
           leaf iff-none {
             type empty;
           }
           leaf iff-hardware-down {
             type empty;
           }
           leaf iff-down {
             type empty;
           }
           leaf iff-up {
             type empty;
           }
           leaf iff-admin-down {
             type empty;
           }
           leaf iff-admin-up {
             type empty;
           }
           leaf iff-link-down {
             type empty;
           }
           leaf iff-device-down {
             type empty;
           }
           leaf iff-point-to-point {
             type empty;
           }
           leaf iff-point-to-multipoint {
             type empty;
           }
           leaf plp-to-clp {
             type empty;
           }
           leaf iff-multiaccess {
             type empty;
           }
           leaf iff-change {
             type empty;
           }
           leaf iff-inverse-arp {
             type empty;
           }
           leaf iff-no-multicast {
             type empty;
           }
           leaf iff-multicast {
             type empty;
           }
           leaf iff-promiscuous {
             type empty;
           }
           leaf iff-all-multicast {
             type empty;
           }
           leaf iff-snmp-traps {
             type empty;
           }
           leaf iff-rx-passive {
             type empty;
           }
           leaf iff-tx-passive {
             type empty;
           }
           leaf iff-ccc-down {
             type empty;
           }
           leaf iff-clear-df {
             type empty;
           }
           leaf iff-tunnel-reassembly {
             type empty;
           }
           leaf iff-acfc {
             type empty;
           }
           leaf iff-pfc {
             type empty;
           }
           leaf iff-rdd {
             type empty;
           }
           leaf iff-looped {
             type empty;
           }
           leaf iff-framing-conflict {
             type empty;
           }
           leaf internal-flags {
             type int32;
             description
               "Hexadecimal value of internal flag bits";
           }
         }
         container ifd-specific-config-flags {
           leaf ifdspf-none {
             type empty;
           }
           leaf ifdspf-multicast-statistics {
             type empty;
           }
           leaf ifdspf-oam-on-svlan {
             type empty;
           }
           leaf internal-flags {
             type int32;
             description
               "Hexadecimal value of internal flag bits";
           }
         }
         container shared-interface-physical-interface {
           description
             "Shared interface physical interface";
           leaf ownership {
             type string;
             description
               "Shared interface physical interface ownership";
           }
         }
         container if-media-flags {
           leaf ifmf-none {
             type empty;
           }
           leaf ifmf-autoselect {
             type empty;
           }
           leaf ifmf-scheduler {
             type empty;
           }
           leaf ifmf-shared-scheduler {
             type empty;
           }
           leaf ifmf-vlan-offload {
             type empty;
           }
           leaf ifmf-keepalives {
             type empty;
           }
           leaf ifmf-no-keepalives {
             type empty;
           }
           leaf ifmf-give-up {
             type empty;
           }
           leaf ifmf-loose-lcp {
             type empty;
           }
           leaf ifmf-loose-ncp {
             type empty;
           }
           leaf ifmf-ppp-acfc {
             type empty;
           }
           leaf ifmf-ppp-pfc {
             type empty;
           }
           leaf ifmf-loose-lmi {
             type empty;
           }
           leaf ifmf-dce {
             type empty;
           }
           leaf ifmf-dte {
             type empty;
           }
           leaf generic-value {
             type int32;
             description
               "Hexadecimal value of unknown flag bits";
           }
           leaf internal-flags {
             type int32;
             description
               "Hexadecimal value of internal flag bits";
           }
         }
         container optics-properties {
           description
             "Optics properties";
           leaf wavelength {
             type string;
             description
               "Wavelength of optics in nanometers";
           }
           leaf frequency {
             type string;
             description
               "Frequency of optics in terahertz";
           }
         }
         container keepalive-config {
           description
             "Configured keepalive settings on this interface";
           leaf keepalive-interval {
             type int32;
           }
           leaf keepalive-up-count {
             type int32;
           }
           leaf keepalive-down-count {
             type int32;
           }
         }
         container lmi-dce-config {
           description
             "Configured LMI DCE setting on this interface";
           leaf lmi-type {
             type string;
           }
           leaf lmi-n392dce {
             type int32;
           }
           leaf lmi-n393dce {
             type int32;
           }
           leaf lmi-t392dce {
             type int32;
           }
         }
         container lmi-dte-config {
           description
             "Configured LMI DTE setting on this interface";
           leaf lmi-type {
             type string;
           }
           leaf lmi-n391dte {
             type int32;
           }
           leaf lmi-n392dte {
             type int32;
           }
           leaf lmi-n393dte {
             type int32;
           }
           leaf lmi-t391dte {
             type int32;
           }
         }
         container queue-counters {
           description
             "Queue counter statistics";
           leaf queue-counters-error-message {
             type string;
             description
               "Queue statistics not available for this interface";
           }
           list queue {
             description
               "Counters for a single queue";
             leaf queue-number {
               type int32;
               description
                 "Queue number";
             }
             leaf queue-counters-queued-packets {
               type uint64;
               description
                 "Queued packet count";
             }
             leaf queue-counters-trans-packets {
               type uint64;
               description
                 "Total number of transmitted packets";
             }
             leaf queue-counters-total-drop-packets {
               type uint64;
               description
                 "Number of total packets dropped at the queue";
             }
             leaf forwarding-class-name {
               type string;
               description
                 "Forwarding class name associated with queue";
             }
             leaf queue-counters-queued-packets-rate {
               type uint64;
               description
                 "Rate at which packets are queued";
             }
             leaf queue-counters-queued-bytes {
               type uint64;
               description
                 "Queued bytes count";
             }
             leaf queue-counters-queued-bytes-rate {
               type uint64;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets-rate {
               type uint64;
               description
                 "Rate at which packets are transmitted";
             }
             leaf queue-counters-trans-bytes {
               type uint64;
               description
                 "Total number of transmitted bytes";
             }
             leaf queue-counters-trans-bytes-rate {
               type uint64;
               description
                 "Rate at which bytes are transmitted";
             }
             leaf queue-counters-tail-drop-packets-na {
               type string;
               description
                 "Number of packets dropped due to tail drop not available";
             }
             leaf queue-counters-tail-drop-packets {
               type uint64;
               description
                 "Number of packets dropped at the tail of the queue";
             }
             leaf queue-counters-tail-drop-packets-rate {
               type uint64;
               description
                 "Rate at which packets are dropped at tail of queue";
             }
             leaf queue-counters-tail-drop-bytes {
               type uint64;
               description
                 "Number of packets dropped at tail drop of the queue";
             }
             leaf queue-counters-tail-drop-bytes-rate {
               type uint64;
               description
                 "Number of packets dropped at tail drop of the queue";
             }
             leaf queue-counters-rate-limit-drop-packets-na {
               type string;
               description
                 "Number of packets dropped due to rate-limit drop not 
                 available";
             }
             leaf queue-counters-rate-limit-drop-packets {
               type uint64;
               description
                 "Number of packets dropped by rate-limit for the queue";
             }
             leaf queue-counters-rate-limit-drop-packets-rate {
               type uint64;
               description
                 "Rate at which packets are dropped by rate-limit for the 
                 queue";
             }
             leaf queue-counters-rate-limit-drop-bytes-na {
               type string;
               description
                 "Number of bytes dropped due to tail drop not available";
             }
             leaf queue-counters-rate-limit-drop-bytes {
               type uint64;
               description
                 "Number of bytes dropped at the tail of the queue";
             }
             leaf queue-counters-rate-limit-drop-bytes-rate {
               type uint64;
               description
                 "Rate at which bytes are dropped at the tail of the queue";
             }
             leaf queue-counters-red-packets-na {
               type string;
               description
                 "Number of packets dropped due to RED not available";
             }
             leaf queue-counters-red-packets {
               type uint64;
               description
                 "Number of packets dropped due to RED";
             }
             leaf queue-counters-red-packets-rate {
               type uint64;
               description
                 "Rate at which packets are dropped due to RED";
             }
             leaf queue-counters-red-packets-ln {
               type uint64;
               description
                 "Number of RED dropped low-loss, non-TCP packets";
             }
             leaf queue-counters-red-packets-rate-ln {
               type uint64;
               description
                 "RED drop rate for low-loss, non-TCP packets";
             }
             leaf queue-counters-red-packets-lt {
               type uint64;
               description
                 "Number of RED dropped of low-loss, TCP packets";
             }
             leaf queue-counters-red-packets-rate-lt {
               type uint64;
               description
                 "RED drop rate for low-loss, TCP packets";
             }
             leaf queue-counters-red-packets-hn {
               type uint64;
               description
                 "Number of RED dropped high-loss, non-TCP packets";
             }
             leaf queue-counters-red-packets-rate-hn {
               type uint64;
               description
                 "RED drop rate for high-loss, non-TCP packets";
             }
             leaf queue-counters-red-packets-ht {
               type uint64;
               description
                 "Number of RED dropped high-loss, TCP packets";
             }
             leaf queue-counters-red-packets-rate-ht {
               type uint64;
               description
                 "RED drop rate for high-loss, TCP packets";
             }
             leaf queue-counters-red-packets-low {
               type uint64;
               description
                 "Number of RED dropped low-loss packets";
             }
             leaf queue-counters-red-packets-rate-low {
               type uint64;
               description
                 "RED drop rate for low-loss packets";
             }
             leaf queue-counters-red-packets-medium-low {
               type uint64;
               description
                 "Number of RED dropped medium-low-loss packets";
             }
             leaf queue-counters-red-packets-rate-medium-low {
               type uint64;
               description
                 "RED drop rate for medium-low-loss packets";
             }
             leaf queue-counters-red-packets-medium-high {
               type uint64;
               description
                 "Number of RED dropped medium-high-loss packets";
             }
             leaf queue-counters-red-packets-rate-medium-high {
               type uint64;
               description
                 "RED drop rate for medium-high-loss packets";
             }
             leaf queue-counters-red-packets-medium {
               type uint64;
               description
                 "Number of RED dropped medium-loss packets";
             }
             leaf queue-counters-red-packets-rate-medium {
               type uint64;
               description
                 "RED drop rate for medium-loss packets";
             }
             leaf queue-counters-red-packets-high {
               type uint64;
               description
                 "Number of RED dropped high-loss packets";
             }
             leaf queue-counters-red-packets-rate-high {
               type uint64;
               description
                 "RED drop rate for high-loss packets";
             }
             leaf queue-counters-red-bytes-na {
               type string;
               description
                 "Number of bytes dropped due to RED not available";
             }
             leaf queue-counters-red-bytes {
               type uint64;
               description
                 "Number of bytes dropped due to RED";
             }
             leaf queue-counters-red-bytes-rate {
               type uint64;
               description
                 "Rate at which bytes are dropped due to RED";
             }
             leaf queue-counters-red-bytes-ln {
               type uint64;
               description
                 "Number of RED dropped low-loss, non-TCP bytes";
             }
             leaf queue-counters-red-bytes-rate-ln {
               type uint64;
               description
                 "RED drop rate for low-loss, non-TCP bytes";
             }
             leaf queue-counters-red-bytes-lt {
               type uint64;
               description
                 "Number of RED dropped low-loss, TCP bytes";
             }
             leaf queue-counters-red-bytes-rate-lt {
               type uint64;
               description
                 "RED drop rate for low-loss, TCP bytes";
             }
             leaf queue-counters-red-bytes-hn {
               type uint64;
               description
                 "Number of RED dropped high-loss, non-TCP bytes";
             }
             leaf queue-counters-red-bytes-rate-hn {
               type uint64;
               description
                 "RED drop rate for high-loss, non-TCP bytes";
             }
             leaf queue-counters-red-bytes-ht {
               type uint64;
               description
                 "Number of RED dropped high-loss, TCP bytes";
             }
             leaf queue-counters-red-bytes-rate-ht {
               type uint64;
               description
                 "RED drop rate for high-loss, TCP bytes";
             }
             leaf queue-counters-red-bytes-low {
               type uint64;
               description
                 "Number of RED dropped low-loss bytes";
             }
             leaf queue-counters-red-bytes-rate-low {
               type uint64;
               description
                 "RED drop rate for low-loss bytes";
             }
             leaf queue-counters-red-bytes-medium-low {
               type uint64;
               description
                 "Number of RED dropped medium-low-loss bytes";
             }
             leaf queue-counters-red-bytes-rate-medium-low {
               type uint64;
               description
                 "RED drop rate for medium-low-loss bytes";
             }
             leaf queue-counters-red-bytes-medium-high {
               type uint64;
               description
                 "Number of RED dropped medium-high-loss bytes";
             }
             leaf queue-counters-red-bytes-rate-medium-high {
               type uint64;
               description
                 "RED drop rate for medium-high-loss bytes";
             }
             leaf queue-counters-red-bytes-medium {
               type uint64;
               description
                 "Number of RED dropped medium-loss bytes";
             }
             leaf queue-counters-red-bytes-rate-medium {
               type uint64;
               description
                 "RED drop rate for medium-loss bytes";
             }
             leaf queue-counters-red-bytes-high {
               type uint64;
               description
                 "Number of RED dropped high-loss bytes";
             }
             leaf queue-counters-red-bytes-rate-high {
               type uint64;
               description
                 "RED drop rate for high-loss bytes";
             }
             leaf queue-counters-timestamp {
               type uint64;
               description
                 "Last packet enqueued timestamp";
             }
             leaf queue-counters-total-drop-packets-rate {
               type uint64;
               description
                 "Number of total packets dropped at the queue";
             }
             leaf queue-counters-total-drop-bytes {
               type uint64;
               description
                 "Number of total packets dropped at the queue";
             }
             leaf queue-counters-total-drop-bytes-rate {
               type uint64;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-short-summary {
             description
               "Summary of queue information on an interface";
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
         }
         container voq-counters {
           description
             "VOQ counter statistics";
           leaf voq-counters-error-message {
             type string;
             description
               "VOQ statistics not available for this interface";
           }
           container voq {
             description
               "Counters for a single voq";
             container fpc {
               description
                 "Counters for a single FPC";
               leaf fpc-no {
                 type int32;
                 description
                   "FPC number";
               }
               container pfe {
                 description
                   "Counters for a single PFE";
                 leaf-list pfe-no {
                   type int32;
                   description
                     "PFE number";
                 }
                 leaf voq-counters-tail-drop-packets {
                   type int32;
                   description
                     "Tail DROP packet count";
                 }
                 leaf voq-counters-tail-drop-packets-rate {
                   type int32;
                   description
                     "Rate at which tail packets are dropped";
                 }
                 leaf voq-counters-tail-drop-bytes {
                   type int32;
                   description
                     "Tail DROP bytes count";
                 }
                 leaf voq-counters-tail-drop-bytes-rate {
                   type int32;
                   description
                     "Rate at which tail bytes are dropped";
                 }
                 leaf voq-counters-drop-packets {
                   type int32;
                   description
                     "DROP packet count";
                 }
                 leaf voq-counters-drop-packets-rate {
                   type int32;
                   description
                     "Rate at which packets are dropped";
                 }
                 leaf voq-counters-drop-bytes {
                   type int32;
                   description
                     "DROP bytes count";
                 }
                 leaf voq-counters-drop-bytes-rate {
                   type int32;
                   description
                     "Rate at which bytes are dropped";
                 }
               }
             }
             leaf queue-number {
               type int32;
               description
                 "Queue number";
             }
             leaf forwarding-class-name {
               type string;
               description
                 "Forwarding class name associated with queue";
             }
           }
         }
         container smart-sfp-av-titan-statistics {
           description
             "AimValley Smart SFP statistics";
           leaf smart-sfp-av-titan-error-message {
             type string;
             description
               "AV Smart SFP un-available";
           }
           container smart-sfp-av-titan-eth-port-statistics {
             leaf rx-crct-frames {
               type uint32;
             }
             leaf rx-crct-bytes {
               type uint32;
             }
             leaf rx-fragments {
               type uint32;
             }
             leaf rx-crct-unicast-frames {
               type uint32;
             }
             leaf rx-crct-multicast-frames {
               type uint32;
             }
             leaf rx-crct-broadcast-frames {
               type uint32;
             }
             leaf rx-err-fcs-frames {
               type uint32;
             }
             leaf rx-len-err-frames {
               type uint32;
             }
             leaf rx-undersize-frames {
               type uint32;
             }
             leaf rx-oversize-frames {
               type uint32;
             }
             leaf rx-inv-vlan-mismatch-frames {
               type uint32;
             }
             leaf rx-discarded-frames {
               type uint32;
             }
             leaf rx-dropped-q-overflow-frames {
               type uint32;
             }
             leaf tx-frames {
               type uint32;
             }
             leaf tx-bytes {
               type uint32;
             }
             leaf tx-unicast-frames {
               type uint32;
             }
             leaf tx-multicast-frames {
               type uint32;
             }
             leaf tx-broadcast-frames {
               type uint32;
             }
           }
           container smart-sfp-av-titan-iwf-statistics {
             leaf rx-packets {
               type uint32;
             }
             leaf tx-packets {
               type uint32;
             }
             leaf malformed-packets {
               type uint32;
             }
             leaf reordered-packets {
               type uint32;
             }
             leaf misordered-dropped-packets {
               type uint32;
             }
             leaf missing-packets {
               type uint32;
             }
             leaf played-out-packets {
               type uint32;
             }
             leaf jb-overrun {
               type uint32;
             }
             leaf jb-underrun {
               type uint32;
             }
           }
           container smart-sfp-av-titan-ds3-statistics {
             leaf rx-bpvexzerrors {
               type uint32;
             }
             leaf rx-cvperrors {
               type uint32;
             }
             leaf b3-errors {
               type uint32;
             }
           }
           container smart-sfp-av-titan-stm-statistics {
             leaf rx-b1-errors {
               type uint32;
             }
             leaf tx-b1-errors {
               type uint32;
             }
           }
         }
         container smart-sfp-av-titan-defects {
           description
             "AimValley Smart SFP defects";
           container smart-sfp-av-titan-defect-list {
             leaf sfp-tdm-defects {
               type string;
             }
             leaf sfp-system-defects {
               type string;
             }
           }
         }
         container forwarding-class-counters {
           description
             "Forwarding-class counter statistics";
           leaf forwarding-class-counters-error-message {
             type string;
             description
               "Forwarding-class statistics not available for this interface";
           }
           container ipv4-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container ipv6-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container mpls-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container layer2-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container other-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container protocol-aggregate-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container forwarding-class-statistics {
             container protocol-aggregate-forwarding-class-counters {
             }
             container ipv4-forwarding-class-counters {
             }
             container ipv6-forwarding-class-counters {
             }
             container mpls-forwarding-class-counters {
             }
             container layer2-forwarding-class-counters {
             }
             container other-forwarding-class-counters {
             }
           }
           container forwarding-class-accounting-parameters {
             leaf forwarding-class-accounting-for-protocol {
               type string;
             }
             leaf forwarding-class-accounting-for-traffic-direction {
               type string;
             }
             leaf forwarding-class-accounting-for-traffic-type {
               type string;
             }
             leaf forwarding-class-accounting-overhead-bytes {
               type uint32;
             }
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container keepalive-statistics {
           description
             "Keepalive statistics for this interface";
           leaf keepalive-lmi-descriptor {
             type string;
           }
           leaf keepalive-input-count {
             type int32;
           }
           leaf keepalive-input-time {
             type string;
           }
           leaf keepalive-output-count {
             type int32;
           }
           leaf keepalive-output-time {
             type string;
           }
         }
         container ppp-flags {
           leaf iff-ppp-flags-acfc {
             type empty;
           }
           leaf iff-ppp-flags-pfc {
             type empty;
           }
         }
         list ncp-information {
           description
             "Network Control Protocol information";
           leaf ncp-protocol {
             type string;
             description
               "Network protocol for this NCP instance";
           }
           leaf ncp-state {
             type string;
             description
               "State of this NCP instance";
           }
         }
         container es-ifd-stats {
           description
             "ES PIC statistics";
           leaf total-anti-replay-count {
             type int32;
             description
               "Number of antireplay failures";
           }
           leaf total-authentication-failure-count {
             type int32;
             description
               "Number of authentication failures";
           }
         }
         container optics-bit-rate {
           leaf bit-rate {
             type string;
             description
               " Optics Bit Rate";
           }
         }
         container optics-fec-statistics {
           leaf fec-corrected-errors {
             type int32;
           }
           leaf fec-valid-time {
             type int32;
           }
           leaf fec-corrected-error-ratio {
             type int32;
           }
           leaf fec-uncorrected-words {
             type int32;
           }
         }
         container preserve-interface-statistics {
           description
             "Interface switchover statistics";
           leaf if-switchover-total {
             type int32;
             description
               "Total number of interface switchovers";
           }
           leaf if-switchover-last-attempt {
             type string;
             description
               "Interface on which the last switchover was attempted";
           }
           leaf if-switchover-last-time {
             type string;
             description
               "Time at which last interface switchover was attempted";
           }
           leaf if-switchover-min-max-avg-time {
             type string;
             description
               "Minimum, maximum and average interface switchover time";
           }
         }
         container extended-port-information {
           leaf local-port-id {
             type uint32;
             description
               "EP Local port id";
           }
           leaf internal-mc-ae-id {
             type uint32;
             description
               "Internal MC-AE id";
           }
           leaf internal-lacp-port-id {
             type uint32;
             description
               "Internal LACP port id";
           }
           leaf internal-mc-ae-redundancy-group {
             type uint32;
             description
               "Internal MC-AE Redundancy group";
           }
           leaf internal-mc-ae-mode {
             type string;
             description
               "Internal MC-AE Mode";
           }
         }
         container traffic-statistics {
           leaf input-bps {
             type int32;
           }
           leaf input-pps {
             type int32;
           }
           leaf output-bps {
             type int32;
           }
           leaf output-pps {
             type int32;
           }
           leaf input-packets {
             type int32;
           }
           leaf output-packets {
             type int32;
           }
           leaf input-bytes {
             type int32;
           }
           leaf output-bytes {
             type int32;
           }
           container ipv6-transit-statistics {
             leaf input-bytes {
               type int32;
             }
             leaf output-bytes {
               type int32;
             }
             leaf input-packets {
               type int32;
             }
             leaf output-packets {
               type int32;
             }
           }
           container ipv6-total-statistics {
             leaf input-bytes {
               type int32;
             }
             leaf output-bytes {
               type int32;
             }
             leaf input-packets {
               type int32;
             }
             leaf output-packets {
               type int32;
             }
           }
         }
         container multicast-statistics {
           description
             "Multicast statistics for interface";
           leaf multicast-statistics-header {
             type empty;
           }
           container ipv4-multicast-statistics {
             description
               "IPV4 multicast statistics for interface";
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
           container ipv6-multicast-statistics {
             description
               "IPV6 multicast statistics for interface";
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
         }
         container ingress-traffic-statistics {
           description
             "Traffic statistics at ingress before entering Packet 
             Forwarding Engine";
           leaf input-bps {
             type int32;
           }
           leaf input-pps {
             type int32;
           }
           leaf input-drop-bps {
             type int32;
             description
               "Drop rate at ingress in bits per second ";
           }
           leaf input-drop-pps {
             type int32;
             description
               "Drop rate at ingress in packets per second ";
           }
           leaf input-bytes {
             type int32;
           }
           leaf input-packets {
             type int32;
           }
           leaf input-drop-bytes {
             type int32;
             description
               "Drop statistics at ingress in bytes";
           }
           leaf input-drop-packets {
             type int32;
             description
               "Drop statistics at ingress in packets";
           }
         }
         container multilink-interface-errors {
           leaf oversized-frames {
             type int32;
             description
               "Number of oversized frames detected";
           }
           leaf input-error-frames {
             type int32;
             description
               "Number of frames for which an error occurred on input";
           }
           leaf input-disabled-bundle {
             type int32;
             description
               "Count of packets received on a disabled link or bundle";
           }
           leaf output-disabled-bundle {
             type int32;
             description
               "Count of packets transmitted on a disabled link or bundle";
           }
           leaf queuing-drops {
             type int32;
             description
               "Count of packets dropped by the output queue of the I/O 
               Manager ASIC";
           }
           leaf packet-buffer-overflow {
             type int32;
             description
               "Number of times the packet data buffer overflowed";
           }
           leaf fragment-buffer-overflow {
             type int32;
             description
               "Number of times the fragment data buffer overflowed";
           }
           leaf fragment-timeout {
             type int32;
             description
               "Fragments timed out during assembly";
           }
           leaf sequence-number-missing {
             type int32;
             description
               "Gap detected in sequence numbers";
           }
           leaf out-of-order-sequence-number {
             type int32;
             description
               "Fragments with an out-of-order sequence number";
           }
           leaf out-of-range-sequence-number {
             type int32;
             description
               "Fragments with an out-of-range sequence number";
           }
           leaf data-memory-error {
             type int32;
             description
               "Errors detected in data memory";
           }
           leaf control-memory-error {
             type int32;
             description
               "Errors detected in control memory";
           }
         }
         container mlfr-uni-nni-bundle-options {
           leaf mlfr-uni-nni-device-type {
             type string;
             description
               "LMI device type of this multilink Frame Relay UNI NNI bundle
               instance";
           }
           leaf mlfr-uni-nni-mrru {
             type int32;
             description
               "Maximum RRU size of this multilink Frame Relay UNI NNI 
               bundle instance";
           }
           leaf mlfr-uni-nni-bandwidth {
             type string;
             description
               "Bandwidth of this multilink Frame Relay UNI NNI bundle";
           }
           leaf red-differential-delay {
             type int32;
             description
               "Maximum allowable differential delay of this multilink Frame
               Relay UNI NNI bundle instance";
           }
           leaf red-differential-delay-action {
             type string;
             description
               "Action to perform (remove link from bundle or disable 
               transmit) when exceeding red limit";
           }
           leaf yellow-differential-delay {
             type int32;
             description
               "Maximum allowable differential delay of this multilink Frame
               Relay UNI NNI bundle instance";
           }
           leaf mlfr-uni-nni-fragment-threshold {
             type int32;
             description
               "Fragment size of this multilink Frame Relay UNI NNI bundle 
               instance";
           }
           leaf mlfr-uni-nni-minimum-links {
             type int32;
             description
               "Minimum number of links to sustain this multilink Frame 
               Relay UNI NNI bundle instance";
           }
           leaf lip-hello-timer {
             type int32;
             description
               "Timer for sending periodic hello messages to the remote 
               endpoint";
           }
           leaf lip-ack-timer {
             type int32;
             description
               "How long to wait for a HELLO_ACK, ADD_LINK_ACK, or 
               REMOVE_LINK_ACK";
           }
           leaf lip-ack-retries {
             type int32;
             description
               "Maximum number of retransmissions for HELLO and LINK_ADD";
           }
           leaf bundle-class {
             type int32;
             description
               "Type of bundle class: A, B or C";
           }
           leaf mlfr-uni-nni-drop-timeout {
             type int32;
             description
               "How long to wait for all fragments of a complete packet to 
               arrive";
           }
           leaf mlfr-uni-nni-link-layer-overhead {
             type string;
             description
               "Multilink Frame Relay UNI NNI bundle link layer overhead";
           }
           leaf mlfr-uni-nni-lmi-type {
             type string;
             description
               "LMI type (ANSI or Q.933A) of this multilink Frame Relay UNI 
               NNI bundle instance";
           }
           leaf t391 {
             type int32;
             description
               "Multilink Frame Relay UNI NNI link integrity verify polling 
               timer";
           }
           leaf t392 {
             type int32;
             description
               "Multilink Frame Relay UNI NNI polling verification timer";
           }
           leaf n391 {
             type int32;
             description
               "Multilink Frame Relay UNI NNI full status polling counter";
           }
           leaf n392 {
             type int32;
             description
               "Multilink Frame Relay UNI NNI LMI error threshold";
           }
           leaf n393 {
             type int32;
             description
               "Multilink Frame Relay UNI NNI LMI monitored event count";
           }
         }
         container multilink-bundle-errors {
           description
             "Multilink bundle errors";
           leaf packet-drops {
             type int32;
             description
               "Number of packets dropped";
           }
           leaf packet-drop-bytes {
             type int32;
             description
               "Number of bytes in dropped packets";
           }
           leaf fragment-drops {
             type int32;
             description
               "Number of fragments dropped";
           }
           leaf fragment-drop-bytes {
             type int32;
             description
               "Number of bytes in dropped fragments";
           }
           leaf mrru-exceeded {
             type int32;
             description
               "Number of assembled packets that exceeded MRRU";
           }
           leaf processing-errors {
             type int32;
             description
               "Number of errors encountered in assembling packets";
           }
         }
         container input-error-list {
           description
             "Input errors on this interface";
           leaf input-errors {
             type int32;
           }
           leaf input-drops {
             type int32;
           }
           leaf invalid-vcs {
             type int32;
           }
           leaf framing-errors {
             type int32;
           }
           leaf input-runts {
             type int32;
           }
           leaf input-giants {
             type int32;
           }
           leaf input-bucket-drops {
             type int32;
           }
           leaf input-discards {
             type int32;
           }
           leaf input-l3-incompletes {
             type int32;
           }
           leaf input-l2-channel-errors {
             type int32;
           }
           leaf input-l2-mismatch-timeouts {
             type int32;
           }
           leaf input-fifo-errors {
             type int32;
           }
           leaf input-dma-errors {
             type int32;
           }
           leaf hs-link-crc-errors {
             type int32;
           }
           leaf hs-link-fifo-overflows {
             type int32;
           }
           leaf sram-errors {
             type int32;
           }
           leaf input-resource-errors {
             type int32;
           }
         }
         container output-error-list {
           description
             "Output errors on this interface";
           leaf carrier-transitions {
             type int32;
           }
           leaf output-errors {
             type int32;
           }
           leaf output-drops {
             type int32;
           }
           leaf output-collisions {
             type int32;
           }
           leaf output-hs-link-fifo-overflows {
             type int32;
           }
           leaf aged-packets {
             type int32;
           }
           leaf output-fifo-errors {
             type int32;
           }
           leaf output-dma-errors {
             type int32;
           }
           leaf hs-link-fifo-underflows {
             type int32;
           }
           leaf hs-link-crc-errors {
             type int32;
           }
           leaf mtu-errors {
             type int32;
           }
           leaf output-resource-errors {
             type int32;
           }
           leaf output-bucket-drops {
             type int32;
           }
           leaf ecn-marked-packets {
             type int32;
           }
         }
         container ber-threshold {
           description
             "Bit error rate (BER) threshold for SONET interface";
           leaf ber-sf {
             type string;
             description
               "BER-SF threshold";
           }
           leaf ber-sd {
             type string;
             description
               "BER-SD threshold";
           }
         }
         container ds1-crc-alarm-threshold {
           description
             "DS1 CRC alarm thresholds";
           leaf ds1-crc-alarm-threshold-major {
             type string;
             description
               "Threshold for CRC Major alarm";
           }
           leaf ds1-crc-alarm-threshold-minor {
             type string;
             description
               "Threshold for CRC Minor alarm";
           }
         }
         container active-alarms {
           leaf type {
             type string;
             description
               "Media type for associated interface alarms";
           }
           container interface-alarms {
             description
               "Container tag for interface alarms";
             leaf alarm-not-present {
               type empty;
               description
                 "No alarm indicated";
             }
             leaf sonet-alarm-lol {
               type empty;
               description
                 "Loss of light alarm";
             }
             leaf sonet-alarm-pll {
               type empty;
               description
                 "PLL lock alarm";
             }
             leaf sonet-alarm-lof {
               type empty;
               description
                 "Loss of frame alarm";
             }
             leaf sonet-alarm-los {
               type empty;
               description
                 "Loss of signal alarm";
             }
             leaf sonet-alarm-sef {
               type empty;
               description
                 "Severely errored frame alarm";
             }
             leaf sonet-alarm-lais {
               type empty;
               description
                 "Line AIS alarm";
             }
             leaf sonet-alarm-pais {
               type empty;
               description
                 "Path AIS alarm";
             }
             leaf sonet-alarm-lop {
               type empty;
               description
                 "Loss of pointer alarm";
             }
             leaf sonet-alarm-berr-sd {
               type empty;
               description
                 "Bit error rate alarm, defect";
             }
             leaf sonet-alarm-berr-sf {
               type empty;
               description
                 "Bit error rate alarm, fault";
             }
             leaf sonet-alarm-lrdi {
               type empty;
               description
                 "Line remote defect indicator alarm";
             }
             leaf sonet-alarm-prdi {
               type empty;
               description
                 "Path remote defect indicator alarm";
             }
             leaf sonet-alarm-rei {
               type empty;
               description
                 "Path remote error indicator alarm";
             }
             leaf sonet-alarm-uneq {
               type empty;
               description
                 "Unequipped alarm";
             }
             leaf sonet-alarm-pmis {
               type empty;
               description
                 "Path payload level mismatch alarm";
             }
             leaf sonet-alarm-loc {
               type empty;
               description
                 "Loss of cell delineation alarm";
             }
             leaf sonet-alarm-vais {
               type empty;
               description
                 "VT AIS alarm";
             }
             leaf sonet-alarm-vlop {
               type empty;
               description
                 "VT loss of pointer alarm";
             }
             leaf sonet-alarm-vrdi {
               type empty;
               description
                 "VT remote defect indicator alarm";
             }
             leaf sonet-alarm-vuneq {
               type empty;
               description
                 "VT unequipped alarm";
             }
             leaf sonet-alarm-vmis {
               type empty;
               description
                 "VT label mismatch alarm";
             }
             leaf sonet-alarm-vloc {
               type empty;
               description
                 "VT loss of cell delineation alarm";
             }
             leaf sdh-alarm-lol {
               type empty;
               description
                 "Loss of light alarm";
             }
             leaf sdh-alarm-pll {
               type empty;
               description
                 "PLL lock alarm";
             }
             leaf sdh-alarm-lof {
               type empty;
               description
                 "Loss of frame alarm";
             }
             leaf sdh-alarm-los {
               type empty;
               description
                 "Loss of signal alarm";
             }
             leaf sdh-alarm-oof {
               type empty;
               description
                 "Out of frame alarm";
             }
             leaf sdh-alarm-msais {
               type empty;
               description
                 "Multiplex section AIS alarm";
             }
             leaf sdh-alarm-hpais {
               type empty;
               description
                 "High order path AIS alarm";
             }
             leaf sdh-alarm-lop {
               type empty;
               description
                 "Loss of pointer alarm";
             }
             leaf sdh-alarm-berr-sd {
               type empty;
               description
                 "Bit error rate alarm, defect";
             }
             leaf sdh-alarm-berr-sf {
               type empty;
               description
                 "Bit error rate alarm, fault";
             }
             leaf sdh-alarm-msferf {
               type empty;
               description
                 "Multiplex section far-end remote failure alarm";
             }
             leaf sdh-alarm-hpferf {
               type empty;
               description
                 "High order path far-end remote failure alarm";
             }
             leaf sdh-alarm-hpfebe {
               type empty;
               description
                 "High order path far-end block error alarm";
             }
             leaf sdh-alarm-hpuneq {
               type empty;
               description
                 "High order path unequipped alarm";
             }
             leaf sdh-alarm-hpplm {
               type empty;
               description
                 "High order path payload level mismatch alarm";
             }
             leaf sdh-alarm-loc {
               type empty;
               description
                 "Loss of cell delineation alarm";
             }
             leaf sdh-alarm-tuais {
               type empty;
               description
                 "TU AIS alarm";
             }
             leaf sdh-alarm-tulop {
               type empty;
               description
                 "TU loss of pointer alarm";
             }
             leaf sdh-alarm-turdi {
               type empty;
               description
                 "TU remote defect indicator alarm";
             }
             leaf sdh-alarm-tuuneq {
               type empty;
               description
                 "TU unequipped alarm";
             }
             leaf sdh-alarm-tumis {
               type empty;
               description
                 "TU label mismatch error";
             }
             leaf sdh-alarm-tuloc {
               type empty;
               description
                 "TU loss of cell delineation alarm";
             }
             leaf ds3-alarm-pll {
               type empty;
               description
                 "PLL lock alarm";
             }
             leaf ds3-alarm-ais {
               type empty;
               description
                 "AIS alarm";
             }
             leaf ds3-alarm-lof {
               type empty;
               description
                 "Loss of frame alarm";
             }
             leaf ds3-alarm-los {
               type empty;
               description
                 "Loss of signal alarm";
             }
             leaf ds3-alarm-lcv {
               type empty;
               description
                 "Line code violation alarm";
             }
             leaf ds3-alarm-exz {
               type empty;
               description
                 "Excessive zeros alarm";
             }
             leaf ds3-alarm-ferf {
               type empty;
               description
                 "Far-end receive failure alarm";
             }
             leaf ds3-alarm-ylw {
               type empty;
               description
                 "Yellow alarm";
             }
             leaf ds3-alarm-idle {
               type empty;
               description
                 "Idle alarm";
             }
             leaf ds1-alarm-ais {
               type empty;
               description
                 "AIS alarm";
             }
             leaf ds1-alarm-lof {
               type empty;
               description
                 "Loss of frame alarm";
             }
             leaf ds1-alarm-los {
               type empty;
               description
                 "Loss of signal alarm";
             }
             leaf ds1-alarm-ylw {
               type empty;
               description
                 "Yellow alarm";
             }
             leaf ds1-alarm-crc-major {
               type empty;
               description
                 "CRC errors crossed major threshold";
             }
             leaf ds1-alarm-crc-minor {
               type empty;
               description
                 "CRC errors crossed minor threshold";
             }
             leaf dsl-alarm-lof {
               type empty;
               description
                 "Loss of frame alarm";
             }
             leaf dsl-alarm-los {
               type empty;
               description
                 "Loss of signal alarm";
             }
             leaf dsl-alarm-lom {
               type empty;
               description
                 "Loss of multiframe alarm";
             }
             leaf dsl-alarm-locdi {
               type empty;
               description
                 "Loss of cell delineation alarm for interleaved channel";
             }
             leaf dsl-alarm-locdni {
               type empty;
               description
                 "Loss of cell delineation alarm for non-interleaved channel";
             }
             leaf dsl-alarm-lop {
               type empty;
               description
                 "Loss of power alarm";
             }
             leaf dsl-alarm-far-lof {
               type empty;
               description
                 "Far-end loss-of-frame alarm";
             }
             leaf dsl-alarm-far-los {
               type empty;
               description
                 "Far-end loss-of-signal alarm";
             }
             leaf dsl-alarm-far-locdi {
               type empty;
               description
                 "Far-end loss-of-cell-delineation alarm for interleaved 
                 channel";
             }
             leaf dsl-alarm-far-locdni {
               type empty;
               description
                 "Far-end loss-of-cell-delineation alarm for non-interleaved
                 channel";
             }
             leaf fibrechannel-alarm-link-down {
               type empty;
               description
                 "Link alive failure";
             }
             leaf ethernet-alarm-link-down {
               type empty;
               description
                 "Link alive failure";
             }
             leaf ethernet-alarm-link-local-fault {
               type empty;
               description
                 "Link local fault";
             }
             leaf ethernet-alarm-link-remote-fault {
               type empty;
               description
                 "Link remote fault";
             }
             leaf ethernet-alarm-lcdp {
               type empty;
               description
                 "Loss of code-group delineation";
             }
             leaf isdn-alarm-los {
               type empty;
               description
                 "Loss of signal alarm";
             }
             leaf isdn-alarm-lof {
               type empty;
               description
                 "Loss of frame alarm";
             }
             leaf shdsl-alarm-losd {
               type empty;
               description
                 "Loss of signal alarm";
             }
             leaf shdsl-alarm-losw {
               type empty;
               description
                 "Loss of sync word alarm";
             }
             leaf shdsl-alarm-line1-losd {
               type empty;
               description
                 "Loss of signal (line 1) alarm";
             }
             leaf shdsl-alarm-line1-losw {
               type empty;
               description
                 "Loss of sync word (line 1) alarm";
             }
             leaf shdsl-alarm-line2-losd {
               type empty;
               description
                 "Loss of signal (line 2) alarm";
             }
             leaf shdsl-alarm-line2-losw {
               type empty;
               description
                 "Loss of sync word (line 2) alarm";
             }
             leaf shdsl-efm-alarm-losd {
               type empty;
               description
                 "Loss of signal alarm";
             }
             leaf shdsl-efm-alarm-losw {
               type empty;
               description
                 "Loss of sync word alarm";
             }
             leaf otn-alarm-los {
               type empty;
               description
                 "Loss of signal alarm";
             }
             leaf otn-alarm-lof {
               type empty;
               description
                 "Loss of frame alarm";
             }
             leaf otn-alarm-lom {
               type empty;
               description
                 "Loss of multiframe alarm";
             }
             leaf otn-alarm-wavelength-lock {
               type empty;
               description
                 "Loss of Wavelength Lock alarm";
             }
             leaf otn-alarm-otu-ais {
               type empty;
               description
                 "OTU Alarm Indication Signal alarm";
             }
             leaf otn-alarm-otu-bdi {
               type empty;
               description
                 "OTU Background Block Error alarm";
             }
             leaf otn-alarm-otu-ttim {
               type empty;
               description
                 "OTU Trail Trace Identifier Mismatch alarm";
             }
             leaf otn-alarm-otu-iae {
               type empty;
               description
                 "OTU Incoming Alignment alarm";
             }
             leaf otn-alarm-otu-sd {
               type empty;
               description
                 "OTU Signal Degrade alarm";
             }
             leaf otn-alarm-otu-sf {
               type empty;
               description
                 "OTU Signal Fail alarm";
             }
             leaf otn-alarm-otu-biae {
               type empty;
               description
                 "OTU Backward Incoming Alignment alarm";
             }
             leaf otn-alarm-otu-tsf {
               type empty;
               description
                 "OTU Trail Signal Fail alarm";
             }
             leaf otn-alarm-otu-ssf {
               type empty;
               description
                 "OTU Server Signal Fail alarm";
             }
             leaf otn-alarm-otu-fec-excessive {
               type empty;
               description
                 "OTU FEC Excessive alarm";
             }
             leaf otn-alarm-otu-fec-degraded {
               type empty;
               description
                 "OTU FEC Degraded alarm";
             }
             leaf otn-alarm-otu-fe-fec-degraded {
               type empty;
               description
                 "OTU FE FEC Degraded/Excessive alarm";
             }
             leaf otn-alarm-otu-threshold-bbe {
               type empty;
               description
                 "OTU Background Block Error threshold alarm";
             }
             leaf otn-alarm-otu-threshold-es {
               type empty;
               description
                 "OTU Errored Seconds threshold alarm";
             }
             leaf otn-alarm-otu-threshold-ses {
               type empty;
               description
                 "OTU Severely Errored Seconds threshold alarm";
             }
             leaf otn-alarm-otu-threshold-uas {
               type empty;
               description
                 "OTU Unavailable Seconds threshold alarm";
             }
             leaf otn-alarm-odu-ais {
               type empty;
               description
                 "ODU  Alarm Indiaction Signal alarm";
             }
             leaf otn-alarm-odu-oci {
               type empty;
               description
                 "ODU Open Connection Indication alarm";
             }
             leaf otn-alarm-odu-lck {
               type empty;
               description
                 "ODU Locked alarm";
             }
             leaf otn-alarm-odu-bdi {
               type empty;
               description
                 "ODU Backward Defect Indication alarm";
             }
             leaf otn-alarm-odu-ttim {
               type empty;
               description
                 "ODU Trail Trace Identifier Mismatch alarm";
             }
             leaf otn-alarm-odu-sd {
               type empty;
               description
                 "ODU Signal Degrade alarm";
             }
             leaf otn-alarm-odu-sf {
               type empty;
               description
                 "ODU Signal Fail alarm";
             }
             leaf otn-alarm-odu-iae {
               type empty;
               description
                 "ODU Incoming Alignment alarm";
             }
             leaf otn-alarm-odu-ltc {
               type empty;
               description
                 "ODU Loss of Tandem Connection alarm";
             }
             leaf otn-alarm-odu-csf {
               type empty;
               description
                 "ODU Client Signal Fail alarm";
             }
             leaf otn-alarm-odu-tsf {
               type empty;
               description
                 "ODU Trail Signal Fail alarm";
             }
             leaf otn-alarm-odu-ssf {
               type empty;
               description
                 "ODU Server Signal Fail alarm";
             }
             leaf otn-alarm-odu-rx-aps-change {
               type empty;
               description
                 "ODU Rx Aps Change alarm";
             }
             leaf otn-alarm-odu-threshold-bbe {
               type empty;
               description
                 "ODU Background Block Error threshold alarm";
             }
             leaf otn-alarm-odu-threshold-es {
               type empty;
               description
                 "ODU Errored Seconds threshold alarm";
             }
             leaf otn-alarm-odu-threshold-ses {
               type empty;
               description
                 "ODU Severely Errored Seconds threshold alarm";
             }
             leaf otn-alarm-odu-threshold-uas {
               type empty;
               description
                 "ODU Unavailable Seconds threshold alarm";
             }
             leaf otn-alarm-opu-pmi {
               type empty;
               description
                 "OPU Payload Mismatch alarm";
             }
             leaf otn-alarm-pre-fec-sd {
               type empty;
               description
                 "Pre-FEC SD alarm";
             }
             leaf otn-alarm-fe-pre-fec-sd {
               type empty;
               description
                 "Far end pre-FEC SD alarm";
             }
             leaf optics-alarms-mod-fault {
               type empty;
               description
                 "Module Fault alarm";
             }
             leaf optics-alarms-lol {
               type empty;
               description
                 "Loss of Lock alarm";
             }
             leaf optics-alarms-los {
               type empty;
               description
                 "Loss of Signal alarms";
             }
             leaf optics-alarms-lof {
               type empty;
               description
                 "Loss of frame alarm";
             }
             leaf optics-alarms-lom {
               type empty;
               description
                 "Loss of multi-frame alarm";
             }
             leaf optics-alarms-otu-bdi {
               type empty;
               description
                 "Backward defect indiacation alarm";
             }
             leaf optics-alarms-rmsf {
               type empty;
               description
                 "Rx Modem sysnc fault alarm";
             }
             leaf optics-alarms-rmlol {
               type empty;
               description
                 "Rx Modem loss of lock alarm";
             }
             leaf optics-alarms-rloa {
               type empty;
               description
                 "Rx loss of alignment alarm";
             }
             leaf optics-alarms-mbclf {
               type empty;
               description
                 "Modulator Bias control loop fail alarm";
             }
             leaf optics-alarms-itlaf {
               type empty;
               description
                 "ITLA Fault alarm";
             }
             leaf optics-alarms-daccf {
               type empty;
               description
                 "DAC Calibration Fault alarm";
             }
             leaf optics-alarms-adccf {
               type empty;
               description
                 "ADC Calibration Fault alarm";
             }
             leaf optics-alarms-fec-degrade {
               type empty;
               description
                 "FEC Degrade alarm";
             }
             leaf optics-alarms-fec-excessive {
               type empty;
               description
                 "FEC Excessive alarm";
             }
             leaf optics-alarms-fe-fec-degrade {
               type empty;
               description
                 "Far-end FEC Degrade alarm";
             }
             leaf optics-alarms-fe-fec-excessive {
               type empty;
               description
                 "Far-end FEC Excessive alarm";
             }
             leaf ima-alarm-startup-fe {
               type empty;
               description
                 "IMA group startup far-end alarm";
             }
             leaf ima-alarm-config-abort {
               type empty;
               description
                 "IMA group config abort alarm";
             }
             leaf ima-alarm-config-abort-fe {
               type empty;
               description
                 "IMA group config abort far-end alarm";
             }
             leaf ima-alarm-insufficient-links {
               type empty;
               description
                 "IMA group insufficient links alarm";
             }
             leaf ima-alarm-insufficient-links-fe {
               type empty;
               description
                 "IMA group insufficient links far-end alarm";
             }
             leaf ima-alarm-blocked {
               type empty;
               description
                 "IMA group blocked alarm";
             }
             leaf ima-alarm-blocked-fe {
               type empty;
               description
                 "IMA group blocked far-end alarm";
             }
             leaf ima-alarm-timing-mismatch {
               type empty;
               description
                 "IMA group timing mismatch alarm";
             }
             leaf ima-alarm-version-mismatch {
               type empty;
               description
                 "IMA group version mismatch alarm";
             }
             leaf ima-alarm-lif {
               type empty;
               description
                 "IMA link loss of IMA frame alarm";
             }
             leaf ima-alarm-lods {
               type empty;
               description
                 "IMA link out of delay synchronization alarm";
             }
             leaf ima-alarm-rdi {
               type empty;
               description
                 "IMA link remote defect indicator alarm";
             }
             leaf ima-alarm-tx-misconnected {
               type empty;
               description
                 "IMA link tx misconnected alarm";
             }
             leaf ima-alarm-rx-misconnected {
               type empty;
               description
                 "IMA link rx misconnected alarm";
             }
             leaf ima-alarm-fault {
               type empty;
               description
                 "IMA link fault alarm";
             }
             leaf ima-alarm-tx-unusable-fe {
               type empty;
               description
                 "IMA link Tx unusable far-end alarm";
             }
             leaf ima-alarm-rx-unusable-fe {
               type empty;
               description
                 "IMA link Tx unusable far-end alarm";
             }
             leaf generic-value {
               type int32;
               description
                 "Hexadecimal value of unknown flag bits";
             }
           }
         }
         container active-defects {
           leaf type {
             type string;
             description
               "Media type for associated interface alarms";
           }
           container interface-alarms {
             description
               "Container tag for interface alarms";
             leaf alarm-not-present {
               type empty;
               description
                 "No alarm indicated";
             }
             leaf sonet-alarm-lol {
               type empty;
               description
                 "Loss of light alarm";
             }
             leaf sonet-alarm-pll {
               type empty;
               description
                 "PLL lock alarm";
             }
             leaf sonet-alarm-lof {
               type empty;
               description
                 "Loss of frame alarm";
             }
             leaf sonet-alarm-los {
               type empty;
               description
                 "Loss of signal alarm";
             }
             leaf sonet-alarm-sef {
               type empty;
               description
                 "Severely errored frame alarm";
             }
             leaf sonet-alarm-lais {
               type empty;
               description
                 "Line AIS alarm";
             }
             leaf sonet-alarm-pais {
               type empty;
               description
                 "Path AIS alarm";
             }
             leaf sonet-alarm-lop {
               type empty;
               description
                 "Loss of pointer alarm";
             }
             leaf sonet-alarm-berr-sd {
               type empty;
               description
                 "Bit error rate alarm, defect";
             }
             leaf sonet-alarm-berr-sf {
               type empty;
               description
                 "Bit error rate alarm, fault";
             }
             leaf sonet-alarm-lrdi {
               type empty;
               description
                 "Line remote defect indicator alarm";
             }
             leaf sonet-alarm-prdi {
               type empty;
               description
                 "Path remote defect indicator alarm";
             }
             leaf sonet-alarm-rei {
               type empty;
               description
                 "Path remote error indicator alarm";
             }
             leaf sonet-alarm-uneq {
               type empty;
               description
                 "Unequipped alarm";
             }
             leaf sonet-alarm-pmis {
               type empty;
               description
                 "Path payload level mismatch alarm";
             }
             leaf sonet-alarm-loc {
               type empty;
               description
                 "Loss of cell delineation alarm";
             }
             leaf sonet-alarm-vais {
               type empty;
               description
                 "VT AIS alarm";
             }
             leaf sonet-alarm-vlop {
               type empty;
               description
                 "VT loss of pointer alarm";
             }
             leaf sonet-alarm-vrdi {
               type empty;
               description
                 "VT remote defect indicator alarm";
             }
             leaf sonet-alarm-vuneq {
               type empty;
               description
                 "VT unequipped alarm";
             }
             leaf sonet-alarm-vmis {
               type empty;
               description
                 "VT label mismatch alarm";
             }
             leaf sonet-alarm-vloc {
               type empty;
               description
                 "VT loss of cell delineation alarm";
             }
             leaf sdh-alarm-lol {
               type empty;
               description
                 "Loss of light alarm";
             }
             leaf sdh-alarm-pll {
               type empty;
               description
                 "PLL lock alarm";
             }
             leaf sdh-alarm-lof {
               type empty;
               description
                 "Loss of frame alarm";
             }
             leaf sdh-alarm-los {
               type empty;
               description
                 "Loss of signal alarm";
             }
             leaf sdh-alarm-oof {
               type empty;
               description
                 "Out of frame alarm";
             }
             leaf sdh-alarm-msais {
               type empty;
               description
                 "Multiplex section AIS alarm";
             }
             leaf sdh-alarm-hpais {
               type empty;
               description
                 "High order path AIS alarm";
             }
             leaf sdh-alarm-lop {
               type empty;
               description
                 "Loss of pointer alarm";
             }
             leaf sdh-alarm-berr-sd {
               type empty;
               description
                 "Bit error rate alarm, defect";
             }
             leaf sdh-alarm-berr-sf {
               type empty;
               description
                 "Bit error rate alarm, fault";
             }
             leaf sdh-alarm-msferf {
               type empty;
               description
                 "Multiplex section far-end remote failure alarm";
             }
             leaf sdh-alarm-hpferf {
               type empty;
               description
                 "High order path far-end remote failure alarm";
             }
             leaf sdh-alarm-hpfebe {
               type empty;
               description
                 "High order path far-end block error alarm";
             }
             leaf sdh-alarm-hpuneq {
               type empty;
               description
                 "High order path unequipped alarm";
             }
             leaf sdh-alarm-hpplm {
               type empty;
               description
                 "High order path payload level mismatch alarm";
             }
             leaf sdh-alarm-loc {
               type empty;
               description
                 "Loss of cell delineation alarm";
             }
             leaf sdh-alarm-tuais {
               type empty;
               description
                 "TU AIS alarm";
             }
             leaf sdh-alarm-tulop {
               type empty;
               description
                 "TU loss of pointer alarm";
             }
             leaf sdh-alarm-turdi {
               type empty;
               description
                 "TU remote defect indicator alarm";
             }
             leaf sdh-alarm-tuuneq {
               type empty;
               description
                 "TU unequipped alarm";
             }
             leaf sdh-alarm-tumis {
               type empty;
               description
                 "TU label mismatch error";
             }
             leaf sdh-alarm-tuloc {
               type empty;
               description
                 "TU loss of cell delineation alarm";
             }
             leaf ds3-alarm-pll {
               type empty;
               description
                 "PLL lock alarm";
             }
             leaf ds3-alarm-ais {
               type empty;
               description
                 "AIS alarm";
             }
             leaf ds3-alarm-lof {
               type empty;
               description
                 "Loss of frame alarm";
             }
             leaf ds3-alarm-los {
               type empty;
               description
                 "Loss of signal alarm";
             }
             leaf ds3-alarm-lcv {
               type empty;
               description
                 "Line code violation alarm";
             }
             leaf ds3-alarm-exz {
               type empty;
               description
                 "Excessive zeros alarm";
             }
             leaf ds3-alarm-ferf {
               type empty;
               description
                 "Far-end receive failure alarm";
             }
             leaf ds3-alarm-ylw {
               type empty;
               description
                 "Yellow alarm";
             }
             leaf ds3-alarm-idle {
               type empty;
               description
                 "Idle alarm";
             }
             leaf ds1-alarm-ais {
               type empty;
               description
                 "AIS alarm";
             }
             leaf ds1-alarm-lof {
               type empty;
               description
                 "Loss of frame alarm";
             }
             leaf ds1-alarm-los {
               type empty;
               description
                 "Loss of signal alarm";
             }
             leaf ds1-alarm-ylw {
               type empty;
               description
                 "Yellow alarm";
             }
             leaf ds1-alarm-crc-major {
               type empty;
               description
                 "CRC errors crossed major threshold";
             }
             leaf ds1-alarm-crc-minor {
               type empty;
               description
                 "CRC errors crossed minor threshold";
             }
             leaf dsl-alarm-lof {
               type empty;
               description
                 "Loss of frame alarm";
             }
             leaf dsl-alarm-los {
               type empty;
               description
                 "Loss of signal alarm";
             }
             leaf dsl-alarm-lom {
               type empty;
               description
                 "Loss of multiframe alarm";
             }
             leaf dsl-alarm-locdi {
               type empty;
               description
                 "Loss of cell delineation alarm for interleaved channel";
             }
             leaf dsl-alarm-locdni {
               type empty;
               description
                 "Loss of cell delineation alarm for non-interleaved channel";
             }
             leaf dsl-alarm-lop {
               type empty;
               description
                 "Loss of power alarm";
             }
             leaf dsl-alarm-far-lof {
               type empty;
               description
                 "Far-end loss-of-frame alarm";
             }
             leaf dsl-alarm-far-los {
               type empty;
               description
                 "Far-end loss-of-signal alarm";
             }
             leaf dsl-alarm-far-locdi {
               type empty;
               description
                 "Far-end loss-of-cell-delineation alarm for interleaved 
                 channel";
             }
             leaf dsl-alarm-far-locdni {
               type empty;
               description
                 "Far-end loss-of-cell-delineation alarm for non-interleaved
                 channel";
             }
             leaf fibrechannel-alarm-link-down {
               type empty;
               description
                 "Link alive failure";
             }
             leaf ethernet-alarm-link-down {
               type empty;
               description
                 "Link alive failure";
             }
             leaf ethernet-alarm-link-local-fault {
               type empty;
               description
                 "Link local fault";
             }
             leaf ethernet-alarm-link-remote-fault {
               type empty;
               description
                 "Link remote fault";
             }
             leaf ethernet-alarm-lcdp {
               type empty;
               description
                 "Loss of code-group delineation";
             }
             leaf isdn-alarm-los {
               type empty;
               description
                 "Loss of signal alarm";
             }
             leaf isdn-alarm-lof {
               type empty;
               description
                 "Loss of frame alarm";
             }
             leaf shdsl-alarm-losd {
               type empty;
               description
                 "Loss of signal alarm";
             }
             leaf shdsl-alarm-losw {
               type empty;
               description
                 "Loss of sync word alarm";
             }
             leaf shdsl-alarm-line1-losd {
               type empty;
               description
                 "Loss of signal (line 1) alarm";
             }
             leaf shdsl-alarm-line1-losw {
               type empty;
               description
                 "Loss of sync word (line 1) alarm";
             }
             leaf shdsl-alarm-line2-losd {
               type empty;
               description
                 "Loss of signal (line 2) alarm";
             }
             leaf shdsl-alarm-line2-losw {
               type empty;
               description
                 "Loss of sync word (line 2) alarm";
             }
             leaf shdsl-efm-alarm-losd {
               type empty;
               description
                 "Loss of signal alarm";
             }
             leaf shdsl-efm-alarm-losw {
               type empty;
               description
                 "Loss of sync word alarm";
             }
             leaf otn-alarm-los {
               type empty;
               description
                 "Loss of signal alarm";
             }
             leaf otn-alarm-lof {
               type empty;
               description
                 "Loss of frame alarm";
             }
             leaf otn-alarm-lom {
               type empty;
               description
                 "Loss of multiframe alarm";
             }
             leaf otn-alarm-wavelength-lock {
               type empty;
               description
                 "Loss of Wavelength Lock alarm";
             }
             leaf otn-alarm-otu-ais {
               type empty;
               description
                 "OTU Alarm Indication Signal alarm";
             }
             leaf otn-alarm-otu-bdi {
               type empty;
               description
                 "OTU Background Block Error alarm";
             }
             leaf otn-alarm-otu-ttim {
               type empty;
               description
                 "OTU Trail Trace Identifier Mismatch alarm";
             }
             leaf otn-alarm-otu-iae {
               type empty;
               description
                 "OTU Incoming Alignment alarm";
             }
             leaf otn-alarm-otu-sd {
               type empty;
               description
                 "OTU Signal Degrade alarm";
             }
             leaf otn-alarm-otu-sf {
               type empty;
               description
                 "OTU Signal Fail alarm";
             }
             leaf otn-alarm-otu-biae {
               type empty;
               description
                 "OTU Backward Incoming Alignment alarm";
             }
             leaf otn-alarm-otu-tsf {
               type empty;
               description
                 "OTU Trail Signal Fail alarm";
             }
             leaf otn-alarm-otu-ssf {
               type empty;
               description
                 "OTU Server Signal Fail alarm";
             }
             leaf otn-alarm-otu-fec-excessive {
               type empty;
               description
                 "OTU FEC Excessive alarm";
             }
             leaf otn-alarm-otu-fec-degraded {
               type empty;
               description
                 "OTU FEC Degraded alarm";
             }
             leaf otn-alarm-otu-fe-fec-degraded {
               type empty;
               description
                 "OTU FE FEC Degraded/Excessive alarm";
             }
             leaf otn-alarm-otu-threshold-bbe {
               type empty;
               description
                 "OTU Background Block Error threshold alarm";
             }
             leaf otn-alarm-otu-threshold-es {
               type empty;
               description
                 "OTU Errored Seconds threshold alarm";
             }
             leaf otn-alarm-otu-threshold-ses {
               type empty;
               description
                 "OTU Severely Errored Seconds threshold alarm";
             }
             leaf otn-alarm-otu-threshold-uas {
               type empty;
               description
                 "OTU Unavailable Seconds threshold alarm";
             }
             leaf otn-alarm-odu-ais {
               type empty;
               description
                 "ODU  Alarm Indiaction Signal alarm";
             }
             leaf otn-alarm-odu-oci {
               type empty;
               description
                 "ODU Open Connection Indication alarm";
             }
             leaf otn-alarm-odu-lck {
               type empty;
               description
                 "ODU Locked alarm";
             }
             leaf otn-alarm-odu-bdi {
               type empty;
               description
                 "ODU Backward Defect Indication alarm";
             }
             leaf otn-alarm-odu-ttim {
               type empty;
               description
                 "ODU Trail Trace Identifier Mismatch alarm";
             }
             leaf otn-alarm-odu-sd {
               type empty;
               description
                 "ODU Signal Degrade alarm";
             }
             leaf otn-alarm-odu-sf {
               type empty;
               description
                 "ODU Signal Fail alarm";
             }
             leaf otn-alarm-odu-iae {
               type empty;
               description
                 "ODU Incoming Alignment alarm";
             }
             leaf otn-alarm-odu-ltc {
               type empty;
               description
                 "ODU Loss of Tandem Connection alarm";
             }
             leaf otn-alarm-odu-csf {
               type empty;
               description
                 "ODU Client Signal Fail alarm";
             }
             leaf otn-alarm-odu-tsf {
               type empty;
               description
                 "ODU Trail Signal Fail alarm";
             }
             leaf otn-alarm-odu-ssf {
               type empty;
               description
                 "ODU Server Signal Fail alarm";
             }
             leaf otn-alarm-odu-rx-aps-change {
               type empty;
               description
                 "ODU Rx Aps Change alarm";
             }
             leaf otn-alarm-odu-threshold-bbe {
               type empty;
               description
                 "ODU Background Block Error threshold alarm";
             }
             leaf otn-alarm-odu-threshold-es {
               type empty;
               description
                 "ODU Errored Seconds threshold alarm";
             }
             leaf otn-alarm-odu-threshold-ses {
               type empty;
               description
                 "ODU Severely Errored Seconds threshold alarm";
             }
             leaf otn-alarm-odu-threshold-uas {
               type empty;
               description
                 "ODU Unavailable Seconds threshold alarm";
             }
             leaf otn-alarm-opu-pmi {
               type empty;
               description
                 "OPU Payload Mismatch alarm";
             }
             leaf otn-alarm-pre-fec-sd {
               type empty;
               description
                 "Pre-FEC SD alarm";
             }
             leaf otn-alarm-fe-pre-fec-sd {
               type empty;
               description
                 "Far end pre-FEC SD alarm";
             }
             leaf optics-alarms-mod-fault {
               type empty;
               description
                 "Module Fault alarm";
             }
             leaf optics-alarms-lol {
               type empty;
               description
                 "Loss of Lock alarm";
             }
             leaf optics-alarms-los {
               type empty;
               description
                 "Loss of Signal alarms";
             }
             leaf optics-alarms-lof {
               type empty;
               description
                 "Loss of frame alarm";
             }
             leaf optics-alarms-lom {
               type empty;
               description
                 "Loss of multi-frame alarm";
             }
             leaf optics-alarms-otu-bdi {
               type empty;
               description
                 "Backward defect indiacation alarm";
             }
             leaf optics-alarms-rmsf {
               type empty;
               description
                 "Rx Modem sysnc fault alarm";
             }
             leaf optics-alarms-rmlol {
               type empty;
               description
                 "Rx Modem loss of lock alarm";
             }
             leaf optics-alarms-rloa {
               type empty;
               description
                 "Rx loss of alignment alarm";
             }
             leaf optics-alarms-mbclf {
               type empty;
               description
                 "Modulator Bias control loop fail alarm";
             }
             leaf optics-alarms-itlaf {
               type empty;
               description
                 "ITLA Fault alarm";
             }
             leaf optics-alarms-daccf {
               type empty;
               description
                 "DAC Calibration Fault alarm";
             }
             leaf optics-alarms-adccf {
               type empty;
               description
                 "ADC Calibration Fault alarm";
             }
             leaf optics-alarms-fec-degrade {
               type empty;
               description
                 "FEC Degrade alarm";
             }
             leaf optics-alarms-fec-excessive {
               type empty;
               description
                 "FEC Excessive alarm";
             }
             leaf optics-alarms-fe-fec-degrade {
               type empty;
               description
                 "Far-end FEC Degrade alarm";
             }
             leaf optics-alarms-fe-fec-excessive {
               type empty;
               description
                 "Far-end FEC Excessive alarm";
             }
             leaf ima-alarm-startup-fe {
               type empty;
               description
                 "IMA group startup far-end alarm";
             }
             leaf ima-alarm-config-abort {
               type empty;
               description
                 "IMA group config abort alarm";
             }
             leaf ima-alarm-config-abort-fe {
               type empty;
               description
                 "IMA group config abort far-end alarm";
             }
             leaf ima-alarm-insufficient-links {
               type empty;
               description
                 "IMA group insufficient links alarm";
             }
             leaf ima-alarm-insufficient-links-fe {
               type empty;
               description
                 "IMA group insufficient links far-end alarm";
             }
             leaf ima-alarm-blocked {
               type empty;
               description
                 "IMA group blocked alarm";
             }
             leaf ima-alarm-blocked-fe {
               type empty;
               description
                 "IMA group blocked far-end alarm";
             }
             leaf ima-alarm-timing-mismatch {
               type empty;
               description
                 "IMA group timing mismatch alarm";
             }
             leaf ima-alarm-version-mismatch {
               type empty;
               description
                 "IMA group version mismatch alarm";
             }
             leaf ima-alarm-lif {
               type empty;
               description
                 "IMA link loss of IMA frame alarm";
             }
             leaf ima-alarm-lods {
               type empty;
               description
                 "IMA link out of delay synchronization alarm";
             }
             leaf ima-alarm-rdi {
               type empty;
               description
                 "IMA link remote defect indicator alarm";
             }
             leaf ima-alarm-tx-misconnected {
               type empty;
               description
                 "IMA link tx misconnected alarm";
             }
             leaf ima-alarm-rx-misconnected {
               type empty;
               description
                 "IMA link rx misconnected alarm";
             }
             leaf ima-alarm-fault {
               type empty;
               description
                 "IMA link fault alarm";
             }
             leaf ima-alarm-tx-unusable-fe {
               type empty;
               description
                 "IMA link Tx unusable far-end alarm";
             }
             leaf ima-alarm-rx-unusable-fe {
               type empty;
               description
                 "IMA link Tx unusable far-end alarm";
             }
             leaf generic-value {
               type int32;
               description
                 "Hexadecimal value of unknown flag bits";
             }
           }
         }
         container media-state-information {
           leaf media-type {
             type string;
             description
               "Type of media this information is for";
           }
           list media-state {
             leaf media-state-name {
               type string;
               description
                 "Media state category";
             }
             leaf media-state-state {
               type string;
               description
                 "Current state for this category";
             }
           }
         }
         container sonet-errors {
           list media-alarm {
             leaf media-alarm-name {
               type string;
             }
             leaf media-alarm-count {
               type int32;
             }
           }
         }
         container sonet-physical-information {
           list media-alarm {
             leaf media-alarm-name {
               type string;
             }
             leaf media-alarm-seconds {
               type int32;
             }
             leaf media-alarm-count {
               type int32;
             }
             leaf media-alarm-state {
               type string;
             }
           }
         }
         container sonet-section-information {
           list media-alarm {
             leaf media-alarm-name {
               type string;
             }
             leaf media-alarm-seconds {
               type int32;
             }
             leaf media-alarm-count {
               type int32;
             }
             leaf media-alarm-state {
               type string;
             }
           }
         }
         container sonet-line-information {
           list media-alarm {
             leaf media-alarm-name {
               type string;
             }
             leaf media-alarm-seconds {
               type int32;
             }
             leaf media-alarm-count {
               type int32;
             }
             leaf media-alarm-state {
               type string;
             }
           }
         }
         container sonet-path-information {
           list media-alarm {
             leaf media-alarm-name {
               type string;
             }
             leaf media-alarm-seconds {
               type int32;
             }
             leaf media-alarm-count {
               type int32;
             }
             leaf media-alarm-state {
               type string;
             }
           }
         }
         container sonet-payload-pointer-information {
           leaf sonet-payload-pointer-curptr {
             type string;
             description
               "Value of the SONET/SDH payload pointer, derived from the H1 
               and H2 overhead bytes";
           }
           leaf sonet-payload-pointer-ptrinc-count {
             type string;
             description
               "Number of times the value of the SONET/SDH payload pointer 
               had positive justification";
           }
           leaf sonet-payload-pointer-ptrdec-count {
             type string;
             description
               "Number of times the value of the SONET/SDH payload pointer 
               had negative justification";
           }
           leaf sonet-payload-pointer-newptr-ndf-count {
             type string;
             description
               "Number of times a new payload pointer was created with the 
               New Data Found flag set";
           }
         }
         container sonet-vt-information {
           list media-alarm {
             leaf media-alarm-name {
               type string;
             }
             leaf media-alarm-seconds {
               type int32;
             }
             leaf media-alarm-count {
               type int32;
             }
             leaf media-alarm-state {
               type string;
             }
           }
         }
         container otn-errors {
           list media-alarm {
             leaf media-alarm-name {
               type string;
             }
             leaf media-alarm-count {
               type int32;
             }
           }
         }
         container otn-fec-statistics {
           leaf fec-corrected-errors {
             type int32;
           }
           leaf fec-valid-time {
             type int32;
           }
           leaf fec-corrected-error-ratio {
             type int32;
           }
           leaf fec-uncorrected-words {
             type int32;
           }
         }
         container otn-fec-alarms {
           description
             "OTN degraded and excessive FEC error rates";
           list media-alarm {
             leaf media-alarm-name {
               type string;
             }
             leaf media-alarm-seconds {
               type int32;
             }
             leaf media-alarm-count {
               type int32;
             }
             leaf media-alarm-state {
               type string;
             }
           }
         }
         container otn-fec-mode {
           leaf fec-mode {
             type string;
             description
               "Optics FEC mode";
           }
         }
         container otn-otn-mode {
           leaf otn-mode {
             type string;
           }
         }
         container otn-otn-rate {
           leaf otn-rate {
             type string;
           }
         }
         container otn-otn-loopback {
           leaf otn-loopback {
             type string;
           }
         }
         container otn-local-loopback {
           leaf local-loopback {
             type string;
           }
         }
         container otn-payload-prbs {
           leaf payload-prbs {
             type string;
           }
         }
         container otn-laser-enable {
           leaf laser-enable {
             type string;
             description
               "Optics laser status";
           }
         }
         container media-information {
           description
             "Information about media alarms";
           leaf media-type {
             type string;
             description
               "Type of media this information is for";
           }
           list media-alarm {
             leaf media-alarm-name {
               type string;
             }
             leaf media-alarm-count {
               type int32;
             }
             leaf media-alarm-seconds {
               type int32;
             }
             leaf media-alarm-state {
               type string;
             }
             leaf ce-counter-name {
               type string;
               description
                 "Circuit Emulation counter information";
             }
             leaf ce-counter-packets {
               type int32;
               description
                 "Circuit Emulation number of packets";
             }
             leaf ce-counter-bytes {
               type int32;
               description
                 "Circuit Emulation number of bytes";
             }
             leaf ce-counter-count {
               type int32;
               description
                 "Circuit Emulation number of event occurrences";
             }
           }
           leaf ds1-timeslots {
             type string;
           }
           leaf ds1-line-encoding {
             type string;
           }
           leaf ds1-byte-encoding {
             type string;
           }
           leaf ds1-data-inversion {
             type string;
           }
           leaf idle-cycle-flag {
             type string;
           }
           leaf start-end-flag {
             type string;
           }
           leaf ds0-byte-encoding {
             type string;
           }
           leaf ds0-data-inversion {
             type string;
           }
           leaf e3-data-inversion {
             type string;
           }
           leaf ds1-buildout {
             type string;
             description
               "Number of feet";
           }
         }
         container ethernet-pcs-statistics {
           description
             "Ethernet PCS statistics";
           leaf bit-error-seconds {
             type int32;
             description
               "Bit error duration";
           }
           leaf errored-blocks-seconds {
             type int32;
             description
               "Errored blocks duration";
           }
         }
         container link-degrade-information {
           leaf lnk-degrd-mon {
             type string;
             description
               "Link degrade feature is enable/disable for this interface";
           }
           leaf lnk-degrd-set-thr {
             type uint32;
             description
               "BER At Which Link Considered Improved";
           }
           leaf lnk-degrd-clr-thr {
             type uint32;
             description
               "BER At Which Link Considered Degraded";
           }
           leaf lnk-degrd-war-set-thr {
             type uint32;
             description
               "BER At Which Warning Will Be Trigged";
           }
           leaf lnk-degrd-war-clr-thr {
             type uint32;
             description
               "BER At Which Warning Will Be Cleared";
           }
           leaf lnk-degrd-est-ber {
             type uint32;
             description
               "Link Degrade Estimated BER";
           }
           leaf lnk-degrd-seconds {
             type uint64;
             description
               "Link Degrade ";
           }
           leaf lnk-degrd-count {
             type uint64;
             description
               "Link Degrade ";
           }
           leaf lnk-degrd-state {
             type string;
             description
               "Link Degrade ";
           }
         }
         container ethernet-fec-mode {
           description
             "Ethernet FEC Mode";
           leaf enabled_fec_mode {
             type string;
             description
               "Enabled FEC mode: <NONE/FEC74/FEC91/FEC108>";
           }
         }
         container ethernet-fec-statistics {
           description
             "Ethernet FEC statistics";
           leaf fec_ccw_count {
             type int32;
             description
               "FEC Corrected Error Count";
           }
           leaf fec_nccw_count {
             type int32;
             description
               "FEC Uncorrected Error Count";
           }
           leaf fec_ccw_error_rate {
             type int32;
             description
               "FEC Corrected Error Rate (errors/sec)";
           }
           leaf fec_nccw_error_rate {
             type int32;
             description
               "FEC Uncorrected Error Rate (errors/sec)";
           }
         }
         container ctle {
           description
             "Ctle ";
           leaf ctle_value {
             type int32;
             description
               "Ctle value";
           }
         }
         container pre-emphasis {
           description
             "Pre-emphasis ";
           leaf pre_emphasis_value {
             type int32;
             description
               "Pre-emphasis value";
           }
         }
         container differential-amplitude {
           description
             "Differential-amplitude ";
           leaf differential_amplitude_value {
             type int32;
             description
               "Differential-amplitude value";
           }
         }
         container ethernet-mac-statistics {
           description
             "Ethernet MAC statistics";
           leaf input-bytes {
             type int32;
           }
           leaf input-packets {
             type int32;
           }
           leaf output-bytes {
             type int32;
           }
           leaf output-packets {
             type int32;
           }
           leaf input-undersized-frames {
             type int32;
           }
           leaf input-unicasts {
             type int32;
           }
           leaf output-unicasts {
             type int32;
           }
           leaf input-broadcasts {
             type int32;
           }
           leaf output-broadcasts {
             type int32;
           }
           leaf input-multicasts {
             type int32;
           }
           leaf output-multicasts {
             type int32;
           }
           leaf input-crc-errors {
             type int32;
           }
           leaf output-crc-errors {
             type int32;
           }
           leaf input-fifo-errors {
             type int32;
           }
           leaf output-fifo-errors {
             type int32;
           }
           leaf input-dma-errors {
             type int32;
           }
           leaf output-dma-errors {
             type int32;
           }
           leaf input-mac-control-frames {
             type int32;
           }
           leaf output-mac-control-frames {
             type int32;
           }
           leaf input-mac-pause-frames {
             type int32;
           }
           leaf output-mac-pause-frames {
             type int32;
           }
           leaf input-oversized-frames {
             type int32;
           }
           leaf input-jabber-frames {
             type int32;
           }
           leaf input-fragment-frames {
             type int32;
           }
           leaf input-vlan-tagged-frames {
             type int32;
           }
           leaf input-code-violations {
             type int32;
           }
           leaf input-total-errors {
             type int32;
           }
           leaf output-total-errors {
             type int32;
           }
           leaf input-policer-frame-drops {
             type int32;
           }
           leaf input-policer-byte-drops {
             type int32;
           }
         }
         container sriov-vf-statistics {
           description
             "SRIOV VF statistics";
           leaf vf-number {
             type uint32;
           }
           leaf pci-address {
             type string;
           }
           leaf mapped-to {
             type string;
           }
           leaf input-bytes {
             type int32;
           }
           leaf input-packets {
             type int32;
           }
           leaf output-bytes {
             type int32;
           }
           leaf output-packets {
             type int32;
           }
           leaf mc-packets {
             type int32;
           }
         }
         container ethernet-prbs-mode {
           description
             "PRBS Mode";
           leaf prbs-mode {
             type string;
             description
               "PRBS Mode: <Enabled/Disabled>";
           }
         }
         container ethernet-prbs-statistics {
           description
             "Ethernet PRBS statistics";
           leaf prbs-lane {
             type int32;
             description
               "PRBS Lane";
           }
           leaf prbs-state {
             type string;
             description
               "PRBS State";
           }
           leaf prbs-error-count {
             type int32;
             description
               "PRBS Error Count";
           }
         }
         container smart-sfp-configurable-type {
           leaf smart-sfp-tdm-management {
             type string;
           }
         }
         container smart-sfp-type {
           leaf smart-sfp-module-type {
             type string;
           }
           leaf smart-sfp-present {
             type string;
           }
         }
         container smart-sfp-config {
           leaf tdm-loopback {
             type string;
           }
           leaf dmac-check-enable {
             type string;
           }
           leaf encap-ecid {
             type int32;
           }
           leaf decap-ecid {
             type int32;
           }
           leaf vlan-id-1 {
             type int32;
           }
           leaf vlan-id-2 {
             type int32;
           }
           leaf mode {
             type string;
           }
           leaf chan-dmac {
             type jt:mac-addr;
           }
         }
         container smart-sfp-oc3-statistics {
           leaf fcs-error-count {
             type uint32;
           }
           leaf sec-sefs {
             type uint32;
           }
           leaf sec-es {
             type uint32;
           }
           leaf sec-es-min15 {
             type uint32;
           }
           leaf sec-ses {
             type uint32;
           }
           leaf sec-ses-min15 {
             type uint32;
           }
           leaf sec-cv {
             type uint32;
           }
           leaf sec-cv-min15 {
             type uint32;
           }
           leaf line-es {
             type uint32;
           }
           leaf line-es-min15 {
             type uint32;
           }
           leaf line-ses {
             type uint32;
           }
           leaf line-ses-min15 {
             type uint32;
           }
           leaf line-cv {
             type uint32;
           }
           leaf line-cv-min15 {
             type uint32;
           }
           leaf line-uas {
             type uint32;
           }
           leaf line-uas-min15 {
             type uint32;
           }
           leaf path-es {
             type uint32;
           }
           leaf path-es-min15 {
             type uint32;
           }
           leaf path-ses {
             type uint32;
           }
           leaf path-ses-min15 {
             type uint32;
           }
           leaf path-cv {
             type uint32;
           }
           leaf path-cv-min15 {
             type uint32;
           }
           leaf path-uas {
             type uint32;
           }
           leaf path-uas-min15 {
             type uint32;
           }
         }
         container smart-sfp-e1t1-statistics {
           leaf e1t1-es {
             type uint32;
           }
           leaf e1t1-es-min15 {
             type uint32;
           }
           leaf e1t1-ses {
             type uint32;
           }
           leaf e1t1-ses-min15 {
             type uint32;
           }
           leaf e1t1-uas {
             type uint32;
           }
           leaf e1t1-uas-min15 {
             type uint32;
           }
           leaf e1t1-bes {
             type uint32;
           }
           leaf e1t1-bes-min15 {
             type uint32;
           }
           leaf e1t1-les {
             type uint32;
           }
           leaf e1t1-les-min15 {
             type uint32;
           }
           leaf e1t1-pes {
             type uint32;
           }
           leaf e1t1-pes-min15 {
             type uint32;
           }
           leaf e1t1-psess {
             type uint32;
           }
           leaf e1t1-psess-min15 {
             type uint32;
           }
           leaf e1t1-ces {
             type uint32;
           }
           leaf e1t1-ces-min15 {
             type uint32;
           }
           leaf e1t1-cses {
             type uint32;
           }
           leaf e1t1-cses-min15 {
             type uint32;
           }
           leaf e1t1-sefs {
             type uint32;
           }
           leaf e1t1-sefs-min15 {
             type uint32;
           }
         }
         container smart-sfp-e3t3-statistics {
           leaf e3t3-les {
             type uint32;
           }
           leaf e3t3-les-min15 {
             type uint32;
           }
           leaf e3t3-pes {
             type uint32;
           }
           leaf e3t3-pes-min15 {
             type uint32;
           }
           leaf e3t3-psess {
             type uint32;
           }
           leaf e3t3-psess-min15 {
             type uint32;
           }
           leaf e3t3-ces {
             type uint32;
           }
           leaf e3t3-ces-min15 {
             type uint32;
           }
           leaf e3t3-cses {
             type uint32;
           }
           leaf e3t3-cses-min15 {
             type uint32;
           }
           leaf e3t3-sefs {
             type uint32;
           }
           leaf e3t3-sefs-min15 {
             type uint32;
           }
           leaf e3t3-uas {
             type uint32;
           }
           leaf e3t3-uas-min15 {
             type uint32;
           }
         }
         container fibrechannel-port-flow-control {
           description
             "Fibre Channel interface flow control";
           leaf fibrechannel-port-flow-control-mode {
             type string;
           }
           list fibrechannel-port-flow-control-credits {
             description
               "Generic flow control credits";
             leaf fibrechannel-port-flow-control-credits-subject {
               type string;
             }
             leaf fibrechannel-port-flow-control-credits-assigned {
               type uint64;
             }
             leaf fibrechannel-port-flow-control-credits-available {
               type uint64;
             }
           }
         }
         container fibrechannel-mac-statistics {
           description
             "Fibre Channel MAC statistics";
           container fibrechannel-mac-statistics-generic {
             leaf link-failures {
               type uint64;
             }
             leaf loss-of-sync {
               type uint64;
             }
             leaf loss-of-signal {
               type uint64;
             }
             leaf sw-link-resets {
               type uint64;
             }
             leaf buffer-to-buffer-credit-recovery-lost-frames {
               type uint64;
             }
             leaf buffer-to-buffer-credit-recovery-lost-rrdys {
               type uint64;
             }
           }
           container fibrechannel-mac-statistics-received {
             leaf rx-class-2-frames {
               type uint64;
             }
             leaf rx-class-2-octets {
               type uint64;
             }
             leaf rx-class-3-frames {
               type uint64;
             }
             leaf rx-class-3-octets {
               type uint64;
             }
             leaf rx-class-f-frames {
               type uint64;
             }
             leaf rx-class-f-octets {
               type uint64;
             }
             leaf class-2-discards {
               type uint64;
             }
             leaf class-3-discards {
               type uint64;
             }
             leaf class-f-discards {
               type uint64;
             }
             leaf rx-frames-too-long {
               type uint64;
             }
             leaf rx-frames-too-short {
               type uint64;
             }
             leaf rx-missing-eof {
               type uint64;
             }
             leaf rx-invalid-crcs {
               type uint64;
             }
             leaf rx-link-resets {
               type uint64;
             }
             leaf rx-link-reset-responses {
               type uint64;
             }
             leaf rx-offlines {
               type uint64;
             }
             leaf rx-not-operationals {
               type uint64;
             }
             leaf rx-invalid-tx-words {
               type uint64;
             }
             leaf rx-encoding-disparity-errors {
               type uint64;
             }
             leaf rx-delimiter-errors {
               type uint64;
             }
             leaf rx-input-buffers-full {
               type uint64;
             }
             leaf rx-invalid-ordered-sets {
               type uint64;
             }
             leaf rx-prim-seq-protocol-errors {
               type uint64;
             }
             leaf rx-other-errors {
               type uint64;
             }
           }
           container fibrechannel-mac-statistics-transmitted {
             leaf tx-class-2-frames {
               type uint64;
             }
             leaf tx-class-2-octets {
               type uint64;
             }
             leaf tx-class-3-frames {
               type uint64;
             }
             leaf tx-class-3-octets {
               type uint64;
             }
             leaf tx-class-f-frames {
               type uint64;
             }
             leaf tx-class-f-octets {
               type uint64;
             }
             leaf tx-link-resets {
               type uint64;
             }
             leaf tx-link-reset-responses {
               type uint64;
             }
             leaf tx-offlines {
               type uint64;
             }
             leaf tx-not-operationals {
               type uint64;
             }
             leaf tx-bb-credit-zeroes {
               type uint64;
             }
             leaf tx-other-errors {
               type uint64;
             }
           }
         }
         container ethernet-filter-statistics {
           description
             "Ethernet filter statistics";
           leaf input-reject-count {
             type int32;
           }
           leaf output-packet-pad-count {
             type int32;
           }
           leaf output-packet-error-count {
             type int32;
           }
           leaf input-packets {
             type int32;
           }
           leaf input-reject-destination-address-count {
             type int32;
           }
           leaf input-reject-source-address-count {
             type int32;
           }
           leaf output-packets {
             type int32;
           }
           leaf cam-destination-filter-count {
             type int32;
           }
           leaf cam-source-filter-count {
             type int32;
           }
         }
         container ethernet-autonegotiation {
           description
             "Ethernet autonegotiation information";
           leaf autonegotiation-status {
             type string;
           }
           leaf link-partner-duplexity {
             type string;
           }
           leaf flow-control {
             type string;
           }
           leaf link-partner-status {
             type string;
             description
               "Auto-negotiation status of link partner";
           }
           leaf link-partner-speed {
             type string;
             description
               "Link partner speed";
           }
           leaf link-partner-reason {
             type string;
             description
               "Reason link partner is down";
           }
           container local-info {
             description
               "Auto-negotiation status of local partner";
             leaf local-flow-control {
               type string;
               description
                 "Local interface flow control type";
             }
             leaf local-flow-control-tx {
               type string;
               description
                 "Local interface flow control tx type";
             }
             leaf local-flow-control-rx {
               type string;
               description
                 "Local interface flow control rx type";
             }
             leaf local-remote-fault {
               type string;
               description
                 "Local interface remote fault type";
             }
             leaf local-link-speed {
               type string;
               description
                 "Local link speed";
             }
             leaf local-link-duplexity {
               type string;
             }
           }
         }
         container mac-database {
           leaf number-of-mac-record {
             type int32;
           }
           list mac-record {
             leaf mac-address {
               type jt:mac-addr;
             }
             leaf receive-frames {
               type int32;
             }
             leaf receive-bytes {
               type int32;
             }
             leaf transmit-frames {
               type int32;
             }
             leaf transmit-bytes {
               type int32;
             }
           }
         }
         container dsl-information {
           description
             "Operational information and statistics for ADSL interfaces";
           leaf dsl-line-status {
             type string;
             description
               "Status of modem";
           }
           leaf dsl-line-operating-mode {
             type string;
             description
               "Line type of digital subscriber line";
           }
           leaf dsl-line-type {
             type string;
             description
               "Line type of digital subscriber line";
           }
           leaf adsl-annex-type {
             type string;
             description
               "Type of ADSL annex";
           }
           leaf adsl-last-fail-code {
             type string;
             description
               "Reason for the last line-open failure";
           }
           leaf adsl-subfunction {
             type int32;
             description
               "Specified analog front-end chip and discrete front end";
           }
           leaf adsl-seconds-in-showtime {
             type int32;
             description
               "Number of seconds the ADSL connection is in showtime state";
           }
           container dsl-chipset-information {
             leaf atu-r-country-code {
               type int32;
               description
                 "Country code for ATU-R chipset vendor";
             }
             leaf atu-c-country-code {
               type int32;
               description
                 "Country code for ATU-C chipset vendor";
             }
             leaf atu-r-vendor-id {
               type string;
               description
                 "ATU-R ITU chipset vendor ID";
             }
             leaf atu-c-vendor-id {
               type string;
               description
                 "ATU-C ITU chipset vendor ID";
             }
             leaf atu-r-vendor-specific {
               type int32;
               description
                 "ATU-R vendor-specific data";
             }
             leaf atu-c-vendor-specific {
               type int32;
               description
                 "ATU-C vendor-specific data";
             }
           }
           container dsl-statistics {
             leaf near-end-attainable-bitrate {
               type int32;
               description
                 "Near-end attainable bit rate";
             }
             leaf far-end-attainable-bitrate {
               type int32;
               description
                 "Far-end attainable bit rate";
             }
             leaf near-end-attenuation {
               type string;
               description
                 "Near-end attenuation";
             }
             leaf far-end-attenuation {
               type string;
               description
                 "Far-end attenuation";
             }
             leaf near-end-capacity-used {
               type int32;
               description
                 "Near-end capacity used";
             }
             leaf far-end-capacity-used {
               type int32;
               description
                 "Far-end capacity used";
             }
             leaf near-end-noise-margin {
               type string;
               description
                 "Near-end noise margin";
             }
             leaf far-end-noise-margin {
               type string;
               description
                 "Far-end noise margin";
             }
             leaf near-end-output-power {
               type string;
               description
                 "Near-end output power";
             }
             leaf far-end-output-power {
               type string;
               description
                 "Far-end output power";
             }
             leaf near-end-interleaved-bitrate {
               type int32;
               description
                 "Near-end interleaved bit rate";
             }
             leaf near-end-fast-bitrate {
               type int32;
               description
                 "Near-end fast bit rate";
             }
             leaf far-end-interleaved-bitrate {
               type int32;
               description
                 "Far-end interleaved bit rate";
             }
             leaf far-end-fast-bitrate {
               type int32;
               description
                 "Far-end fast bit rate";
             }
             leaf near-end-interleaved-crc {
               type int32;
               description
                 "Near-end interleaved cyclic redundancy check correction";
             }
             leaf near-end-fast-crc {
               type int32;
               description
                 "Near-end fast cyclic redundancy check correction";
             }
             leaf far-end-interleaved-crc {
               type int32;
               description
                 "Far-end interleaved cyclic redundancy check correction";
             }
             leaf far-end-fast-crc {
               type int32;
               description
                 "Far-end fast cyclic redundancy check";
             }
             leaf near-end-interleaved-fec {
               type int32;
               description
                 "Near-end interleaved footer error correction";
             }
             leaf near-end-fast-fec {
               type int32;
               description
                 "Near-end fast footer error correction";
             }
             leaf far-end-interleaved-fec {
               type int32;
               description
                 "Far-end interleaved footer error correction";
             }
             leaf far-end-fast-fec {
               type int32;
               description
                 "Far-end fast footer error correction";
             }
             leaf near-end-interleaved-hec {
               type int32;
               description
                 "Near-end interleaved header error correction";
             }
             leaf near-end-fast-hec {
               type int32;
               description
                 "Near-end fast header error correction";
             }
             leaf far-end-interleaved-hec {
               type int32;
               description
                 "Far-end interleaved header error correction";
             }
             leaf far-end-fast-hec {
               type int32;
               description
                 "Far-end fast header error correction";
             }
             leaf near-end-interleaved-rx-cells {
               type int32;
               description
                 "Near-end interleaved receiver cells";
             }
             leaf near-end-fast-rx-cells {
               type int32;
               description
                 "Near-end fast receiver cells";
             }
             leaf near-end-interleaved-tx-cells {
               type int32;
               description
                 "Near-end interleaved transmitter cells";
             }
             leaf near-end-fast-tx-cells {
               type int32;
               description
                 "Near-end fast transmitter cells";
             }
             leaf interleaved-rx-cells {
               type int32;
               description
                 "Interleaved receiver cells";
             }
             leaf fast-rx-cells {
               type int32;
               description
                 "Fast receiver cells";
             }
             leaf interleaved-tx-cells {
               type int32;
               description
                 "Interleaved transmitter cells";
             }
             leaf fast-tx-cells {
               type int32;
               description
                 "Fast transmitter cells";
             }
           }
         }
         container vdsl-information {
           description
             "Operational information and statistics for VDSL interfaces";
           leaf vdsl-line-status {
             type string;
             description
               "Status of modem";
           }
           leaf vdsl-line-profile-type {
             type string;
             description
               "Line type of digital subscriber line";
           }
           leaf vdsl-line-type {
             type string;
             description
               "Line type of digital subscriber line";
           }
           leaf vdsl-annex-type {
             type string;
             description
               "Type of VDSL annex";
           }
           leaf vdsl-last-fail-code {
             type string;
             description
               "Reason for the last line-open failure";
           }
           leaf vdsl-subfunction {
             type int32;
             description
               "Specified analog front-end chip and discrete front end";
           }
           leaf vdsl-seconds-in-showtime {
             type int32;
             description
               "Number of seconds the VDSL connection is in showtime state";
           }
           container vdsl-chipset-information {
             leaf vtu-r-country-code {
               type int32;
               description
                 "Country code for VTU-R chipset vendor";
             }
             leaf vtu-c-country-code {
               type int32;
               description
                 "Country code for VTU-C chipset vendor";
             }
             leaf vtu-r-vendor-id {
               type string;
               description
                 "VTU-R ITU chipset vendor ID";
             }
             leaf vtu-c-vendor-id {
               type string;
               description
                 "VTU-C ITU chipset vendor ID";
             }
             leaf vtu-r-vendor-specific {
               type int32;
               description
                 "VTU-R vendor-specific data";
             }
             leaf vtu-c-vendor-specific {
               type int32;
               description
                 "VTU-C vendor-specific data";
             }
           }
           container vdsl-statistics {
             leaf vdsl-near-end-attainable-bitrate {
               type int32;
               description
                 "Near end attainable bit rate ";
             }
             leaf vdsl-far-end-attainable-bitrate {
               type int32;
               description
                 "Far-end attainable bit rate";
             }
             leaf vdsl-near-end-attenuation {
               type string;
               description
                 "Near-end attenuation";
             }
             leaf vdsl-far-end-attenuation {
               type string;
               description
                 "Far-end attenuation";
             }
             leaf vdsl-near-end-capacity-used {
               type int32;
               description
                 "Near-end capacity used";
             }
             leaf vdsl-far-end-capacity-used {
               type int32;
               description
                 "Far-end capacity used";
             }
             leaf vdsl-near-end-noise-margin {
               type string;
               description
                 "Near-end noise margin";
             }
             leaf vdsl-far-end-noise-margin {
               type string;
               description
                 "Far-end noise margin";
             }
             leaf vdsl-near-end-output-power {
               type string;
               description
                 "Near-end output power";
             }
             leaf vdsl-far-end-output-power {
               type string;
               description
                 "Far-end output power";
             }
             leaf vdsl-near-end-interleaved-bitrate {
               type int32;
               description
                 "Near-end interleaved bit rate";
             }
             leaf vdsl-near-end-fast-bitrate {
               type int32;
               description
                 "Near-end fast bit rate";
             }
             leaf vdsl-far-end-interleaved-bitrate {
               type int32;
               description
                 "Far-end interleaved bit rate";
             }
             leaf vdsl-far-end-fast-bitrate {
               type int32;
               description
                 "Far-end fast bit rate";
             }
             leaf vdsl-near-end-interleaved-crc {
               type int32;
               description
                 "Near-end interleaved cyclic redundancy check correction";
             }
             leaf vdsl-near-end-fast-crc {
               type int32;
               description
                 "Near-end fast cyclic redundancy check correction";
             }
             leaf vdsl-far-end-interleaved-crc {
               type int32;
               description
                 "Far-end interleaved cyclic redundancy check correction";
             }
             leaf vdsl-far-end-fast-crc {
               type int32;
               description
                 "Far-end fast cyclic redundancy check";
             }
             leaf vdsl-near-end-interleaved-fec {
               type int32;
               description
                 "Near-end interleaved footer error correction";
             }
             leaf vdsl-near-end-fast-fec {
               type int32;
               description
                 "Near-end fast footer error correction";
             }
             leaf vdsl-far-end-interleaved-fec {
               type int32;
               description
                 "Far-end interleaved footer error correction";
             }
             leaf vdsl-far-end-fast-fec {
               type int32;
               description
                 "Far-end fast footer error correction";
             }
             leaf vdsl-near-end-interleaved-hec {
               type int32;
               description
                 "Near-end interleaved header error correction";
             }
             leaf vdsl-near-end-fast-hec {
               type int32;
               description
                 "Near-end fast header error correction";
             }
             leaf vdsl-far-end-interleaved-hec {
               type int32;
               description
                 "Far-end interleaved header error correction";
             }
             leaf vdsl-far-end-fast-hec {
               type int32;
               description
                 "Far-end fast header error correction";
             }
             leaf vdsl-near-end-interleaved-rx-cells {
               type int32;
               description
                 "Near-end interleaved receiver cells";
             }
             leaf vdsl-near-end-fast-rx-cells {
               type int32;
               description
                 "Near-end fast receiver cells";
             }
             leaf vdsl-near-end-interleaved-tx-cells {
               type int32;
               description
                 "Near-end interleaved transmitter cells";
             }
             leaf vdsl-near-end-fast-tx-cells {
               type int32;
               description
                 "Near-end fast transmitter cells";
             }
           }
         }
         container shdsl-information {
           description
             "Operational information and statistics for SHDSL interfaces";
           leaf shdsl-line-termination {
             type string;
             description
               "Line termination remote or central";
           }
           leaf shdsl-annex {
             type string;
             description
               "Type of SHDSL annex";
           }
           leaf shdsl-line-mode {
             type string;
             description
               "Two or four wire mode";
           }
           leaf shdsl-modem-status {
             type string;
             description
               "Status of the SHDSL modem";
           }
           leaf shdsl-bit-rate {
             type int32;
             description
               "Actual line rate";
           }
           leaf shdsl-last-fail-reason {
             type string;
             description
               "Reason for last line-open failure";
           }
           leaf shdsl-last-fail-code {
             type int32;
             description
               "Last line-open failure code";
           }
           leaf shdsl-framer-mode {
             type string;
             description
               "Framer mode used";
           }
           leaf shdsl-dying-gasp {
             type string;
             description
               "Dying gasp is enabled or disabled";
           }
           leaf shdsl-framer-sync-status {
             type string;
             description
               "Framer synchronization status";
           }
           leaf shdsl-chipset-version {
             type int32;
             description
               "Version number for the DSP/framer chip";
           }
           leaf shdsl-firmware-version {
             type string;
             description
               "Transreceiver firmware release number";
           }
           container shdsl-statistics {
             leaf shdsl-loop-attenuation {
               type int32;
               description
                 "An estimate of the loop attenuation";
             }
             leaf shdsl-transmit-power {
               type int32;
               description
                 "Nominal transmit power";
             }
             leaf shdsl-receiver-gain {
               type int32;
               description
                 "Total receiver gain";
             }
             leaf shdsl-snr-sampling {
               type int32;
               description
                 "Received signal to noise ratio";
             }
             leaf shdsl-rx-cells {
               type int32;
               description
                 "Total ATM cells received";
             }
             leaf shdsl-tx-cells {
               type int32;
               description
                 "Total ATM cells transmitted";
             }
             leaf shdsl-crc {
               type int32;
               description
                 "Number of CRC errors";
             }
             leaf shdsl-sega {
               type int32;
               description
                 "Number of SEGA errors";
             }
             leaf shdsl-losw {
               type int32;
               description
                 "Number of LOSW  errors";
             }
             leaf shdsl-hec {
               type int32;
               description
                 "Header error check errors";
             }
             leaf shdsl-cell-drop {
               type int32;
               description
                 "Cells dropped because of errors";
             }
           }
         }
         container efm-information {
           description
             "Operational information and statistics for EFM interfaces";
           container efm-group-statistics {
             leaf efm-type {
               type string;
               description
                 "EFM type Single pair or EFM bond";
             }
             leaf efm-active-pairs {
               type int32;
               description
                 "Number of EFM Active Pairs";
             }
             leaf efm-group-bit-rate {
               type int32;
               description
                 "Bit rate (in Kbps) for EFM Group";
             }
           }
           container efm-line-statistics {
             leaf line-pair {
               type int32;
               description
                 "Line Pair Number";
             }
             leaf line-status {
               type string;
             }
             container active-alarms-efm {
               leaf type-efm {
                 type string;
                 description
                   "Media type for associated interface alarms";
               }
               container interface-alarms {
                 description
                   "Container tag for interface alarms";
                 leaf alarm-not-present {
                   type empty;
                   description
                     "No alarm indicated";
                 }
                 leaf sonet-alarm-lol {
                   type empty;
                   description
                     "Loss of light alarm";
                 }
                 leaf sonet-alarm-pll {
                   type empty;
                   description
                     "PLL lock alarm";
                 }
                 leaf sonet-alarm-lof {
                   type empty;
                   description
                     "Loss of frame alarm";
                 }
                 leaf sonet-alarm-los {
                   type empty;
                   description
                     "Loss of signal alarm";
                 }
                 leaf sonet-alarm-sef {
                   type empty;
                   description
                     "Severely errored frame alarm";
                 }
                 leaf sonet-alarm-lais {
                   type empty;
                   description
                     "Line AIS alarm";
                 }
                 leaf sonet-alarm-pais {
                   type empty;
                   description
                     "Path AIS alarm";
                 }
                 leaf sonet-alarm-lop {
                   type empty;
                   description
                     "Loss of pointer alarm";
                 }
                 leaf sonet-alarm-berr-sd {
                   type empty;
                   description
                     "Bit error rate alarm, defect";
                 }
                 leaf sonet-alarm-berr-sf {
                   type empty;
                   description
                     "Bit error rate alarm, fault";
                 }
                 leaf sonet-alarm-lrdi {
                   type empty;
                   description
                     "Line remote defect indicator alarm";
                 }
                 leaf sonet-alarm-prdi {
                   type empty;
                   description
                     "Path remote defect indicator alarm";
                 }
                 leaf sonet-alarm-rei {
                   type empty;
                   description
                     "Path remote error indicator alarm";
                 }
                 leaf sonet-alarm-uneq {
                   type empty;
                   description
                     "Unequipped alarm";
                 }
                 leaf sonet-alarm-pmis {
                   type empty;
                   description
                     "Path payload level mismatch alarm";
                 }
                 leaf sonet-alarm-loc {
                   type empty;
                   description
                     "Loss of cell delineation alarm";
                 }
                 leaf sonet-alarm-vais {
                   type empty;
                   description
                     "VT AIS alarm";
                 }
                 leaf sonet-alarm-vlop {
                   type empty;
                   description
                     "VT loss of pointer alarm";
                 }
                 leaf sonet-alarm-vrdi {
                   type empty;
                   description
                     "VT remote defect indicator alarm";
                 }
                 leaf sonet-alarm-vuneq {
                   type empty;
                   description
                     "VT unequipped alarm";
                 }
                 leaf sonet-alarm-vmis {
                   type empty;
                   description
                     "VT label mismatch alarm";
                 }
                 leaf sonet-alarm-vloc {
                   type empty;
                   description
                     "VT loss of cell delineation alarm";
                 }
                 leaf sdh-alarm-lol {
                   type empty;
                   description
                     "Loss of light alarm";
                 }
                 leaf sdh-alarm-pll {
                   type empty;
                   description
                     "PLL lock alarm";
                 }
                 leaf sdh-alarm-lof {
                   type empty;
                   description
                     "Loss of frame alarm";
                 }
                 leaf sdh-alarm-los {
                   type empty;
                   description
                     "Loss of signal alarm";
                 }
                 leaf sdh-alarm-oof {
                   type empty;
                   description
                     "Out of frame alarm";
                 }
                 leaf sdh-alarm-msais {
                   type empty;
                   description
                     "Multiplex section AIS alarm";
                 }
                 leaf sdh-alarm-hpais {
                   type empty;
                   description
                     "High order path AIS alarm";
                 }
                 leaf sdh-alarm-lop {
                   type empty;
                   description
                     "Loss of pointer alarm";
                 }
                 leaf sdh-alarm-berr-sd {
                   type empty;
                   description
                     "Bit error rate alarm, defect";
                 }
                 leaf sdh-alarm-berr-sf {
                   type empty;
                   description
                     "Bit error rate alarm, fault";
                 }
                 leaf sdh-alarm-msferf {
                   type empty;
                   description
                     "Multiplex section far-end remote failure alarm";
                 }
                 leaf sdh-alarm-hpferf {
                   type empty;
                   description
                     "High order path far-end remote failure alarm";
                 }
                 leaf sdh-alarm-hpfebe {
                   type empty;
                   description
                     "High order path far-end block error alarm";
                 }
                 leaf sdh-alarm-hpuneq {
                   type empty;
                   description
                     "High order path unequipped alarm";
                 }
                 leaf sdh-alarm-hpplm {
                   type empty;
                   description
                     "High order path payload level mismatch alarm";
                 }
                 leaf sdh-alarm-loc {
                   type empty;
                   description
                     "Loss of cell delineation alarm";
                 }
                 leaf sdh-alarm-tuais {
                   type empty;
                   description
                     "TU AIS alarm";
                 }
                 leaf sdh-alarm-tulop {
                   type empty;
                   description
                     "TU loss of pointer alarm";
                 }
                 leaf sdh-alarm-turdi {
                   type empty;
                   description
                     "TU remote defect indicator alarm";
                 }
                 leaf sdh-alarm-tuuneq {
                   type empty;
                   description
                     "TU unequipped alarm";
                 }
                 leaf sdh-alarm-tumis {
                   type empty;
                   description
                     "TU label mismatch error";
                 }
                 leaf sdh-alarm-tuloc {
                   type empty;
                   description
                     "TU loss of cell delineation alarm";
                 }
                 leaf ds3-alarm-pll {
                   type empty;
                   description
                     "PLL lock alarm";
                 }
                 leaf ds3-alarm-ais {
                   type empty;
                   description
                     "AIS alarm";
                 }
                 leaf ds3-alarm-lof {
                   type empty;
                   description
                     "Loss of frame alarm";
                 }
                 leaf ds3-alarm-los {
                   type empty;
                   description
                     "Loss of signal alarm";
                 }
                 leaf ds3-alarm-lcv {
                   type empty;
                   description
                     "Line code violation alarm";
                 }
                 leaf ds3-alarm-exz {
                   type empty;
                   description
                     "Excessive zeros alarm";
                 }
                 leaf ds3-alarm-ferf {
                   type empty;
                   description
                     "Far-end receive failure alarm";
                 }
                 leaf ds3-alarm-ylw {
                   type empty;
                   description
                     "Yellow alarm";
                 }
                 leaf ds3-alarm-idle {
                   type empty;
                   description
                     "Idle alarm";
                 }
                 leaf ds1-alarm-ais {
                   type empty;
                   description
                     "AIS alarm";
                 }
                 leaf ds1-alarm-lof {
                   type empty;
                   description
                     "Loss of frame alarm";
                 }
                 leaf ds1-alarm-los {
                   type empty;
                   description
                     "Loss of signal alarm";
                 }
                 leaf ds1-alarm-ylw {
                   type empty;
                   description
                     "Yellow alarm";
                 }
                 leaf ds1-alarm-crc-major {
                   type empty;
                   description
                     "CRC errors crossed major threshold";
                 }
                 leaf ds1-alarm-crc-minor {
                   type empty;
                   description
                     "CRC errors crossed minor threshold";
                 }
                 leaf dsl-alarm-lof {
                   type empty;
                   description
                     "Loss of frame alarm";
                 }
                 leaf dsl-alarm-los {
                   type empty;
                   description
                     "Loss of signal alarm";
                 }
                 leaf dsl-alarm-lom {
                   type empty;
                   description
                     "Loss of multiframe alarm";
                 }
                 leaf dsl-alarm-locdi {
                   type empty;
                   description
                     "Loss of cell delineation alarm for interleaved channel";
                 }
                 leaf dsl-alarm-locdni {
                   type empty;
                   description
                     "Loss of cell delineation alarm for non-interleaved 
                     channel";
                 }
                 leaf dsl-alarm-lop {
                   type empty;
                   description
                     "Loss of power alarm";
                 }
                 leaf dsl-alarm-far-lof {
                   type empty;
                   description
                     "Far-end loss-of-frame alarm";
                 }
                 leaf dsl-alarm-far-los {
                   type empty;
                   description
                     "Far-end loss-of-signal alarm";
                 }
                 leaf dsl-alarm-far-locdi {
                   type empty;
                   description
                     "Far-end loss-of-cell-delineation alarm for interleaved
                     channel";
                 }
                 leaf dsl-alarm-far-locdni {
                   type empty;
                   description
                     "Far-end loss-of-cell-delineation alarm for 
                     non-interleaved channel";
                 }
                 leaf fibrechannel-alarm-link-down {
                   type empty;
                   description
                     "Link alive failure";
                 }
                 leaf ethernet-alarm-link-down {
                   type empty;
                   description
                     "Link alive failure";
                 }
                 leaf ethernet-alarm-link-local-fault {
                   type empty;
                   description
                     "Link local fault";
                 }
                 leaf ethernet-alarm-link-remote-fault {
                   type empty;
                   description
                     "Link remote fault";
                 }
                 leaf ethernet-alarm-lcdp {
                   type empty;
                   description
                     "Loss of code-group delineation";
                 }
                 leaf isdn-alarm-los {
                   type empty;
                   description
                     "Loss of signal alarm";
                 }
                 leaf isdn-alarm-lof {
                   type empty;
                   description
                     "Loss of frame alarm";
                 }
                 leaf shdsl-alarm-losd {
                   type empty;
                   description
                     "Loss of signal alarm";
                 }
                 leaf shdsl-alarm-losw {
                   type empty;
                   description
                     "Loss of sync word alarm";
                 }
                 leaf shdsl-alarm-line1-losd {
                   type empty;
                   description
                     "Loss of signal (line 1) alarm";
                 }
                 leaf shdsl-alarm-line1-losw {
                   type empty;
                   description
                     "Loss of sync word (line 1) alarm";
                 }
                 leaf shdsl-alarm-line2-losd {
                   type empty;
                   description
                     "Loss of signal (line 2) alarm";
                 }
                 leaf shdsl-alarm-line2-losw {
                   type empty;
                   description
                     "Loss of sync word (line 2) alarm";
                 }
                 leaf shdsl-efm-alarm-losd {
                   type empty;
                   description
                     "Loss of signal alarm";
                 }
                 leaf shdsl-efm-alarm-losw {
                   type empty;
                   description
                     "Loss of sync word alarm";
                 }
                 leaf otn-alarm-los {
                   type empty;
                   description
                     "Loss of signal alarm";
                 }
                 leaf otn-alarm-lof {
                   type empty;
                   description
                     "Loss of frame alarm";
                 }
                 leaf otn-alarm-lom {
                   type empty;
                   description
                     "Loss of multiframe alarm";
                 }
                 leaf otn-alarm-wavelength-lock {
                   type empty;
                   description
                     "Loss of Wavelength Lock alarm";
                 }
                 leaf otn-alarm-otu-ais {
                   type empty;
                   description
                     "OTU Alarm Indication Signal alarm";
                 }
                 leaf otn-alarm-otu-bdi {
                   type empty;
                   description
                     "OTU Background Block Error alarm";
                 }
                 leaf otn-alarm-otu-ttim {
                   type empty;
                   description
                     "OTU Trail Trace Identifier Mismatch alarm";
                 }
                 leaf otn-alarm-otu-iae {
                   type empty;
                   description
                     "OTU Incoming Alignment alarm";
                 }
                 leaf otn-alarm-otu-sd {
                   type empty;
                   description
                     "OTU Signal Degrade alarm";
                 }
                 leaf otn-alarm-otu-sf {
                   type empty;
                   description
                     "OTU Signal Fail alarm";
                 }
                 leaf otn-alarm-otu-biae {
                   type empty;
                   description
                     "OTU Backward Incoming Alignment alarm";
                 }
                 leaf otn-alarm-otu-tsf {
                   type empty;
                   description
                     "OTU Trail Signal Fail alarm";
                 }
                 leaf otn-alarm-otu-ssf {
                   type empty;
                   description
                     "OTU Server Signal Fail alarm";
                 }
                 leaf otn-alarm-otu-fec-excessive {
                   type empty;
                   description
                     "OTU FEC Excessive alarm";
                 }
                 leaf otn-alarm-otu-fec-degraded {
                   type empty;
                   description
                     "OTU FEC Degraded alarm";
                 }
                 leaf otn-alarm-otu-fe-fec-degraded {
                   type empty;
                   description
                     "OTU FE FEC Degraded/Excessive alarm";
                 }
                 leaf otn-alarm-otu-threshold-bbe {
                   type empty;
                   description
                     "OTU Background Block Error threshold alarm";
                 }
                 leaf otn-alarm-otu-threshold-es {
                   type empty;
                   description
                     "OTU Errored Seconds threshold alarm";
                 }
                 leaf otn-alarm-otu-threshold-ses {
                   type empty;
                   description
                     "OTU Severely Errored Seconds threshold alarm";
                 }
                 leaf otn-alarm-otu-threshold-uas {
                   type empty;
                   description
                     "OTU Unavailable Seconds threshold alarm";
                 }
                 leaf otn-alarm-odu-ais {
                   type empty;
                   description
                     "ODU  Alarm Indiaction Signal alarm";
                 }
                 leaf otn-alarm-odu-oci {
                   type empty;
                   description
                     "ODU Open Connection Indication alarm";
                 }
                 leaf otn-alarm-odu-lck {
                   type empty;
                   description
                     "ODU Locked alarm";
                 }
                 leaf otn-alarm-odu-bdi {
                   type empty;
                   description
                     "ODU Backward Defect Indication alarm";
                 }
                 leaf otn-alarm-odu-ttim {
                   type empty;
                   description
                     "ODU Trail Trace Identifier Mismatch alarm";
                 }
                 leaf otn-alarm-odu-sd {
                   type empty;
                   description
                     "ODU Signal Degrade alarm";
                 }
                 leaf otn-alarm-odu-sf {
                   type empty;
                   description
                     "ODU Signal Fail alarm";
                 }
                 leaf otn-alarm-odu-iae {
                   type empty;
                   description
                     "ODU Incoming Alignment alarm";
                 }
                 leaf otn-alarm-odu-ltc {
                   type empty;
                   description
                     "ODU Loss of Tandem Connection alarm";
                 }
                 leaf otn-alarm-odu-csf {
                   type empty;
                   description
                     "ODU Client Signal Fail alarm";
                 }
                 leaf otn-alarm-odu-tsf {
                   type empty;
                   description
                     "ODU Trail Signal Fail alarm";
                 }
                 leaf otn-alarm-odu-ssf {
                   type empty;
                   description
                     "ODU Server Signal Fail alarm";
                 }
                 leaf otn-alarm-odu-rx-aps-change {
                   type empty;
                   description
                     "ODU Rx Aps Change alarm";
                 }
                 leaf otn-alarm-odu-threshold-bbe {
                   type empty;
                   description
                     "ODU Background Block Error threshold alarm";
                 }
                 leaf otn-alarm-odu-threshold-es {
                   type empty;
                   description
                     "ODU Errored Seconds threshold alarm";
                 }
                 leaf otn-alarm-odu-threshold-ses {
                   type empty;
                   description
                     "ODU Severely Errored Seconds threshold alarm";
                 }
                 leaf otn-alarm-odu-threshold-uas {
                   type empty;
                   description
                     "ODU Unavailable Seconds threshold alarm";
                 }
                 leaf otn-alarm-opu-pmi {
                   type empty;
                   description
                     "OPU Payload Mismatch alarm";
                 }
                 leaf otn-alarm-pre-fec-sd {
                   type empty;
                   description
                     "Pre-FEC SD alarm";
                 }
                 leaf otn-alarm-fe-pre-fec-sd {
                   type empty;
                   description
                     "Far end pre-FEC SD alarm";
                 }
                 leaf optics-alarms-mod-fault {
                   type empty;
                   description
                     "Module Fault alarm";
                 }
                 leaf optics-alarms-lol {
                   type empty;
                   description
                     "Loss of Lock alarm";
                 }
                 leaf optics-alarms-los {
                   type empty;
                   description
                     "Loss of Signal alarms";
                 }
                 leaf optics-alarms-lof {
                   type empty;
                   description
                     "Loss of frame alarm";
                 }
                 leaf optics-alarms-lom {
                   type empty;
                   description
                     "Loss of multi-frame alarm";
                 }
                 leaf optics-alarms-otu-bdi {
                   type empty;
                   description
                     "Backward defect indiacation alarm";
                 }
                 leaf optics-alarms-rmsf {
                   type empty;
                   description
                     "Rx Modem sysnc fault alarm";
                 }
                 leaf optics-alarms-rmlol {
                   type empty;
                   description
                     "Rx Modem loss of lock alarm";
                 }
                 leaf optics-alarms-rloa {
                   type empty;
                   description
                     "Rx loss of alignment alarm";
                 }
                 leaf optics-alarms-mbclf {
                   type empty;
                   description
                     "Modulator Bias control loop fail alarm";
                 }
                 leaf optics-alarms-itlaf {
                   type empty;
                   description
                     "ITLA Fault alarm";
                 }
                 leaf optics-alarms-daccf {
                   type empty;
                   description
                     "DAC Calibration Fault alarm";
                 }
                 leaf optics-alarms-adccf {
                   type empty;
                   description
                     "ADC Calibration Fault alarm";
                 }
                 leaf optics-alarms-fec-degrade {
                   type empty;
                   description
                     "FEC Degrade alarm";
                 }
                 leaf optics-alarms-fec-excessive {
                   type empty;
                   description
                     "FEC Excessive alarm";
                 }
                 leaf optics-alarms-fe-fec-degrade {
                   type empty;
                   description
                     "Far-end FEC Degrade alarm";
                 }
                 leaf optics-alarms-fe-fec-excessive {
                   type empty;
                   description
                     "Far-end FEC Excessive alarm";
                 }
                 leaf ima-alarm-startup-fe {
                   type empty;
                   description
                     "IMA group startup far-end alarm";
                 }
                 leaf ima-alarm-config-abort {
                   type empty;
                   description
                     "IMA group config abort alarm";
                 }
                 leaf ima-alarm-config-abort-fe {
                   type empty;
                   description
                     "IMA group config abort far-end alarm";
                 }
                 leaf ima-alarm-insufficient-links {
                   type empty;
                   description
                     "IMA group insufficient links alarm";
                 }
                 leaf ima-alarm-insufficient-links-fe {
                   type empty;
                   description
                     "IMA group insufficient links far-end alarm";
                 }
                 leaf ima-alarm-blocked {
                   type empty;
                   description
                     "IMA group blocked alarm";
                 }
                 leaf ima-alarm-blocked-fe {
                   type empty;
                   description
                     "IMA group blocked far-end alarm";
                 }
                 leaf ima-alarm-timing-mismatch {
                   type empty;
                   description
                     "IMA group timing mismatch alarm";
                 }
                 leaf ima-alarm-version-mismatch {
                   type empty;
                   description
                     "IMA group version mismatch alarm";
                 }
                 leaf ima-alarm-lif {
                   type empty;
                   description
                     "IMA link loss of IMA frame alarm";
                 }
                 leaf ima-alarm-lods {
                   type empty;
                   description
                     "IMA link out of delay synchronization alarm";
                 }
                 leaf ima-alarm-rdi {
                   type empty;
                   description
                     "IMA link remote defect indicator alarm";
                 }
                 leaf ima-alarm-tx-misconnected {
                   type empty;
                   description
                     "IMA link tx misconnected alarm";
                 }
                 leaf ima-alarm-rx-misconnected {
                   type empty;
                   description
                     "IMA link rx misconnected alarm";
                 }
                 leaf ima-alarm-fault {
                   type empty;
                   description
                     "IMA link fault alarm";
                 }
                 leaf ima-alarm-tx-unusable-fe {
                   type empty;
                   description
                     "IMA link Tx unusable far-end alarm";
                 }
                 leaf ima-alarm-rx-unusable-fe {
                   type empty;
                   description
                     "IMA link Tx unusable far-end alarm";
                 }
                 leaf generic-value {
                   type int32;
                   description
                     "Hexadecimal value of unknown flag bits";
                 }
               }
             }
             container active-defects-efm {
               leaf type-efm {
                 type string;
                 description
                   "Media type for associated interface alarms";
               }
               container interface-alarms {
                 description
                   "Container tag for interface alarms";
                 leaf alarm-not-present {
                   type empty;
                   description
                     "No alarm indicated";
                 }
                 leaf sonet-alarm-lol {
                   type empty;
                   description
                     "Loss of light alarm";
                 }
                 leaf sonet-alarm-pll {
                   type empty;
                   description
                     "PLL lock alarm";
                 }
                 leaf sonet-alarm-lof {
                   type empty;
                   description
                     "Loss of frame alarm";
                 }
                 leaf sonet-alarm-los {
                   type empty;
                   description
                     "Loss of signal alarm";
                 }
                 leaf sonet-alarm-sef {
                   type empty;
                   description
                     "Severely errored frame alarm";
                 }
                 leaf sonet-alarm-lais {
                   type empty;
                   description
                     "Line AIS alarm";
                 }
                 leaf sonet-alarm-pais {
                   type empty;
                   description
                     "Path AIS alarm";
                 }
                 leaf sonet-alarm-lop {
                   type empty;
                   description
                     "Loss of pointer alarm";
                 }
                 leaf sonet-alarm-berr-sd {
                   type empty;
                   description
                     "Bit error rate alarm, defect";
                 }
                 leaf sonet-alarm-berr-sf {
                   type empty;
                   description
                     "Bit error rate alarm, fault";
                 }
                 leaf sonet-alarm-lrdi {
                   type empty;
                   description
                     "Line remote defect indicator alarm";
                 }
                 leaf sonet-alarm-prdi {
                   type empty;
                   description
                     "Path remote defect indicator alarm";
                 }
                 leaf sonet-alarm-rei {
                   type empty;
                   description
                     "Path remote error indicator alarm";
                 }
                 leaf sonet-alarm-uneq {
                   type empty;
                   description
                     "Unequipped alarm";
                 }
                 leaf sonet-alarm-pmis {
                   type empty;
                   description
                     "Path payload level mismatch alarm";
                 }
                 leaf sonet-alarm-loc {
                   type empty;
                   description
                     "Loss of cell delineation alarm";
                 }
                 leaf sonet-alarm-vais {
                   type empty;
                   description
                     "VT AIS alarm";
                 }
                 leaf sonet-alarm-vlop {
                   type empty;
                   description
                     "VT loss of pointer alarm";
                 }
                 leaf sonet-alarm-vrdi {
                   type empty;
                   description
                     "VT remote defect indicator alarm";
                 }
                 leaf sonet-alarm-vuneq {
                   type empty;
                   description
                     "VT unequipped alarm";
                 }
                 leaf sonet-alarm-vmis {
                   type empty;
                   description
                     "VT label mismatch alarm";
                 }
                 leaf sonet-alarm-vloc {
                   type empty;
                   description
                     "VT loss of cell delineation alarm";
                 }
                 leaf sdh-alarm-lol {
                   type empty;
                   description
                     "Loss of light alarm";
                 }
                 leaf sdh-alarm-pll {
                   type empty;
                   description
                     "PLL lock alarm";
                 }
                 leaf sdh-alarm-lof {
                   type empty;
                   description
                     "Loss of frame alarm";
                 }
                 leaf sdh-alarm-los {
                   type empty;
                   description
                     "Loss of signal alarm";
                 }
                 leaf sdh-alarm-oof {
                   type empty;
                   description
                     "Out of frame alarm";
                 }
                 leaf sdh-alarm-msais {
                   type empty;
                   description
                     "Multiplex section AIS alarm";
                 }
                 leaf sdh-alarm-hpais {
                   type empty;
                   description
                     "High order path AIS alarm";
                 }
                 leaf sdh-alarm-lop {
                   type empty;
                   description
                     "Loss of pointer alarm";
                 }
                 leaf sdh-alarm-berr-sd {
                   type empty;
                   description
                     "Bit error rate alarm, defect";
                 }
                 leaf sdh-alarm-berr-sf {
                   type empty;
                   description
                     "Bit error rate alarm, fault";
                 }
                 leaf sdh-alarm-msferf {
                   type empty;
                   description
                     "Multiplex section far-end remote failure alarm";
                 }
                 leaf sdh-alarm-hpferf {
                   type empty;
                   description
                     "High order path far-end remote failure alarm";
                 }
                 leaf sdh-alarm-hpfebe {
                   type empty;
                   description
                     "High order path far-end block error alarm";
                 }
                 leaf sdh-alarm-hpuneq {
                   type empty;
                   description
                     "High order path unequipped alarm";
                 }
                 leaf sdh-alarm-hpplm {
                   type empty;
                   description
                     "High order path payload level mismatch alarm";
                 }
                 leaf sdh-alarm-loc {
                   type empty;
                   description
                     "Loss of cell delineation alarm";
                 }
                 leaf sdh-alarm-tuais {
                   type empty;
                   description
                     "TU AIS alarm";
                 }
                 leaf sdh-alarm-tulop {
                   type empty;
                   description
                     "TU loss of pointer alarm";
                 }
                 leaf sdh-alarm-turdi {
                   type empty;
                   description
                     "TU remote defect indicator alarm";
                 }
                 leaf sdh-alarm-tuuneq {
                   type empty;
                   description
                     "TU unequipped alarm";
                 }
                 leaf sdh-alarm-tumis {
                   type empty;
                   description
                     "TU label mismatch error";
                 }
                 leaf sdh-alarm-tuloc {
                   type empty;
                   description
                     "TU loss of cell delineation alarm";
                 }
                 leaf ds3-alarm-pll {
                   type empty;
                   description
                     "PLL lock alarm";
                 }
                 leaf ds3-alarm-ais {
                   type empty;
                   description
                     "AIS alarm";
                 }
                 leaf ds3-alarm-lof {
                   type empty;
                   description
                     "Loss of frame alarm";
                 }
                 leaf ds3-alarm-los {
                   type empty;
                   description
                     "Loss of signal alarm";
                 }
                 leaf ds3-alarm-lcv {
                   type empty;
                   description
                     "Line code violation alarm";
                 }
                 leaf ds3-alarm-exz {
                   type empty;
                   description
                     "Excessive zeros alarm";
                 }
                 leaf ds3-alarm-ferf {
                   type empty;
                   description
                     "Far-end receive failure alarm";
                 }
                 leaf ds3-alarm-ylw {
                   type empty;
                   description
                     "Yellow alarm";
                 }
                 leaf ds3-alarm-idle {
                   type empty;
                   description
                     "Idle alarm";
                 }
                 leaf ds1-alarm-ais {
                   type empty;
                   description
                     "AIS alarm";
                 }
                 leaf ds1-alarm-lof {
                   type empty;
                   description
                     "Loss of frame alarm";
                 }
                 leaf ds1-alarm-los {
                   type empty;
                   description
                     "Loss of signal alarm";
                 }
                 leaf ds1-alarm-ylw {
                   type empty;
                   description
                     "Yellow alarm";
                 }
                 leaf ds1-alarm-crc-major {
                   type empty;
                   description
                     "CRC errors crossed major threshold";
                 }
                 leaf ds1-alarm-crc-minor {
                   type empty;
                   description
                     "CRC errors crossed minor threshold";
                 }
                 leaf dsl-alarm-lof {
                   type empty;
                   description
                     "Loss of frame alarm";
                 }
                 leaf dsl-alarm-los {
                   type empty;
                   description
                     "Loss of signal alarm";
                 }
                 leaf dsl-alarm-lom {
                   type empty;
                   description
                     "Loss of multiframe alarm";
                 }
                 leaf dsl-alarm-locdi {
                   type empty;
                   description
                     "Loss of cell delineation alarm for interleaved channel";
                 }
                 leaf dsl-alarm-locdni {
                   type empty;
                   description
                     "Loss of cell delineation alarm for non-interleaved 
                     channel";
                 }
                 leaf dsl-alarm-lop {
                   type empty;
                   description
                     "Loss of power alarm";
                 }
                 leaf dsl-alarm-far-lof {
                   type empty;
                   description
                     "Far-end loss-of-frame alarm";
                 }
                 leaf dsl-alarm-far-los {
                   type empty;
                   description
                     "Far-end loss-of-signal alarm";
                 }
                 leaf dsl-alarm-far-locdi {
                   type empty;
                   description
                     "Far-end loss-of-cell-delineation alarm for interleaved
                     channel";
                 }
                 leaf dsl-alarm-far-locdni {
                   type empty;
                   description
                     "Far-end loss-of-cell-delineation alarm for 
                     non-interleaved channel";
                 }
                 leaf fibrechannel-alarm-link-down {
                   type empty;
                   description
                     "Link alive failure";
                 }
                 leaf ethernet-alarm-link-down {
                   type empty;
                   description
                     "Link alive failure";
                 }
                 leaf ethernet-alarm-link-local-fault {
                   type empty;
                   description
                     "Link local fault";
                 }
                 leaf ethernet-alarm-link-remote-fault {
                   type empty;
                   description
                     "Link remote fault";
                 }
                 leaf ethernet-alarm-lcdp {
                   type empty;
                   description
                     "Loss of code-group delineation";
                 }
                 leaf isdn-alarm-los {
                   type empty;
                   description
                     "Loss of signal alarm";
                 }
                 leaf isdn-alarm-lof {
                   type empty;
                   description
                     "Loss of frame alarm";
                 }
                 leaf shdsl-alarm-losd {
                   type empty;
                   description
                     "Loss of signal alarm";
                 }
                 leaf shdsl-alarm-losw {
                   type empty;
                   description
                     "Loss of sync word alarm";
                 }
                 leaf shdsl-alarm-line1-losd {
                   type empty;
                   description
                     "Loss of signal (line 1) alarm";
                 }
                 leaf shdsl-alarm-line1-losw {
                   type empty;
                   description
                     "Loss of sync word (line 1) alarm";
                 }
                 leaf shdsl-alarm-line2-losd {
                   type empty;
                   description
                     "Loss of signal (line 2) alarm";
                 }
                 leaf shdsl-alarm-line2-losw {
                   type empty;
                   description
                     "Loss of sync word (line 2) alarm";
                 }
                 leaf shdsl-efm-alarm-losd {
                   type empty;
                   description
                     "Loss of signal alarm";
                 }
                 leaf shdsl-efm-alarm-losw {
                   type empty;
                   description
                     "Loss of sync word alarm";
                 }
                 leaf otn-alarm-los {
                   type empty;
                   description
                     "Loss of signal alarm";
                 }
                 leaf otn-alarm-lof {
                   type empty;
                   description
                     "Loss of frame alarm";
                 }
                 leaf otn-alarm-lom {
                   type empty;
                   description
                     "Loss of multiframe alarm";
                 }
                 leaf otn-alarm-wavelength-lock {
                   type empty;
                   description
                     "Loss of Wavelength Lock alarm";
                 }
                 leaf otn-alarm-otu-ais {
                   type empty;
                   description
                     "OTU Alarm Indication Signal alarm";
                 }
                 leaf otn-alarm-otu-bdi {
                   type empty;
                   description
                     "OTU Background Block Error alarm";
                 }
                 leaf otn-alarm-otu-ttim {
                   type empty;
                   description
                     "OTU Trail Trace Identifier Mismatch alarm";
                 }
                 leaf otn-alarm-otu-iae {
                   type empty;
                   description
                     "OTU Incoming Alignment alarm";
                 }
                 leaf otn-alarm-otu-sd {
                   type empty;
                   description
                     "OTU Signal Degrade alarm";
                 }
                 leaf otn-alarm-otu-sf {
                   type empty;
                   description
                     "OTU Signal Fail alarm";
                 }
                 leaf otn-alarm-otu-biae {
                   type empty;
                   description
                     "OTU Backward Incoming Alignment alarm";
                 }
                 leaf otn-alarm-otu-tsf {
                   type empty;
                   description
                     "OTU Trail Signal Fail alarm";
                 }
                 leaf otn-alarm-otu-ssf {
                   type empty;
                   description
                     "OTU Server Signal Fail alarm";
                 }
                 leaf otn-alarm-otu-fec-excessive {
                   type empty;
                   description
                     "OTU FEC Excessive alarm";
                 }
                 leaf otn-alarm-otu-fec-degraded {
                   type empty;
                   description
                     "OTU FEC Degraded alarm";
                 }
                 leaf otn-alarm-otu-fe-fec-degraded {
                   type empty;
                   description
                     "OTU FE FEC Degraded/Excessive alarm";
                 }
                 leaf otn-alarm-otu-threshold-bbe {
                   type empty;
                   description
                     "OTU Background Block Error threshold alarm";
                 }
                 leaf otn-alarm-otu-threshold-es {
                   type empty;
                   description
                     "OTU Errored Seconds threshold alarm";
                 }
                 leaf otn-alarm-otu-threshold-ses {
                   type empty;
                   description
                     "OTU Severely Errored Seconds threshold alarm";
                 }
                 leaf otn-alarm-otu-threshold-uas {
                   type empty;
                   description
                     "OTU Unavailable Seconds threshold alarm";
                 }
                 leaf otn-alarm-odu-ais {
                   type empty;
                   description
                     "ODU  Alarm Indiaction Signal alarm";
                 }
                 leaf otn-alarm-odu-oci {
                   type empty;
                   description
                     "ODU Open Connection Indication alarm";
                 }
                 leaf otn-alarm-odu-lck {
                   type empty;
                   description
                     "ODU Locked alarm";
                 }
                 leaf otn-alarm-odu-bdi {
                   type empty;
                   description
                     "ODU Backward Defect Indication alarm";
                 }
                 leaf otn-alarm-odu-ttim {
                   type empty;
                   description
                     "ODU Trail Trace Identifier Mismatch alarm";
                 }
                 leaf otn-alarm-odu-sd {
                   type empty;
                   description
                     "ODU Signal Degrade alarm";
                 }
                 leaf otn-alarm-odu-sf {
                   type empty;
                   description
                     "ODU Signal Fail alarm";
                 }
                 leaf otn-alarm-odu-iae {
                   type empty;
                   description
                     "ODU Incoming Alignment alarm";
                 }
                 leaf otn-alarm-odu-ltc {
                   type empty;
                   description
                     "ODU Loss of Tandem Connection alarm";
                 }
                 leaf otn-alarm-odu-csf {
                   type empty;
                   description
                     "ODU Client Signal Fail alarm";
                 }
                 leaf otn-alarm-odu-tsf {
                   type empty;
                   description
                     "ODU Trail Signal Fail alarm";
                 }
                 leaf otn-alarm-odu-ssf {
                   type empty;
                   description
                     "ODU Server Signal Fail alarm";
                 }
                 leaf otn-alarm-odu-rx-aps-change {
                   type empty;
                   description
                     "ODU Rx Aps Change alarm";
                 }
                 leaf otn-alarm-odu-threshold-bbe {
                   type empty;
                   description
                     "ODU Background Block Error threshold alarm";
                 }
                 leaf otn-alarm-odu-threshold-es {
                   type empty;
                   description
                     "ODU Errored Seconds threshold alarm";
                 }
                 leaf otn-alarm-odu-threshold-ses {
                   type empty;
                   description
                     "ODU Severely Errored Seconds threshold alarm";
                 }
                 leaf otn-alarm-odu-threshold-uas {
                   type empty;
                   description
                     "ODU Unavailable Seconds threshold alarm";
                 }
                 leaf otn-alarm-opu-pmi {
                   type empty;
                   description
                     "OPU Payload Mismatch alarm";
                 }
                 leaf otn-alarm-pre-fec-sd {
                   type empty;
                   description
                     "Pre-FEC SD alarm";
                 }
                 leaf otn-alarm-fe-pre-fec-sd {
                   type empty;
                   description
                     "Far end pre-FEC SD alarm";
                 }
                 leaf optics-alarms-mod-fault {
                   type empty;
                   description
                     "Module Fault alarm";
                 }
                 leaf optics-alarms-lol {
                   type empty;
                   description
                     "Loss of Lock alarm";
                 }
                 leaf optics-alarms-los {
                   type empty;
                   description
                     "Loss of Signal alarms";
                 }
                 leaf optics-alarms-lof {
                   type empty;
                   description
                     "Loss of frame alarm";
                 }
                 leaf optics-alarms-lom {
                   type empty;
                   description
                     "Loss of multi-frame alarm";
                 }
                 leaf optics-alarms-otu-bdi {
                   type empty;
                   description
                     "Backward defect indiacation alarm";
                 }
                 leaf optics-alarms-rmsf {
                   type empty;
                   description
                     "Rx Modem sysnc fault alarm";
                 }
                 leaf optics-alarms-rmlol {
                   type empty;
                   description
                     "Rx Modem loss of lock alarm";
                 }
                 leaf optics-alarms-rloa {
                   type empty;
                   description
                     "Rx loss of alignment alarm";
                 }
                 leaf optics-alarms-mbclf {
                   type empty;
                   description
                     "Modulator Bias control loop fail alarm";
                 }
                 leaf optics-alarms-itlaf {
                   type empty;
                   description
                     "ITLA Fault alarm";
                 }
                 leaf optics-alarms-daccf {
                   type empty;
                   description
                     "DAC Calibration Fault alarm";
                 }
                 leaf optics-alarms-adccf {
                   type empty;
                   description
                     "ADC Calibration Fault alarm";
                 }
                 leaf optics-alarms-fec-degrade {
                   type empty;
                   description
                     "FEC Degrade alarm";
                 }
                 leaf optics-alarms-fec-excessive {
                   type empty;
                   description
                     "FEC Excessive alarm";
                 }
                 leaf optics-alarms-fe-fec-degrade {
                   type empty;
                   description
                     "Far-end FEC Degrade alarm";
                 }
                 leaf optics-alarms-fe-fec-excessive {
                   type empty;
                   description
                     "Far-end FEC Excessive alarm";
                 }
                 leaf ima-alarm-startup-fe {
                   type empty;
                   description
                     "IMA group startup far-end alarm";
                 }
                 leaf ima-alarm-config-abort {
                   type empty;
                   description
                     "IMA group config abort alarm";
                 }
                 leaf ima-alarm-config-abort-fe {
                   type empty;
                   description
                     "IMA group config abort far-end alarm";
                 }
                 leaf ima-alarm-insufficient-links {
                   type empty;
                   description
                     "IMA group insufficient links alarm";
                 }
                 leaf ima-alarm-insufficient-links-fe {
                   type empty;
                   description
                     "IMA group insufficient links far-end alarm";
                 }
                 leaf ima-alarm-blocked {
                   type empty;
                   description
                     "IMA group blocked alarm";
                 }
                 leaf ima-alarm-blocked-fe {
                   type empty;
                   description
                     "IMA group blocked far-end alarm";
                 }
                 leaf ima-alarm-timing-mismatch {
                   type empty;
                   description
                     "IMA group timing mismatch alarm";
                 }
                 leaf ima-alarm-version-mismatch {
                   type empty;
                   description
                     "IMA group version mismatch alarm";
                 }
                 leaf ima-alarm-lif {
                   type empty;
                   description
                     "IMA link loss of IMA frame alarm";
                 }
                 leaf ima-alarm-lods {
                   type empty;
                   description
                     "IMA link out of delay synchronization alarm";
                 }
                 leaf ima-alarm-rdi {
                   type empty;
                   description
                     "IMA link remote defect indicator alarm";
                 }
                 leaf ima-alarm-tx-misconnected {
                   type empty;
                   description
                     "IMA link tx misconnected alarm";
                 }
                 leaf ima-alarm-rx-misconnected {
                   type empty;
                   description
                     "IMA link rx misconnected alarm";
                 }
                 leaf ima-alarm-fault {
                   type empty;
                   description
                     "IMA link fault alarm";
                 }
                 leaf ima-alarm-tx-unusable-fe {
                   type empty;
                   description
                     "IMA link Tx unusable far-end alarm";
                 }
                 leaf ima-alarm-rx-unusable-fe {
                   type empty;
                   description
                     "IMA link Tx unusable far-end alarm";
                 }
                 leaf generic-value {
                   type int32;
                   description
                     "Hexadecimal value of unknown flag bits";
                 }
               }
             }
             container media-information {
               description
                 "Information about media alarms";
               leaf media-type {
                 type string;
                 description
                   "Type of media this information is for";
               }
               list media-alarm {
                 leaf media-alarm-name {
                   type string;
                 }
                 leaf media-alarm-count {
                   type int32;
                 }
                 leaf media-alarm-seconds {
                   type int32;
                 }
                 leaf media-alarm-state {
                   type string;
                 }
                 leaf ce-counter-name {
                   type string;
                   description
                     "Circuit Emulation counter information";
                 }
                 leaf ce-counter-packets {
                   type int32;
                   description
                     "Circuit Emulation number of packets";
                 }
                 leaf ce-counter-bytes {
                   type int32;
                   description
                     "Circuit Emulation number of bytes";
                 }
                 leaf ce-counter-count {
                   type int32;
                   description
                     "Circuit Emulation number of event occurrences";
                 }
               }
               leaf ds1-timeslots {
                 type string;
               }
               leaf ds1-line-encoding {
                 type string;
               }
               leaf ds1-byte-encoding {
                 type string;
               }
               leaf ds1-data-inversion {
                 type string;
               }
               leaf idle-cycle-flag {
                 type string;
               }
               leaf start-end-flag {
                 type string;
               }
               leaf ds0-byte-encoding {
                 type string;
               }
               leaf ds0-data-inversion {
                 type string;
               }
               leaf e3-data-inversion {
                 type string;
               }
               leaf ds1-buildout {
                 type string;
                 description
                   "Number of feet";
               }
             }
             container shdsl-information {
               description
                 "Operational information and statistics for SHDSL 
                 interfaces";
               leaf shdsl-line-termination {
                 type string;
                 description
                   "Line termination remote or central";
               }
               leaf shdsl-annex {
                 type string;
                 description
                   "Type of SHDSL annex";
               }
               leaf shdsl-line-mode {
                 type string;
                 description
                   "Two or four wire mode";
               }
               leaf shdsl-modem-status {
                 type string;
                 description
                   "Status of the SHDSL modem";
               }
               leaf shdsl-bit-rate {
                 type int32;
                 description
                   "Actual line rate";
               }
               leaf shdsl-last-fail-reason {
                 type string;
                 description
                   "Reason for last line-open failure";
               }
               leaf shdsl-last-fail-code {
                 type int32;
                 description
                   "Last line-open failure code";
               }
               leaf shdsl-framer-mode {
                 type string;
                 description
                   "Framer mode used";
               }
               leaf shdsl-paf-status {
                 type string;
                 description
                   "EFM PAF Status";
               }
               leaf shdsl-dying-gasp {
                 type string;
                 description
                   "Dying gasp is enabled or disabled";
               }
               leaf shdsl-framer-sync-status {
                 type string;
                 description
                   "Framer synchronization status";
               }
               leaf shdsl-chipset-version {
                 type int32;
                 description
                   "Version number for the DSP/framer chip";
               }
               leaf shdsl-firmware-version {
                 type string;
                 description
                   "Transreceiver firmware release number";
               }
               container shdsl-statistics {
                 leaf shdsl-loop-attenuation {
                   type int32;
                   description
                     "An estimate of the loop attenuation";
                 }
                 leaf shdsl-transmit-power {
                   type int32;
                   description
                     "Nominal transmit power";
                 }
                 leaf shdsl-receiver-gain {
                   type int32;
                   description
                     "Total receiver gain";
                 }
                 leaf shdsl-snr-sampling {
                   type int32;
                   description
                     "Received signal to noise ratio";
                 }
                 leaf shdsl-rx-cells {
                   type int32;
                   description
                     "Total ATM cells received";
                 }
                 leaf shdsl-tx-cells {
                   type int32;
                   description
                     "Total ATM cells transmitted";
                 }
                 leaf shdsl-crc {
                   type int32;
                   description
                     "Number of CRC errors";
                 }
                 leaf shdsl-sega {
                   type int32;
                   description
                     "Number of SEGA errors";
                 }
                 leaf shdsl-losw {
                   type int32;
                   description
                     "Number of LOSW  errors";
                 }
                 leaf shdsl-hec {
                   type int32;
                   description
                     "Header error check errors";
                 }
                 leaf shdsl-cell-drop {
                   type int32;
                   description
                     "Cells dropped because of errors";
                 }
               }
             }
           }
         }
         container atm-information {
           description
             "Operational information and statistics for ATM interfaces";
           leaf atm-hcs-state {
             type string;
           }
           leaf atm-loss-of-cell {
             type string;
           }
           container plcp-defects {
             list media-alarm {
               leaf media-alarm-name {
                 type string;
               }
               leaf media-alarm-seconds {
                 type int32;
               }
               leaf media-alarm-count {
                 type int32;
               }
               leaf media-alarm-state {
                 type string;
               }
             }
           }
           container atm-defects {
             list media-alarm {
               leaf media-alarm-name {
                 type string;
               }
               leaf media-alarm-seconds {
                 type int32;
               }
               leaf media-alarm-count {
                 type int32;
               }
               leaf media-alarm-state {
                 type string;
               }
             }
           }
           container plcp-statistics {
             leaf ferr-count {
               type int32;
             }
             leaf ferr-seconds {
               type int32;
             }
             leaf bipe-count {
               type int32;
             }
             leaf bipe-seconds {
               type int32;
             }
             leaf febe-count {
               type int32;
             }
             leaf febe-seconds {
               type int32;
             }
           }
           container atm-statistics {
             leaf uncorrectable-hcs-errors {
               type int32;
             }
             leaf correctable-hcs-errors {
               type int32;
             }
             leaf tx-cell-fifo-overruns {
               type int32;
             }
             leaf rx-cell-fifo-overruns {
               type int32;
             }
             leaf rx-cell-fifo-underruns {
               type int32;
             }
             leaf rx-cell-count {
               type int32;
             }
             leaf tx-cell-count {
               type int32;
             }
             leaf tx-idle-cell-count {
               type int32;
             }
             leaf vc-queue-drops {
               type int32;
             }
             leaf no-buffers {
               type int32;
             }
             leaf length-errors {
               type int32;
             }
             leaf timeouts {
               type int32;
             }
             leaf bundle-timeouts {
               type int32;
             }
             leaf rx-invalid-vcs {
               type int32;
             }
             leaf bad-crcs {
               type int32;
             }
             leaf oam-cell-no-buffers {
               type int32;
             }
           }
         }
         container modem-information {
           description
             "Operational information for MODEM interfaces";
           leaf modem-type {
             type string;
             description
               "Modem type information";
           }
           leaf init-command-str {
             type string;
             description
               "Modem initialization command string";
           }
           leaf init-status {
             type string;
             description
               "Modem initialization status";
           }
           leaf call-status {
             type string;
             description
               "Current status of call";
           }
           leaf call-duration {
             type int32;
             description
               "Duration for which call has been on";
           }
           leaf call-direction {
             type string;
             description
               "Direction of call (incoming or outgoing)";
           }
           leaf baud-rate {
             type int32;
             description
               "Modem baud rate";
           }
           leaf error-code {
             type string;
             description
               "Error string as returned by modem";
           }
         }
         container serial-information {
           description
             "Serial interfaces information and statistics";
           leaf serial-information.heading {
             type string;
             description
               "Serial interfaces information and statistics";
           }
           leaf dce-loopback-override {
             type string;
           }
           container line-protocol {
             leaf line-protocol-mode {
               type string;
             }
           }
           container resync-history {
             leaf resync-counter {
               type int32;
             }
             leaf resync-timestamp {
               type string;
             }
           }
           container clocking-mode {
             leaf clock-mode {
               type string;
             }
           }
           container clocking-rate {
             leaf clock-rate {
               type string;
               description
                 "Interface clock rate";
             }
           }
           container serial-encoding {
             leaf serial-encoding-conf {
               type string;
             }
           }
           container dtr-circuit {
             leaf dtr-circuit-mode {
               type string;
             }
           }
           container eia530-signal-polarity {
             leaf dtr-polarity {
               type string;
             }
             leaf rts-polarity {
               type string;
             }
             leaf dcd-polarity {
               type string;
             }
             leaf dsr-polarity {
               type string;
             }
             leaf cts-polarity {
               type string;
             }
             leaf tm-polarity {
               type string;
             }
           }
           container x21-signal-polarity {
             leaf rts-polarity {
               type string;
             }
             leaf cts-polarity {
               type string;
             }
           }
           container serial-loopback {
             leaf serial-loopback-mode {
               type string;
             }
           }
           container tx-clock {
             leaf tx-clock-mode {
               type string;
             }
           }
           container data-signal {
             leaf rx-clock {
               type string;
             }
           }
           container eia530-control-signal {
             leaf eia530-mode {
               type string;
             }
             container to-dce {
               leaf dtr {
                 type string;
               }
               leaf rts {
                 type string;
               }
               leaf cts {
                 type string;
               }
               leaf dcd {
                 type string;
               }
               leaf dsr {
                 type string;
               }
             }
             container from-dce {
               leaf dtr {
                 type string;
               }
               leaf rts {
                 type string;
               }
               leaf cts {
                 type string;
               }
               leaf dcd {
                 type string;
               }
               leaf dsr {
                 type string;
               }
               leaf tm {
                 type string;
               }
             }
             container to-dte {
               leaf dtr {
                 type string;
               }
               leaf rts {
                 type string;
               }
               leaf cts {
                 type string;
               }
               leaf dcd {
                 type string;
               }
               leaf dsr {
                 type string;
               }
             }
             container from-dte {
               leaf dtr {
                 type string;
               }
               leaf rts {
                 type string;
               }
               leaf cts {
                 type string;
               }
               leaf dcd {
                 type string;
               }
               leaf dsr {
                 type string;
               }
               leaf tm {
                 type string;
               }
             }
           }
           container x21-control-signal {
             leaf rts {
               type string;
             }
             leaf cts {
               type string;
             }
           }
         }
         container virtual-path-information {
           description
             "Operational information and statistics for a virtual path";
           leaf vpi {
             type int32;
             description
               "Virtual path identifier";
           }
           leaf atm-tm-cbr {
             type empty;
             description
               "Constant bit rate";
           }
           leaf atm-tm-vbr {
             type empty;
             description
               "Variable bit rate";
           }
           leaf atm-tm-rtvbr {
             type empty;
             description
               "Real-time variable bit rate";
           }
           leaf peak {
             type int32;
           }
           leaf sustained {
             type int32;
           }
           leaf burst {
             type int32;
           }
           leaf queue-limit {
             type int32;
           }
           leaf down-time {
             type int32;
             description
               "Total down time for this circuit";
           }
           leaf last-down-time {
             type int32;
             description
               "Time elapsed since circuit last went down";
           }
           leaf cdvt {
             type int32;
           }
           container ifvp-flags {
             leaf ifvp-down {
               type empty;
             }
             leaf ifvp-none {
               type empty;
             }
             leaf ifvp-active {
               type empty;
             }
             leaf ifvp-closed {
               type empty;
             }
             leaf ifvp-oam {
               type empty;
             }
             leaf ifvp-shaping {
               type empty;
             }
             leaf ifvp-passiveoam {
               type empty;
             }
             leaf ifvp-tunnel {
               type empty;
             }
             leaf generic-value {
               type int32;
               description
                 "Hexadecimal value of unknown flag bits";
             }
           }
           container oam-parameters {
             leaf period {
               type int32;
             }
             leaf up-count {
               type int32;
             }
             leaf down-count {
               type int32;
             }
           }
           container oam-statistics {
             description
               "Container tag for OAM statistics";
             leaf oam-total-received-count {
               type int32;
             }
             leaf oam-total-transmitted-count {
               type int32;
             }
             leaf oam-loopback-received-count {
               type int32;
             }
             leaf oam-loopback-transmitted-count {
               type int32;
             }
             leaf oam-loopback-received-last {
               type string;
             }
             leaf oam-loopback-transmitted-last {
               type string;
             }
             leaf oam-rdi-received-count {
               type int32;
             }
             leaf oam-rdi-transmitted-count {
               type int32;
             }
             leaf oam-rdi-received-last {
               type string;
             }
             leaf oam-rdi-transmitted-last {
               type string;
             }
             leaf oam-ais-received-count {
               type int32;
             }
             leaf oam-ais-transmitted-count {
               type int32;
             }
             leaf oam-ais-received-last {
               type string;
             }
             leaf oam-ais-transmitted-last {
               type string;
             }
           }
           container traffic-statistics {
             leaf input-bps {
               type int32;
             }
             leaf input-pps {
               type int32;
             }
             leaf output-bps {
               type int32;
             }
             leaf output-pps {
               type int32;
             }
             leaf input-packets {
               type int32;
             }
             leaf output-packets {
               type int32;
             }
             leaf input-bytes {
               type int32;
             }
             leaf output-bytes {
               type int32;
             }
             container ipv6-transit-statistics {
               leaf input-bytes {
                 type int32;
               }
               leaf output-bytes {
                 type int32;
               }
               leaf input-packets {
                 type int32;
               }
               leaf output-packets {
                 type int32;
               }
             }
             container ipv6-total-statistics {
               leaf input-bytes {
                 type int32;
               }
               leaf output-bytes {
                 type int32;
               }
               leaf input-packets {
                 type int32;
               }
               leaf output-packets {
                 type int32;
               }
             }
           }
         }
         container ct3-information {
           list interface-tx-queue {
             key "name";
             leaf name {
               type string;
               description
                 "Name of this item";
             }
             leaf bandwidth {
               type string;
             }
             leaf wrr {
               type string;
             }
             leaf output-packets {
               type int32;
             }
             leaf output-bytes {
               type int32;
             }
             leaf output-drops {
               type int32;
             }
             leaf output-errors {
               type int32;
             }
             leaf output-drops-bytes {
               type int32;
             }
           }
         }
         container cds1-information {
           list interface-tx-queue {
             key "name";
             leaf name {
               type string;
               description
                 "Name of this item";
             }
             leaf bandwidth {
               type string;
             }
             leaf wrr {
               type string;
             }
             leaf output-packets {
               type int32;
             }
             leaf output-bytes {
               type int32;
             }
             leaf output-drops {
               type int32;
             }
             leaf output-errors {
               type int32;
             }
             leaf output-drops-bytes {
               type int32;
             }
           }
         }
         container nxds0-information {
           list interface-tx-queue {
             key "name";
             leaf name {
               type string;
               description
                 "Name of this item";
             }
             leaf bandwidth {
               type string;
             }
             leaf wrr {
               type string;
             }
             leaf output-packets {
               type int32;
             }
             leaf output-bytes {
               type int32;
             }
             leaf output-drops {
               type int32;
             }
             leaf output-errors {
               type int32;
             }
             leaf output-drops-bytes {
               type int32;
             }
           }
         }
         container dsu-information {
           description
             "DSU configuration and statistics";
           leaf dsu-compatibility-mode {
             type string;
           }
           leaf dsu-scrambler {
             type string;
           }
           leaf dsu-subrate {
             type string;
           }
           leaf feac-loopback {
             type string;
           }
           leaf feac-response {
             type string;
           }
           leaf feac-count {
             type int32;
           }
         }
         container ds3-bert-information {
           description
             "DS3 BERT configuration and statistics";
           leaf ds3-bert-period {
             type int32;
           }
           leaf ds3-bert-elapsed {
             type int32;
           }
           leaf ds3-bert-status {
             type string;
           }
           leaf ds3-bert-algorithm {
             type string;
           }
           leaf ds3-bert-induced-error-rate {
             type int32;
           }
           leaf ds3-bert-bit-count {
             type int32;
           }
           leaf ds3-bert-bit-count-overflow {
             type int32;
           }
           leaf ds3-bert-error-bit-count {
             type int32;
           }
           leaf ds3-bert-error-bit-count-overflow {
             type int32;
           }
           leaf ds3-bert-error-rate {
             type string;
           }
           leaf ds3-bert-los-status {
             type string;
           }
           leaf ds3-bert-los-count {
             type int32;
           }
           leaf ds3-bert-los-seconds {
             type int32;
           }
         }
         container e3-bert-information {
           description
             "E3 BERT configuration and statistics";
           leaf e3-bert-period {
             type int32;
           }
           leaf e3-bert-elapsed {
             type int32;
           }
           leaf e3-bert-status {
             type string;
           }
           leaf e3-bert-algorithm {
             type string;
           }
           leaf e3-bert-induced-error-rate {
             type int32;
           }
           leaf e3-bert-bit-count {
             type int32;
           }
           leaf e3-bert-bit-count-overflow {
             type int32;
           }
           leaf e3-bert-error-bit-count {
             type int32;
           }
           leaf e3-bert-error-bit-count-overflow {
             type int32;
           }
           leaf e3-bert-error-rate {
             type string;
           }
           leaf e3-bert-los-status {
             type string;
           }
           leaf e3-bert-los-count {
             type string;
           }
           leaf e3-bert-los-seconds {
             type string;
           }
         }
         container ds1-bert-information {
           description
             "DS1 BERT configuration and statistics";
           leaf ds1-bert-period {
             type int32;
           }
           leaf ds1-bert-elapsed {
             type int32;
           }
           leaf ds1-bert-status {
             type string;
           }
           leaf ds1-bert-induced-error-rate {
             type int32;
           }
           leaf ds1-bert-algorithm {
             type string;
           }
           leaf ds1-bert-bit-count {
             type int32;
           }
           leaf ds1-bert-error-bit-count {
             type int32;
           }
           leaf ds1-bert-error-rate {
             type string;
           }
           leaf ds1-bert-los-status {
             type string;
           }
           leaf ds1-bert-los-count {
             type int32;
           }
           leaf ds1-bert-los-seconds {
             type int32;
           }
         }
         container ds0-bert-information {
           description
             "DS0 BERT configuration and statistics";
           leaf ds0-bert-period {
             type int32;
           }
           leaf ds0-bert-elapsed {
             type int32;
           }
           leaf ds0-bert-status {
             type string;
           }
           leaf ds0-bert-induced-error-rate {
             type int32;
           }
           leaf ds0-bert-algorithm {
             type string;
           }
           leaf ds0-bert-bit-count {
             type int32;
           }
           leaf ds0-bert-error-bit-count {
             type int32;
           }
           leaf ds0-bert-error-rate {
             type string;
           }
           leaf ds0-bert-los-status {
             type string;
           }
           leaf ds0-bert-los-count {
             type int32;
           }
           leaf ds0-bert-los-seconds {
             type int32;
           }
         }
         container hdlc-information {
           leaf hdlc-rx-bucket-state {
             type string;
           }
           leaf hdlc-rx-bit-rate {
             type int32;
           }
           leaf hdlc-rx-threshold {
             type int32;
           }
           leaf hdlc-tx-bucket-state {
             type string;
           }
           leaf hdlc-tx-bit-rate {
             type int32;
           }
           leaf hdlc-tx-threshold {
             type int32;
           }
           leaf hdlc-giant-threshold {
             type int32;
           }
           leaf hdlc-runt-threshold {
             type int32;
           }
         }
         container pfe-information {
           description
             "Information about Packet Forwarding Engine configuration";
           leaf destination-slot {
             type int32;
           }
           leaf destination-mask {
             type int32;
           }
           leaf stream-number {
             type int32;
           }
           leaf stream-mask {
             type int32;
           }
           leaf plp-byte-count {
             type int32;
           }
           leaf plp-byte {
             type string;
           }
           leaf pop-all-label {
             type string;
           }
         }
         list logical-interface {
           key "name";
           description
             "Information about a single logical interface";
           leaf lcp-state {
             type string;
             description
               "State of the Line Control Protocol";
           }
           leaf chap-state {
             type string;
             description
               "State of the Challenge Handshake Authentication Protocol";
           }
           leaf pap-state {
             type string;
             description
               "State of the Password Authentication Protocol";
           }
           leaf name {
             type string;
             description
               "Name of this item";
           }
           leaf local-index {
             type int32;
             description
               "Local kernel index for this interface";
           }
           leaf snmp-index {
             type int32;
             description
               "SNMP ifIndex for this interface";
           }
           leaf hardware-token {
             type int32;
             description
               "Hardware token for layer 3 ifl";
           }
           leaf generation {
             type int32;
             description
               "Generation number used to distinguish between successive 
               instances of this interface";
           }
           leaf description {
             type string;
             description
               "Description of this interface";
           }
           leaf multilink-flapped {
             type string;
             description
               "Time when the interface last flapped";
           }
           leaf logical-interface-bandwidth {
             type string;
             description
               "Bandwidth of this logical interface";
           }
           leaf link-address {
             type string;
             description
               "Link address on this logical interface";
           }
           leaf encapsulation {
             type string;
             description
               "Encapsulation on the logical interface";
           }
           leaf esi-value {
             type string;
             description
               "Ethernet segment identifier for this interface";
           }
           leaf esi-mode {
             type string;
             description
               "Ethernet segment mode for this interface";
           }
           leaf evpn-multihomed-status {
             type string;
           }
           leaf virtual-gateway-esi-value {
             type string;
             description
               "Ethernet segment identifier for this interface";
           }
           leaf virtual-gateway-esi-mode {
             type string;
             description
               "Ethernet segment mode for this interface";
           }
           leaf interface-set-name {
             type string;
             description
               "Class-of-service interface-set name";
           }
           leaf tenant-name {
             type string;
             description
               "Tenant name assigned to logical interface";
           }
           leaf demux-table-type {
             type string;
             description
               "Demux table enabled on the logical interface";
           }
           leaf gre-keepalive-configured {
             type string;
             description
               "Gre Keepalives enabled on the logical interface";
           }
           leaf gre-keepalive-adj-state {
             type string;
             description
               "Gre Keepalives enabled on the logical interface";
           }
           leaf copy-tos-to-outer-ip-header {
             type string;
             description
               "Flag that enables copying of the value in the ToS field of 
               the IP packet's payload header to the delivery header in the
               generic routingencapsulation packet";
           }
           leaf copy-tos-to-outer-ip-header-transit {
             type string;
             description
               "Flag that enables copying of the value in the ToS field of 
               the IP packet's payload header to the delivery header in the
               generic routing encapsulation transit packet";
           }
           leaf redundant-logical-interface-name {
             type string;
             description
               "Name of the redundant logical interface";
           }
           leaf logical-interface-mac {
             type string;
             description
               "MAC on the logical interface";
           }
           leaf logical-interface-vgw-v4-mac {
             type string;
             description
               "MAC on the logical interface";
           }
           leaf logical-interface-vgw-v6-mac {
             type string;
             description
               "MAC on the logical interface";
           }
           leaf vrfname {
             type string;
             description
               "Routing instance name";
           }
           leaf zonename {
             type string;
             description
               "Zone name";
           }
           leaf subunit {
             type int32;
             description
               "Subunit for this interface";
           }
           leaf dialer-time-to-disconnect {
             type string;
             description
               "Time for dialer to disconnect due to idle timeout";
           }
           container if-config-flags {
             leaf iff-none {
               type empty;
             }
             leaf iff-hardware-down {
               type empty;
             }
             leaf iff-down {
               type empty;
             }
             leaf iff-up {
               type empty;
             }
             leaf iff-admin-down {
               type empty;
             }
             leaf iff-admin-up {
               type empty;
             }
             leaf iff-link-down {
               type empty;
             }
             leaf iff-device-down {
               type empty;
             }
             leaf iff-point-to-point {
               type empty;
             }
             leaf iff-point-to-multipoint {
               type empty;
             }
             leaf plp-to-clp {
               type empty;
             }
             leaf iff-multiaccess {
               type empty;
             }
             leaf iff-change {
               type empty;
             }
             leaf iff-inverse-arp {
               type empty;
             }
             leaf iff-no-multicast {
               type empty;
             }
             leaf iff-multicast {
               type empty;
             }
             leaf iff-promiscuous {
               type empty;
             }
             leaf iff-all-multicast {
               type empty;
             }
             leaf iff-snmp-traps {
               type empty;
             }
             leaf iff-rx-passive {
               type empty;
             }
             leaf iff-tx-passive {
               type empty;
             }
             leaf iff-ccc-down {
               type empty;
             }
             leaf iff-clear-df {
               type empty;
             }
             leaf iff-tunnel-reassembly {
               type empty;
             }
             leaf iff-acfc {
               type empty;
             }
             leaf iff-pfc {
               type empty;
             }
             leaf iff-rdd {
               type empty;
             }
             leaf iff-looped {
               type empty;
             }
             leaf iff-framing-conflict {
               type empty;
             }
             leaf internal-flags {
               type int32;
               description
                 "Hexadecimal value of internal flag bits";
             }
           }
           container layer2-input-policer-information {
             description
               "Information about Layer 2 input policer for interface";
             leaf layer2-input-policer {
               type string;
               description
                 "Name of the Layer 2 input policer";
             }
           }
           container layer2-output-policer-information {
             description
               "Information about Layer 2 output policer for interface";
             leaf layer2-output-policer {
               type string;
               description
                 "Name of the Layer 2 output policer";
             }
           }
           container atm-input-policer-information {
             description
               "Information about atm input policer for interface";
             leaf atm-input-policer {
               type string;
               description
                 "Name of the atm input policer";
             }
           }
           container pppoe-information {
             description
               "PPPoE information";
             list pppoe-interface {
               leaf state {
                 type string;
                 description
                   "State";
               }
               leaf session-id {
                 type string;
                 description
                   "Session ID";
               }
               leaf ac-name-session {
                 type string;
                 description
                   "Session AC name";
               }
               leaf remote-mac {
                 type string;
                 description
                   "Remote MAC address";
               }
               leaf ac-name-config {
                 type string;
                 description
                   "Configured AC name";
               }
               leaf service-name {
                 type string;
                 description
                   "Service name";
               }
               leaf auto-reconnect {
                 type string;
                 description
                   "Autoreconnect timeout";
               }
               leaf idle-timeout {
                 type string;
                 description
                   "Idle timeout";
               }
               leaf underlying-interface-name {
                 type string;
                 description
                   "Underlying interface name";
               }
               leaf underlying-interface-index {
                 type string;
                 description
                   "Underlying interface index";
               }
               leaf padg-credits {
                 type int32;
                 description
                   "PADG transmit credits";
               }
               leaf pppoe-credit-scale-factor {
                 type string;
                 description
                   "Scaling factor";
               }
               leaf ignore-eol-tag {
                 type string;
                 description
                   "Ignore End-of-List TAG";
               }
               leaf ppp-max-payload-tag {
                 type int32;
                 description
                   "PPP-Max-Payload TAG";
               }
               leaf interface-name {
                 type string;
                 description
                   "Class-of-service interface name";
               }
               leaf interface-index {
                 type uint32;
                 description
                   "Class-of-service interface index";
               }
               leaf aci-iflset-name {
                 type string;
                 description
                   "ACI Interface Set name";
               }
               leaf aci-iflset-index {
                 type string;
                 description
                   "ACI Interface Set index";
               }
               leaf ifl-type {
                 type string;
                 description
                   "Type";
               }
               leaf session-uptime {
                 type string;
                 description
                   "Duration for which the session has been up";
               }
               leaf dynamic-profile {
                 type string;
                 description
                   "Dynamic Profile name";
               }
               leaf pppoe-credits {
                 type string;
                 description
                   "Forwarding credit balances";
               }
               leaf dynamic-interface-bandwidth {
                 type string;
                 description
                   "Dynamic interface bandwidth";
               }
               leaf agent-circuit-id {
                 type string;
                 description
                   "Agent Circuit ID";
               }
               leaf agent-remote-id {
                 type string;
                 description
                   "Agent Remote ID";
               }
               leaf padm-motm {
                 type string;
                 description
                   "PADM Message of the Moment tag";
               }
               leaf padm-hurl {
                 type string;
                 description
                   "PADM HTTP URL tag";
               }
             }
           }
           container pppoe-underlying-information {
             description
               "PPPoE Underlying information";
             list pppoe-underlying-interface {
               leaf dynamic-profile {
                 type string;
                 description
                   "Dynamic Profile name";
               }
               leaf service-name-table {
                 type string;
                 description
                   "Name of Service Name Table";
               }
               leaf max-sessions {
                 type int32;
                 description
                   "Maximum number of PPPoE sessions";
               }
               leaf max-sessions-vsa-ignore {
                 type string;
                 description
                   "Ignore max-sessions VSA";
               }
               leaf duplicate-protection {
                 type string;
                 description
                   "Duplicate protection mode";
               }
               leaf short-cycle-protection {
                 type string;
                 description
                   "Short cycle protection mode";
               }
               leaf direct-connect {
                 type string;
                 description
                   "Direct connect mode";
               }
               leaf ac-name {
                 type string;
                 description
                   "Access Concentrator name";
               }
               leaf underlying-interface-name {
                 type string;
                 description
                   "Underlying interface name";
               }
               leaf underlying-interface-index {
                 type string;
                 description
                   "Underlying interface index";
               }
               leaf encapsulation-type-identifier {
                 type string;
                 description
                   "Encapsulation type identifier";
               }
               leaf state {
                 type string;
                 description
                   "State";
               }
               leaf active-sessions {
                 type int32;
                 description
                   "Number of active PPPoE sessions";
               }
               leaf aci-autosensing {
                 type string;
                 description
                   "ACI VLAN Autosensing mode";
               }
               leaf line-identity-autosensing {
                 type string;
                 description
                   "Line Identity Autosensing mode";
               }
             }
           }
           container aci-vlan-information {
             leaf dynamic-profile {
               type string;
               description
                 "Dynamic Profile name";
             }
           }
           container line-identity-information {
             leaf dynamic-profile {
               type string;
               description
                 "Dynamic Profile name";
             }
             leaf circuit-id {
               type string;
               description
                 "Aci vlan attribute";
             }
             leaf remote-id {
               type string;
               description
                 "Aci vlan attribute";
             }
             leaf accept-no-ids {
               type string;
               description
                 "Aci vlan attribute";
             }
           }
           container demux-information {
             description
               "Demux information";
             container demux-interface {
               leaf demux-underlying-interface-name {
                 type string;
                 description
                   "Underlying interface name";
               }
               leaf demux-underlying-interface-index {
                 type string;
                 description
                   "Underlying interface index";
               }
               leaf demux-inet-prefix-type {
                 type string;
                 description
                   "Prefix type";
               }
               leaf demux-inet-prefix-count {
                 type string;
                 description
                   "IPv4 Prefix count";
               }
               leaf demux-inet-prefix {
                 type string;
                 description
                   "IPv4 Prefix";
               }
               leaf demux-inet6-prefix-type {
                 type string;
                 description
                   "Prefix type";
               }
               leaf demux-inet6-prefix-count {
                 type string;
                 description
                   "IPv6 Prefix count";
               }
               leaf demux-inet6-prefix {
                 type string;
                 description
                   "IPv6 Prefix";
               }
             }
           }
           container dual-ad-icl-color-information {
             container dual-ad-icl-color-info {
               description
                 "Dual-AD ICL Color Information";
               leaf dual-ad-icl-color-type {
                 type uint32;
                 description
                   "Dual-AD ICL Color Type";
               }
               leaf dual-ad-icl-color {
                 type uint32;
                 description
                   "Dual-AD ICL Color";
               }
             }
           }
           container dialer-information {
             description
               "Dialer information";
             leaf dialer-time-to-disconnect {
               type string;
               description
                 "Time for dialer to disconnect due to idle timeout";
             }
             container dialer-interface {
               leaf dialer-interface-name {
                 type string;
                 description
                   "Interface name";
               }
               leaf dialer-interface-state {
                 type string;
                 description
                   "Dialer interface state";
               }
               leaf pool-id {
                 type string;
                 description
                   "Pool identifier";
               }
               leaf primary-interface {
                 type string;
                 description
                   "Primary interface";
               }
               leaf activation-delay {
                 type string;
                 description
                   "Activation delay";
               }
               leaf deactivation-delay {
                 type string;
                 description
                   "Deactivation delay";
               }
               leaf activation-delay-elapsed {
                 type string;
                 description
                   "Activation delay elapsed";
               }
               leaf deactivation-delay-elapsed {
                 type string;
                 description
                   "Deactivation delay elapsed";
               }
               leaf call-idle-timeout {
                 type string;
                 description
                   "Call idle timeout";
               }
               leaf initial-route-check {
                 type string;
                 description
                   "Initial route check delay";
               }
               leaf redial-delay {
                 type string;
                 description
                   "Delay before dialer dials out again (seconds)";
               }
               leaf callback-wait-period {
                 type string;
                 description
                   "Delay before dialer attempts callback (seconds)";
               }
               leaf callback-wait-period-elapsed {
                 type string;
                 description
                   "Number of seconds in callback wait period that have 
                   elapsed";
               }
               leaf load-threshold {
                 type string;
                 description
                   "Load threshold that determines when interfaces are added
                   to bundle";
               }
               leaf load-interval {
                 type string;
                 description
                   "Interval over which average load is calculated";
               }
               container dialer-interface-flags {
                 description
                   "Flags indicating interface configuration";
                 leaf backup {
                   type empty;
                   description
                     "Dialer backup";
                 }
                 leaf multilink {
                   type empty;
                   description
                     "Dialer multilink";
                 }
                 leaf watchlist {
                   type empty;
                   description
                     "Dialer watchlist";
                 }
                 leaf interesting-detected {
                   type empty;
                   description
                     "Interesting packet detected";
                 }
               }
             }
           }
           container shared-interface-information {
             description
               "Shared interface information";
             container shared-interface-logical-interface {
               description
                 "Shared interface logical interface";
               leaf peer-interface-name {
                 type string;
                 description
                   "Peer interface name";
               }
               leaf interface-shared-with {
                 type string;
                 description
                   "Logical interface owner";
               }
               leaf rx-fe {
                 type string;
                 description
                   "Rx tunnel token forwarding element";
               }
               leaf rx-nhid {
                 type string;
                 description
                   "Rx tunnel token next hop index";
               }
               leaf tx-fe {
                 type string;
                 description
                   "Tx tunnel token forwarding element";
               }
               leaf tx-nhid {
                 type string;
                 description
                   "Tx tunnel token next hop index";
               }
             }
           }
           container mac-database {
             leaf number-of-mac-record {
               type int32;
             }
             list mac-record {
               leaf mac-address {
                 type jt:mac-addr;
               }
               leaf receive-frames {
                 type int32;
               }
               leaf receive-bytes {
                 type int32;
               }
               leaf transmit-frames {
                 type int32;
               }
               leaf transmit-bytes {
                 type int32;
               }
             }
           }
           container policer-overhead {
             description
               "Policer overhead information";
             leaf ingress-policer-overhead {
               type int32;
               description
                 "Ingress policer overhead information";
             }
             leaf egress-policer-overhead {
               type int32;
               description
                 "Egress policer overhead information";
             }
           }
           container queue-counters {
             description
               "Queue counter statistics";
             leaf queue-counters-error-message {
               type string;
               description
                 "Queue statistics not available for this interface";
             }
             list queue {
               description
                 "Counters for a single queue";
               leaf queue-number {
                 type int32;
                 description
                   "Queue number";
               }
               leaf queue-counters-queued-packets {
                 type uint64;
                 description
                   "Queued packet count";
               }
               leaf queue-counters-trans-packets {
                 type uint64;
                 description
                   "Total number of transmitted packets";
               }
               leaf queue-counters-total-drop-packets {
                 type uint64;
                 description
                   "Number of total packets dropped at the queue";
               }
               leaf forwarding-class-name {
                 type string;
                 description
                   "Forwarding class name associated with queue";
               }
               leaf queue-counters-queued-packets-rate {
                 type uint64;
                 description
                   "Rate at which packets are queued";
               }
               leaf queue-counters-queued-bytes {
                 type uint64;
                 description
                   "Queued bytes count";
               }
               leaf queue-counters-queued-bytes-rate {
                 type uint64;
                 description
                   "Rate at which bytes are queued";
               }
               leaf queue-counters-queued-packets-na {
                 type string;
                 description
                   "Queued packets not available";
               }
               leaf queue-counters-queued-bytes-na {
                 type string;
                 description
                   "Queued bytes not available";
               }
               leaf queue-counters-trans-packets-rate {
                 type uint64;
                 description
                   "Rate at which packets are transmitted";
               }
               leaf queue-counters-trans-bytes {
                 type uint64;
                 description
                   "Total number of transmitted bytes";
               }
               leaf queue-counters-trans-bytes-rate {
                 type uint64;
                 description
                   "Rate at which bytes are transmitted";
               }
               leaf queue-counters-tail-drop-packets-na {
                 type string;
                 description
                   "Number of packets dropped due to tail drop not available";
               }
               leaf queue-counters-tail-drop-packets {
                 type uint64;
                 description
                   "Number of packets dropped at the tail of the queue";
               }
               leaf queue-counters-tail-drop-packets-rate {
                 type uint64;
                 description
                   "Rate at which packets are dropped at tail of queue";
               }
               leaf queue-counters-tail-drop-bytes {
                 type uint64;
                 description
                   "Number of packets dropped at tail drop of the queue";
               }
               leaf queue-counters-tail-drop-bytes-rate {
                 type uint64;
                 description
                   "Number of packets dropped at tail drop of the queue";
               }
               leaf queue-counters-rate-limit-drop-packets-na {
                 type string;
                 description
                   "Number of packets dropped due to rate-limit drop not 
                   available";
               }
               leaf queue-counters-rate-limit-drop-packets {
                 type uint64;
                 description
                   "Number of packets dropped by rate-limit for the queue";
               }
               leaf queue-counters-rate-limit-drop-packets-rate {
                 type uint64;
                 description
                   "Rate at which packets are dropped by rate-limit for the 
                   queue";
               }
               leaf queue-counters-rate-limit-drop-bytes-na {
                 type string;
                 description
                   "Number of bytes dropped due to tail drop not available";
               }
               leaf queue-counters-rate-limit-drop-bytes {
                 type uint64;
                 description
                   "Number of bytes dropped at the tail of the queue";
               }
               leaf queue-counters-rate-limit-drop-bytes-rate {
                 type uint64;
                 description
                   "Rate at which bytes are dropped at the tail of the queue";
               }
               leaf queue-counters-red-packets-na {
                 type string;
                 description
                   "Number of packets dropped due to RED not available";
               }
               leaf queue-counters-red-packets {
                 type uint64;
                 description
                   "Number of packets dropped due to RED";
               }
               leaf queue-counters-red-packets-rate {
                 type uint64;
                 description
                   "Rate at which packets are dropped due to RED";
               }
               leaf queue-counters-red-packets-ln {
                 type uint64;
                 description
                   "Number of RED dropped low-loss, non-TCP packets";
               }
               leaf queue-counters-red-packets-rate-ln {
                 type uint64;
                 description
                   "RED drop rate for low-loss, non-TCP packets";
               }
               leaf queue-counters-red-packets-lt {
                 type uint64;
                 description
                   "Number of RED dropped of low-loss, TCP packets";
               }
               leaf queue-counters-red-packets-rate-lt {
                 type uint64;
                 description
                   "RED drop rate for low-loss, TCP packets";
               }
               leaf queue-counters-red-packets-hn {
                 type uint64;
                 description
                   "Number of RED dropped high-loss, non-TCP packets";
               }
               leaf queue-counters-red-packets-rate-hn {
                 type uint64;
                 description
                   "RED drop rate for high-loss, non-TCP packets";
               }
               leaf queue-counters-red-packets-ht {
                 type uint64;
                 description
                   "Number of RED dropped high-loss, TCP packets";
               }
               leaf queue-counters-red-packets-rate-ht {
                 type uint64;
                 description
                   "RED drop rate for high-loss, TCP packets";
               }
               leaf queue-counters-red-packets-low {
                 type uint64;
                 description
                   "Number of RED dropped low-loss packets";
               }
               leaf queue-counters-red-packets-rate-low {
                 type uint64;
                 description
                   "RED drop rate for low-loss packets";
               }
               leaf queue-counters-red-packets-medium-low {
                 type uint64;
                 description
                   "Number of RED dropped medium-low-loss packets";
               }
               leaf queue-counters-red-packets-rate-medium-low {
                 type uint64;
                 description
                   "RED drop rate for medium-low-loss packets";
               }
               leaf queue-counters-red-packets-medium-high {
                 type uint64;
                 description
                   "Number of RED dropped medium-high-loss packets";
               }
               leaf queue-counters-red-packets-rate-medium-high {
                 type uint64;
                 description
                   "RED drop rate for medium-high-loss packets";
               }
               leaf queue-counters-red-packets-medium {
                 type uint64;
                 description
                   "Number of RED dropped medium-loss packets";
               }
               leaf queue-counters-red-packets-rate-medium {
                 type uint64;
                 description
                   "RED drop rate for medium-loss packets";
               }
               leaf queue-counters-red-packets-high {
                 type uint64;
                 description
                   "Number of RED dropped high-loss packets";
               }
               leaf queue-counters-red-packets-rate-high {
                 type uint64;
                 description
                   "RED drop rate for high-loss packets";
               }
               leaf queue-counters-red-bytes-na {
                 type string;
                 description
                   "Number of bytes dropped due to RED not available";
               }
               leaf queue-counters-red-bytes {
                 type uint64;
                 description
                   "Number of bytes dropped due to RED";
               }
               leaf queue-counters-red-bytes-rate {
                 type uint64;
                 description
                   "Rate at which bytes are dropped due to RED";
               }
               leaf queue-counters-red-bytes-ln {
                 type uint64;
                 description
                   "Number of RED dropped low-loss, non-TCP bytes";
               }
               leaf queue-counters-red-bytes-rate-ln {
                 type uint64;
                 description
                   "RED drop rate for low-loss, non-TCP bytes";
               }
               leaf queue-counters-red-bytes-lt {
                 type uint64;
                 description
                   "Number of RED dropped low-loss, TCP bytes";
               }
               leaf queue-counters-red-bytes-rate-lt {
                 type uint64;
                 description
                   "RED drop rate for low-loss, TCP bytes";
               }
               leaf queue-counters-red-bytes-hn {
                 type uint64;
                 description
                   "Number of RED dropped high-loss, non-TCP bytes";
               }
               leaf queue-counters-red-bytes-rate-hn {
                 type uint64;
                 description
                   "RED drop rate for high-loss, non-TCP bytes";
               }
               leaf queue-counters-red-bytes-ht {
                 type uint64;
                 description
                   "Number of RED dropped high-loss, TCP bytes";
               }
               leaf queue-counters-red-bytes-rate-ht {
                 type uint64;
                 description
                   "RED drop rate for high-loss, TCP bytes";
               }
               leaf queue-counters-red-bytes-low {
                 type uint64;
                 description
                   "Number of RED dropped low-loss bytes";
               }
               leaf queue-counters-red-bytes-rate-low {
                 type uint64;
                 description
                   "RED drop rate for low-loss bytes";
               }
               leaf queue-counters-red-bytes-medium-low {
                 type uint64;
                 description
                   "Number of RED dropped medium-low-loss bytes";
               }
               leaf queue-counters-red-bytes-rate-medium-low {
                 type uint64;
                 description
                   "RED drop rate for medium-low-loss bytes";
               }
               leaf queue-counters-red-bytes-medium-high {
                 type uint64;
                 description
                   "Number of RED dropped medium-high-loss bytes";
               }
               leaf queue-counters-red-bytes-rate-medium-high {
                 type uint64;
                 description
                   "RED drop rate for medium-high-loss bytes";
               }
               leaf queue-counters-red-bytes-medium {
                 type uint64;
                 description
                   "Number of RED dropped medium-loss bytes";
               }
               leaf queue-counters-red-bytes-rate-medium {
                 type uint64;
                 description
                   "RED drop rate for medium-loss bytes";
               }
               leaf queue-counters-red-bytes-high {
                 type uint64;
                 description
                   "Number of RED dropped high-loss bytes";
               }
               leaf queue-counters-red-bytes-rate-high {
                 type uint64;
                 description
                   "RED drop rate for high-loss bytes";
               }
               leaf queue-counters-timestamp {
                 type uint64;
                 description
                   "Last packet enqueued timestamp";
               }
               leaf queue-counters-total-drop-packets-rate {
                 type uint64;
                 description
                   "Number of total packets dropped at the queue";
               }
               leaf queue-counters-total-drop-bytes {
                 type uint64;
                 description
                   "Number of total packets dropped at the queue";
               }
               leaf queue-counters-total-drop-bytes-rate {
                 type uint64;
                 description
                   "Number of total packets dropped at the queue";
               }
               leaf queue-counters-reserved-buffer-packets {
                 type int32;
                 description
                   "Queues's usage of reserved buffer pool in pkts";
               }
               leaf queue-counters-reserved-buffer-bytes {
                 type int32;
                 description
                   "Queues's usage of reserved buffer pool in bytes";
               }
               leaf queue-counters-shared-buffer-packets {
                 type int32;
                 description
                   "Queues's usage of shared buffer pool in pkts";
               }
               leaf queue-counters-shared-buffer-bytes {
                 type int32;
                 description
                   "Queues's usage of shared buffer pool in bytes";
               }
               leaf queue-counters-depth-average {
                 type int32;
                 description
                   "Time averaged queue depth";
               }
               leaf queue-counters-depth-current {
                 type int32;
                 description
                   "Current instantaneous queue depth";
               }
               leaf queue-counters-depth-peak {
                 type int32;
                 description
                   "Peak queue depth";
               }
               leaf queue-counters-depth-max {
                 type int32;
                 description
                   "Maximum queue depth attained";
               }
               leaf queue-counters-srx-reserved-buffer-bytes {
                 type int32;
                 description
                   "Queues's usage of reserved buffer pool in bytes";
               }
               leaf queue-counters-srx-depth-current {
                 type int32;
                 description
                   "Current instantaneous queue depth";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
             container interface-cos-short-summary {
               description
                 "Summary of queue information on an interface";
               leaf intf-cos-queue-type {
                 type string;
                 description
                   "Interface queue type";
               }
               leaf intf-cos-num-queues-supported {
                 type int32;
                 description
                   "Number of queues supported on this interface";
               }
               leaf intf-cos-num-queues-in-use {
                 type int32;
                 description
                   "Number of queues currently in use on this interface";
               }
               leaf intf-cos-queue-dedicated-or-shared {
                 type string;
                 description
                   "Interface has dedicated or shared queues";
               }
               leaf intf-cos-sched-resource-type {
                 type string;
                 description
                   "Interface scheduling resource type";
               }
               leaf intf-cos-sched-resource-usage-mic-limit {
                 type int32;
                 description
                   "MIC/PIC scheduling resource usage limit";
               }
               leaf intf-cos-sched-resource-usage-mic-count {
                 type int32;
                 description
                   "MIC/PIC scheduling resource usage count";
               }
               leaf intf-cos-sched-resource-usage-port-limit {
                 type int32;
                 description
                   "Interface scheduling resource limit";
               }
               leaf intf-cos-sched-resource-usage-port-count {
                 type int32;
                 description
                   "Interface scheduling resource usage";
               }
             }
             container interface-cos-summary {
               description
                 "Summary of forwarding class and queue information on an 
                 interface";
               leaf intf-cos-forwarding-classes-supported {
                 type int32;
                 description
                   "Number of forwarding classes supported on this interface";
               }
               leaf intf-cos-forwarding-classes-in-use {
                 type int32;
                 description
                   "Number of forwarding classes currently in use on this 
                   interface";
               }
               leaf intf-cos-queue-type {
                 type string;
                 description
                   "Interface queue type";
               }
               leaf intf-cos-num-queues-supported {
                 type int32;
                 description
                   "Number of queues supported on this interface";
               }
               leaf intf-cos-num-queues-in-use {
                 type int32;
                 description
                   "Number of queues currently in use on this interface";
               }
               leaf intf-cos-queue-dedicated-or-shared {
                 type string;
                 description
                   "Interface has dedicated or shared queues";
               }
               leaf intf-cos-sched-resource-type {
                 type string;
                 description
                   "Interface scheduling resource type";
               }
               leaf intf-cos-sched-resource-usage-mic-limit {
                 type int32;
                 description
                   "MIC/PIC scheduling resource usage limit";
               }
               leaf intf-cos-sched-resource-usage-mic-count {
                 type int32;
                 description
                   "MIC/PIC scheduling resource usage count";
               }
               leaf intf-cos-sched-resource-usage-port-limit {
                 type int32;
                 description
                   "Interface scheduling resource limit";
               }
               leaf intf-cos-sched-resource-usage-port-count {
                 type int32;
                 description
                   "Interface scheduling resource usage";
               }
               leaf intf-cos-burst-size-for-ifl {
                 type int32;
                 description
                   "Burst size for the logical interface";
               }
             }
           }
           container ingress-queue-counters {
             description
               "Ingress queue counter statistics";
             list queue {
               description
                 "Counters for a single queue";
               leaf queue-number {
                 type int32;
                 description
                   "Queue number";
               }
               leaf forwarding-class-name {
                 type string;
                 description
                   "Forwarding class name associated with queue";
               }
               leaf queue-counters-queued-packets {
                 type uint64;
                 description
                   "Queued packet count";
               }
               leaf queue-counters-queued-packets-rate {
                 type uint64;
                 description
                   "Rate at which packets are queued";
               }
               leaf queue-counters-queued-bytes {
                 type uint64;
                 description
                   "Queued bytes count";
               }
               leaf queue-counters-queued-bytes-rate {
                 type uint64;
                 description
                   "Rate at which bytes are queued";
               }
               leaf queue-counters-queued-packets-na {
                 type string;
                 description
                   "Queued packets not available";
               }
               leaf queue-counters-queued-bytes-na {
                 type string;
                 description
                   "Queued bytes not available";
               }
               leaf queue-counters-trans-packets {
                 type uint64;
                 description
                   "Total number of transmitted packets";
               }
               leaf queue-counters-trans-packets-rate {
                 type uint64;
                 description
                   "Rate at which packets are transmitted";
               }
               leaf queue-counters-trans-bytes {
                 type uint64;
                 description
                   "Total number of transmitted bytes";
               }
               leaf queue-counters-trans-bytes-rate {
                 type uint64;
                 description
                   "Rate at which bytes are transmitted";
               }
               leaf queue-counters-tail-drop-packets-na {
                 type string;
                 description
                   "Number of packets dropped due to tail drop not available";
               }
               leaf queue-counters-tail-drop-packets {
                 type uint64;
                 description
                   "Number of packets dropped at the tail of the queue";
               }
               leaf queue-counters-tail-drop-packets-rate {
                 type uint64;
                 description
                   "Rate at which packets are dropped at tail of queue";
               }
               leaf queue-counters-tail-drop-bytes {
                 type uint64;
                 description
                   "Number of packets dropped at tail drop of the queue";
               }
               leaf queue-counters-tail-drop-bytes-rate {
                 type uint64;
                 description
                   "Number of packets dropped at tail drop of the queue";
               }
               leaf queue-counters-rate-limit-drop-packets-na {
                 type string;
                 description
                   "Number of packets dropped due to rate-limit drop not 
                   available";
               }
               leaf queue-counters-rate-limit-drop-packets {
                 type uint64;
                 description
                   "Number of packets dropped by rate-limit for the queue";
               }
               leaf queue-counters-rate-limit-drop-packets-rate {
                 type uint64;
                 description
                   "Rate at which packets are dropped by rate-limit for the 
                   queue";
               }
               leaf queue-counters-rate-limit-drop-bytes-na {
                 type string;
                 description
                   "Number of bytes dropped due to tail drop not available";
               }
               leaf queue-counters-rate-limit-drop-bytes {
                 type uint64;
                 description
                   "Number of bytes dropped at the tail of the queue";
               }
               leaf queue-counters-rate-limit-drop-bytes-rate {
                 type uint64;
                 description
                   "Rate at which bytes are dropped at the tail of the queue";
               }
               leaf queue-counters-red-packets-na {
                 type string;
                 description
                   "Number of packets dropped due to RED not available";
               }
               leaf queue-counters-red-packets {
                 type uint64;
                 description
                   "Number of packets dropped due to RED";
               }
               leaf queue-counters-red-packets-rate {
                 type uint64;
                 description
                   "Rate at which packets are dropped due to RED";
               }
               leaf queue-counters-red-packets-ln {
                 type uint64;
                 description
                   "Number of RED dropped low-loss, non-TCP packets";
               }
               leaf queue-counters-red-packets-rate-ln {
                 type uint64;
                 description
                   "RED drop rate for low-loss, non-TCP packets";
               }
               leaf queue-counters-red-packets-lt {
                 type uint64;
                 description
                   "Number of RED dropped of low-loss, TCP packets";
               }
               leaf queue-counters-red-packets-rate-lt {
                 type uint64;
                 description
                   "RED drop rate for low-loss, TCP packets";
               }
               leaf queue-counters-red-packets-hn {
                 type uint64;
                 description
                   "Number of RED dropped high-loss, non-TCP packets";
               }
               leaf queue-counters-red-packets-rate-hn {
                 type uint64;
                 description
                   "RED drop rate for high-loss, non-TCP packets";
               }
               leaf queue-counters-red-packets-ht {
                 type uint64;
                 description
                   "Number of RED dropped high-loss, TCP packets";
               }
               leaf queue-counters-red-packets-rate-ht {
                 type uint64;
                 description
                   "RED drop rate for high-loss, TCP packets";
               }
               leaf queue-counters-red-packets-low {
                 type uint64;
                 description
                   "Number of RED dropped low-loss packets";
               }
               leaf queue-counters-red-packets-rate-low {
                 type uint64;
                 description
                   "RED drop rate for low-loss packets";
               }
               leaf queue-counters-red-packets-medium-low {
                 type uint64;
                 description
                   "Number of RED dropped medium-low-loss packets";
               }
               leaf queue-counters-red-packets-rate-medium-low {
                 type uint64;
                 description
                   "RED drop rate for medium-low-loss packets";
               }
               leaf queue-counters-red-packets-medium-high {
                 type uint64;
                 description
                   "Number of RED dropped medium-high-loss packets";
               }
               leaf queue-counters-red-packets-rate-medium-high {
                 type uint64;
                 description
                   "RED drop rate for medium-high-loss packets";
               }
               leaf queue-counters-red-packets-medium {
                 type uint64;
                 description
                   "Number of RED dropped medium-loss packets";
               }
               leaf queue-counters-red-packets-rate-medium {
                 type uint64;
                 description
                   "RED drop rate for medium-loss packets";
               }
               leaf queue-counters-red-packets-high {
                 type uint64;
                 description
                   "Number of RED dropped high-loss packets";
               }
               leaf queue-counters-red-packets-rate-high {
                 type uint64;
                 description
                   "RED drop rate for high-loss packets";
               }
               leaf queue-counters-red-bytes-na {
                 type string;
                 description
                   "Number of bytes dropped due to RED not available";
               }
               leaf queue-counters-red-bytes {
                 type uint64;
                 description
                   "Number of bytes dropped due to RED";
               }
               leaf queue-counters-red-bytes-rate {
                 type uint64;
                 description
                   "Rate at which bytes are dropped due to RED";
               }
               leaf queue-counters-red-bytes-ln {
                 type uint64;
                 description
                   "Number of RED dropped low-loss, non-TCP bytes";
               }
               leaf queue-counters-red-bytes-rate-ln {
                 type uint64;
                 description
                   "RED drop rate for low-loss, non-TCP bytes";
               }
               leaf queue-counters-red-bytes-lt {
                 type uint64;
                 description
                   "Number of RED dropped low-loss, TCP bytes";
               }
               leaf queue-counters-red-bytes-rate-lt {
                 type uint64;
                 description
                   "RED drop rate for low-loss, TCP bytes";
               }
               leaf queue-counters-red-bytes-hn {
                 type uint64;
                 description
                   "Number of RED dropped high-loss, non-TCP bytes";
               }
               leaf queue-counters-red-bytes-rate-hn {
                 type uint64;
                 description
                   "RED drop rate for high-loss, non-TCP bytes";
               }
               leaf queue-counters-red-bytes-ht {
                 type uint64;
                 description
                   "Number of RED dropped high-loss, TCP bytes";
               }
               leaf queue-counters-red-bytes-rate-ht {
                 type uint64;
                 description
                   "RED drop rate for high-loss, TCP bytes";
               }
               leaf queue-counters-red-bytes-low {
                 type uint64;
                 description
                   "Number of RED dropped low-loss bytes";
               }
               leaf queue-counters-red-bytes-rate-low {
                 type uint64;
                 description
                   "RED drop rate for low-loss bytes";
               }
               leaf queue-counters-red-bytes-medium-low {
                 type uint64;
                 description
                   "Number of RED dropped medium-low-loss bytes";
               }
               leaf queue-counters-red-bytes-rate-medium-low {
                 type uint64;
                 description
                   "RED drop rate for medium-low-loss bytes";
               }
               leaf queue-counters-red-bytes-medium-high {
                 type uint64;
                 description
                   "Number of RED dropped medium-high-loss bytes";
               }
               leaf queue-counters-red-bytes-rate-medium-high {
                 type uint64;
                 description
                   "RED drop rate for medium-high-loss bytes";
               }
               leaf queue-counters-red-bytes-medium {
                 type uint64;
                 description
                   "Number of RED dropped medium-loss bytes";
               }
               leaf queue-counters-red-bytes-rate-medium {
                 type uint64;
                 description
                   "RED drop rate for medium-loss bytes";
               }
               leaf queue-counters-red-bytes-high {
                 type uint64;
                 description
                   "Number of RED dropped high-loss bytes";
               }
               leaf queue-counters-red-bytes-rate-high {
                 type uint64;
                 description
                   "RED drop rate for high-loss bytes";
               }
               leaf queue-counters-timestamp {
                 type uint64;
                 description
                   "Last packet enqueued timestamp";
               }
               leaf queue-counters-total-drop-packets {
                 type uint64;
                 description
                   "Number of total packets dropped at the queue";
               }
               leaf queue-counters-total-drop-packets-rate {
                 type uint64;
                 description
                   "Number of total packets dropped at the queue";
               }
               leaf queue-counters-total-drop-bytes {
                 type uint64;
                 description
                   "Number of total packets dropped at the queue";
               }
               leaf queue-counters-total-drop-bytes-rate {
                 type uint64;
                 description
                   "Number of total packets dropped at the queue";
               }
               leaf queue-counters-reserved-buffer-packets {
                 type int32;
                 description
                   "Queues's usage of reserved buffer pool in pkts";
               }
               leaf queue-counters-reserved-buffer-bytes {
                 type int32;
                 description
                   "Queues's usage of reserved buffer pool in bytes";
               }
               leaf queue-counters-shared-buffer-packets {
                 type int32;
                 description
                   "Queues's usage of shared buffer pool in pkts";
               }
               leaf queue-counters-shared-buffer-bytes {
                 type int32;
                 description
                   "Queues's usage of shared buffer pool in bytes";
               }
               leaf queue-counters-depth-average {
                 type int32;
                 description
                   "Time averaged queue depth";
               }
               leaf queue-counters-depth-current {
                 type int32;
                 description
                   "Current instantaneous queue depth";
               }
               leaf queue-counters-depth-peak {
                 type int32;
                 description
                   "Peak queue depth";
               }
               leaf queue-counters-depth-max {
                 type int32;
                 description
                   "Maximum queue depth attained";
               }
               leaf queue-counters-srx-reserved-buffer-bytes {
                 type int32;
                 description
                   "Queues's usage of reserved buffer pool in bytes";
               }
               leaf queue-counters-srx-depth-current {
                 type int32;
                 description
                   "Current instantaneous queue depth";
               }
             }
             container interface-cos-summary {
               description
                 "Summary of forwarding class and queue information on an 
                 interface";
               leaf intf-cos-forwarding-classes-supported {
                 type int32;
                 description
                   "Number of forwarding classes supported on this interface";
               }
               leaf intf-cos-forwarding-classes-in-use {
                 type int32;
                 description
                   "Number of forwarding classes currently in use on this 
                   interface";
               }
               leaf intf-cos-queue-type {
                 type string;
                 description
                   "Interface queue type";
               }
               leaf intf-cos-num-queues-supported {
                 type int32;
                 description
                   "Number of queues supported on this interface";
               }
               leaf intf-cos-num-queues-in-use {
                 type int32;
                 description
                   "Number of queues currently in use on this interface";
               }
               leaf intf-cos-queue-dedicated-or-shared {
                 type string;
                 description
                   "Interface has dedicated or shared queues";
               }
               leaf intf-cos-sched-resource-type {
                 type string;
                 description
                   "Interface scheduling resource type";
               }
               leaf intf-cos-sched-resource-usage-mic-limit {
                 type int32;
                 description
                   "MIC/PIC scheduling resource usage limit";
               }
               leaf intf-cos-sched-resource-usage-mic-count {
                 type int32;
                 description
                   "MIC/PIC scheduling resource usage count";
               }
               leaf intf-cos-sched-resource-usage-port-limit {
                 type int32;
                 description
                   "Interface scheduling resource limit";
               }
               leaf intf-cos-sched-resource-usage-port-count {
                 type int32;
                 description
                   "Interface scheduling resource usage";
               }
               leaf intf-cos-burst-size-for-ifl {
                 type int32;
                 description
                   "Burst size for the logical interface";
               }
             }
             container interface-cos-short-summary {
               description
                 "Summary of queue information on an interface";
               leaf intf-cos-queue-type {
                 type string;
                 description
                   "Interface queue type";
               }
               leaf intf-cos-num-queues-supported {
                 type int32;
                 description
                   "Number of queues supported on this interface";
               }
               leaf intf-cos-num-queues-in-use {
                 type int32;
                 description
                   "Number of queues currently in use on this interface";
               }
               leaf intf-cos-queue-dedicated-or-shared {
                 type string;
                 description
                   "Interface has dedicated or shared queues";
               }
               leaf intf-cos-sched-resource-type {
                 type string;
                 description
                   "Interface scheduling resource type";
               }
               leaf intf-cos-sched-resource-usage-mic-limit {
                 type int32;
                 description
                   "MIC/PIC scheduling resource usage limit";
               }
               leaf intf-cos-sched-resource-usage-mic-count {
                 type int32;
                 description
                   "MIC/PIC scheduling resource usage count";
               }
               leaf intf-cos-sched-resource-usage-port-limit {
                 type int32;
                 description
                   "Interface scheduling resource limit";
               }
               leaf intf-cos-sched-resource-usage-port-count {
                 type int32;
                 description
                   "Interface scheduling resource usage";
               }
             }
             container queue-num-forwarding-class-name-map {
               leaf queue-number {
                 type int32;
                 description
                   "Queue number";
               }
               leaf forwarding-class-name {
                 type string;
                 description
                   "Forwarding class name associated with queue";
               }
             }
           }
           container forwarding-class-counters {
             description
               "Forwarding-class counter statistics";
             leaf forwarding-class-counters-error-message {
               type string;
               description
                 "Forwarding-class statistics not available for this 
                 interface";
             }
             container forwarding-class-accounting-parameters {
               leaf forwarding-class-accounting-for-protocol {
                 type string;
               }
               leaf forwarding-class-accounting-for-traffic-direction {
                 type string;
               }
               leaf forwarding-class-accounting-for-traffic-type {
                 type string;
               }
               leaf forwarding-class-accounting-overhead-bytes {
                 type uint32;
               }
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
             container ipv4-forwarding-class-counters {
               leaf forwarding-class-stats-type {
                 type string;
               }
               container per-forwarding-class-counters {
                 leaf fc_name_header {
                   type string;
                 }
                 leaf forwarding-class-name {
                   type string;
                   description
                     "Forwarding class name associated with queue";
                 }
                 leaf fc-input-bytes {
                   type int32;
                 }
                 leaf fc-input-bytes-rate {
                   type int32;
                   description
                     "Input bytes rate";
                 }
                 leaf fc-output-bytes {
                   type int32;
                 }
                 leaf fc-output-bytes-rate {
                   type int32;
                   description
                     "Output bytes rate";
                 }
                 leaf fc-input-packets {
                   type int32;
                 }
                 leaf fc-input-packets-rate {
                   type int32;
                   description
                     "Input packets rate";
                 }
                 leaf fc-output-packets {
                   type int32;
                 }
                 leaf fc-output-packets-rate {
                   type int32;
                   description
                     "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container ipv6-forwarding-class-counters {
               leaf forwarding-class-stats-type {
                 type string;
               }
               container per-forwarding-class-counters {
                 leaf fc_name_header {
                   type string;
                 }
                 leaf forwarding-class-name {
                   type string;
                   description
                     "Forwarding class name associated with queue";
                 }
                 leaf fc-input-bytes {
                   type int32;
                 }
                 leaf fc-input-bytes-rate {
                   type int32;
                   description
                     "Input bytes rate";
                 }
                 leaf fc-output-bytes {
                   type int32;
                 }
                 leaf fc-output-bytes-rate {
                   type int32;
                   description
                     "Output bytes rate";
                 }
                 leaf fc-input-packets {
                   type int32;
                 }
                 leaf fc-input-packets-rate {
                   type int32;
                   description
                     "Input packets rate";
                 }
                 leaf fc-output-packets {
                   type int32;
                 }
                 leaf fc-output-packets-rate {
                   type int32;
                   description
                     "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container mpls-forwarding-class-counters {
               leaf forwarding-class-stats-type {
                 type string;
               }
               container per-forwarding-class-counters {
                 leaf fc_name_header {
                   type string;
                 }
                 leaf forwarding-class-name {
                   type string;
                   description
                     "Forwarding class name associated with queue";
                 }
                 leaf fc-input-bytes {
                   type int32;
                 }
                 leaf fc-input-bytes-rate {
                   type int32;
                   description
                     "Input bytes rate";
                 }
                 leaf fc-output-bytes {
                   type int32;
                 }
                 leaf fc-output-bytes-rate {
                   type int32;
                   description
                     "Output bytes rate";
                 }
                 leaf fc-input-packets {
                   type int32;
                 }
                 leaf fc-input-packets-rate {
                   type int32;
                   description
                     "Input packets rate";
                 }
                 leaf fc-output-packets {
                   type int32;
                 }
                 leaf fc-output-packets-rate {
                   type int32;
                   description
                     "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container layer2-forwarding-class-counters {
               leaf forwarding-class-stats-type {
                 type string;
               }
               container per-forwarding-class-counters {
                 leaf fc_name_header {
                   type string;
                 }
                 leaf forwarding-class-name {
                   type string;
                   description
                     "Forwarding class name associated with queue";
                 }
                 leaf fc-input-bytes {
                   type int32;
                 }
                 leaf fc-input-bytes-rate {
                   type int32;
                   description
                     "Input bytes rate";
                 }
                 leaf fc-output-bytes {
                   type int32;
                 }
                 leaf fc-output-bytes-rate {
                   type int32;
                   description
                     "Output bytes rate";
                 }
                 leaf fc-input-packets {
                   type int32;
                 }
                 leaf fc-input-packets-rate {
                   type int32;
                   description
                     "Input packets rate";
                 }
                 leaf fc-output-packets {
                   type int32;
                 }
                 leaf fc-output-packets-rate {
                   type int32;
                   description
                     "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container other-forwarding-class-counters {
               leaf forwarding-class-stats-type {
                 type string;
               }
               container per-forwarding-class-counters {
                 leaf fc_name_header {
                   type string;
                 }
                 leaf forwarding-class-name {
                   type string;
                   description
                     "Forwarding class name associated with queue";
                 }
                 leaf fc-input-bytes {
                   type int32;
                 }
                 leaf fc-input-bytes-rate {
                   type int32;
                   description
                     "Input bytes rate";
                 }
                 leaf fc-output-bytes {
                   type int32;
                 }
                 leaf fc-output-bytes-rate {
                   type int32;
                   description
                     "Output bytes rate";
                 }
                 leaf fc-input-packets {
                   type int32;
                 }
                 leaf fc-input-packets-rate {
                   type int32;
                   description
                     "Input packets rate";
                 }
                 leaf fc-output-packets {
                   type int32;
                 }
                 leaf fc-output-packets-rate {
                   type int32;
                   description
                     "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container protocol-aggregate-forwarding-class-counters {
               leaf forwarding-class-stats-type {
                 type string;
               }
               container per-forwarding-class-counters {
                 leaf fc_name_header {
                   type string;
                 }
                 leaf forwarding-class-name {
                   type string;
                   description
                     "Forwarding class name associated with queue";
                 }
                 leaf fc-input-bytes {
                   type int32;
                 }
                 leaf fc-input-bytes-rate {
                   type int32;
                   description
                     "Input bytes rate";
                 }
                 leaf fc-output-bytes {
                   type int32;
                 }
                 leaf fc-output-bytes-rate {
                   type int32;
                   description
                     "Output bytes rate";
                 }
                 leaf fc-input-packets {
                   type int32;
                 }
                 leaf fc-input-packets-rate {
                   type int32;
                   description
                     "Input packets rate";
                 }
                 leaf fc-output-packets {
                   type int32;
                 }
                 leaf fc-output-packets-rate {
                   type int32;
                   description
                     "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container forwarding-class-statistics {
               container protocol-aggregate-forwarding-class-counters {
               }
               container ipv4-forwarding-class-counters {
               }
               container ipv6-forwarding-class-counters {
               }
               container mpls-forwarding-class-counters {
               }
               container layer2-forwarding-class-counters {
               }
               container other-forwarding-class-counters {
               }
             }
           }
           container multilink-bundle-link-information {
             leaf multilink-active-bundle-links {
               type int32;
               description
                 "Number of active bundle links in this multilink bundle 
                 instance";
             }
             leaf multilink-removed-bundle-links {
               type int32;
               description
                 "Number of bundle links that are removed from service in 
                 this multilink bundle instance";
             }
             leaf multilink-disabled-bundle-links {
               type int32;
               description
                 "Number of bundle links that are not allowed to transmit in
                 this multilink bundle instance";
             }
           }
           container multilink-bundle-options {
             leaf mrru {
               type int32;
             }
             leaf remote-mrru {
               type int32;
               description
                 "Remote max received reconstructed unit";
             }
             leaf drop-timeout {
               type int32;
             }
             leaf mlppp-inner-ppp-pfc {
               type string;
               description
                 "MLPPP inner PPP protocol field compression";
             }
             leaf sequence-number-format {
               type string;
             }
             leaf ml-fragment-threshold {
               type int32;
             }
             leaf minimum-links {
               type int32;
             }
             leaf interleave-fragments {
               type string;
             }
             leaf multilink-classes {
               type int32;
               description
                 "Number of multilink classes";
             }
             leaf link-layer-overhead {
               type string;
               description
                 "Link layer overhead";
             }
             leaf filler-packet-interval {
               type int32;
             }
           }
           container multilink-bundle-errors {
             description
               "Multilink bundle errors";
             leaf packet-drops {
               type int32;
               description
                 "Number of packets dropped";
             }
             leaf packet-drop-bytes {
               type int32;
               description
                 "Number of bytes in dropped packets";
             }
             leaf fragment-drops {
               type int32;
               description
                 "Number of fragments dropped";
             }
             leaf fragment-drop-bytes {
               type int32;
               description
                 "Number of bytes in dropped fragments";
             }
             leaf mrru-exceeded {
               type int32;
               description
                 "Number of assembled packets that exceeded MRRU";
             }
             leaf processing-errors {
               type int32;
               description
                 "Number of errors encountered in assembling packets";
             }
           }
           container multilink-traffic-statistics {
             container bundle {
               container multilink-frames {
                 description
                   "Link-pic bound frame statistics for multilink bundles 
                   and classes";
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
               container network-frames {
                 description
                   "Internet/RE bound frame statistics for multilink bundles
                   and classes";
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
               container network-v6-frames {
                 description
                   "Transit IPV6 statistics for multilink bundles";
                 leaf inputv6-packets {
                   type int32;
                 }
                 leaf inputv6-bytes {
                   type int32;
                 }
                 leaf outputv6-packets {
                   type int32;
                 }
                 leaf outputv6-bytes {
                   type int32;
                 }
               }
             }
             container class {
               description
                 "Multilink class traffic statistics";
               container class-info {
                 description
                   "Multilink class information";
                 leaf multilink-class-id {
                   type int32;
                   description
                     "Multilink class ID";
                 }
               }
               container multilink-frames {
                 description
                   "Link-pic bound frame statistics for multilink bundles 
                   and classes";
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
               container network-frames {
                 description
                   "Internet/RE bound frame statistics for multilink bundles
                   and classes";
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
             }
             list link {
               key "name";
               leaf name {
                 type string;
                 description
                   "Name of this item";
               }
               leaf down {
                 type empty;
                 description
                   "Link is down";
               }
               leaf link-uptime {
                 type string;
                 description
                   "Total uptime for the member link";
               }
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
             container multilink-detail-statistics {
               container bundle-detail {
                 container fragments {
                   description
                     "Fragment statistics for multilink bundles and classes";
                   leaf input-frames {
                     type int32;
                   }
                   leaf input-fps {
                     type int32;
                   }
                   leaf input-bytes {
                     type int32;
                   }
                   leaf input-bps {
                     type int32;
                   }
                   leaf output-frames {
                     type int32;
                   }
                   leaf output-fps {
                     type int32;
                   }
                   leaf output-bytes {
                     type int32;
                   }
                   leaf output-bps {
                     type int32;
                   }
                 }
                 container non-fragments {
                   description
                     "Non-fragment statistics for multilink bundles and 
                     classes";
                   leaf input-frames {
                     type int32;
                   }
                   leaf input-fps {
                     type int32;
                   }
                   leaf input-bytes {
                     type int32;
                   }
                   leaf input-bps {
                     type int32;
                   }
                   leaf output-frames {
                     type int32;
                   }
                   leaf output-fps {
                     type int32;
                   }
                   leaf output-bytes {
                     type int32;
                   }
                   leaf output-bps {
                     type int32;
                   }
                 }
                 container lfi {
                   description
                     "LFI frame statistics for multilink bundles and classes";
                   leaf input-frames {
                     type int32;
                   }
                   leaf input-fps {
                     type int32;
                   }
                   leaf input-bytes {
                     type int32;
                   }
                   leaf input-bps {
                     type int32;
                   }
                   leaf output-frames {
                     type int32;
                   }
                   leaf output-fps {
                     type int32;
                   }
                   leaf output-bytes {
                     type int32;
                   }
                   leaf output-bps {
                     type int32;
                   }
                 }
               }
               container class-detail {
                 container class-info {
                   description
                     "Multilink class information";
                   leaf multilink-class-id {
                     type int32;
                     description
                       "Multilink class ID";
                   }
                 }
                 container fragments {
                   description
                     "Fragment statistics for multilink bundles and classes";
                   leaf input-frames {
                     type int32;
                   }
                   leaf input-fps {
                     type int32;
                   }
                   leaf input-bytes {
                     type int32;
                   }
                   leaf input-bps {
                     type int32;
                   }
                   leaf output-frames {
                     type int32;
                   }
                   leaf output-fps {
                     type int32;
                   }
                   leaf output-bytes {
                     type int32;
                   }
                   leaf output-bps {
                     type int32;
                   }
                 }
                 container non-fragments {
                   description
                     "Non-fragment statistics for multilink bundles and 
                     classes";
                   leaf input-frames {
                     type int32;
                   }
                   leaf input-fps {
                     type int32;
                   }
                   leaf input-bytes {
                     type int32;
                   }
                   leaf input-bps {
                     type int32;
                   }
                   leaf output-frames {
                     type int32;
                   }
                   leaf output-fps {
                     type int32;
                   }
                   leaf output-bytes {
                     type int32;
                   }
                   leaf output-bps {
                     type int32;
                   }
                 }
               }
             }
             container crtp {
               container crtp-sessions {
                 leaf input-frames {
                   type int32;
                 }
                 leaf output-frames {
                   type int32;
                 }
               }
               list crtp-statistics {
                 key "name";
                 leaf name {
                   type string;
                   description
                     "Name of this item";
                 }
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
             }
           }
           container statistics-account-overhead {
             description
               "Statistics account overhead information";
             leaf ingress-account-overhead {
               type int32;
               description
                 "Ingress Statistics account overhead information";
             }
             leaf egress-account-overhead {
               type int32;
               description
                 "Egress Statistics account overhead information";
             }
           }
           container traffic-statistics {
             leaf input-bps {
               type int32;
             }
             leaf input-pps {
               type int32;
             }
             leaf output-bps {
               type int32;
             }
             leaf output-pps {
               type int32;
             }
             leaf input-packets {
               type int32;
             }
             leaf output-packets {
               type int32;
             }
             leaf input-bytes {
               type int32;
             }
             leaf output-bytes {
               type int32;
             }
             container ipv6-transit-statistics {
               leaf input-bytes {
                 type int32;
               }
               leaf output-bytes {
                 type int32;
               }
               leaf input-packets {
                 type int32;
               }
               leaf output-packets {
                 type int32;
               }
             }
             container ipv6-total-statistics {
               leaf input-bytes {
                 type int32;
               }
               leaf output-bytes {
                 type int32;
               }
               leaf input-packets {
                 type int32;
               }
               leaf output-packets {
                 type int32;
               }
             }
           }
           container multicast-statistics {
             description
               "Multicast statistics for interface";
             leaf multicast-statistics-header {
               type empty;
             }
             container ipv4-multicast-statistics {
               description
                 "IPV4 multicast statistics for interface";
               leaf input-bytes {
                 type int32;
               }
               leaf input-bps {
                 type int32;
               }
               leaf output-bytes {
                 type int32;
               }
               leaf output-bps {
                 type int32;
               }
               leaf input-packets {
                 type int32;
               }
               leaf input-pps {
                 type int32;
               }
               leaf output-packets {
                 type int32;
               }
               leaf output-pps {
                 type int32;
               }
             }
             container ipv6-multicast-statistics {
               description
                 "IPV6 multicast statistics for interface";
               leaf input-bytes {
                 type int32;
               }
               leaf input-bps {
                 type int32;
               }
               leaf output-bytes {
                 type int32;
               }
               leaf output-bps {
                 type int32;
               }
               leaf input-packets {
                 type int32;
               }
               leaf input-pps {
                 type int32;
               }
               leaf output-packets {
                 type int32;
               }
               leaf output-pps {
                 type int32;
               }
             }
           }
           container ingress-traffic-statistics {
             description
               "Traffic statistics at ingress before entering Packet 
               Forwarding Engine";
             leaf input-bps {
               type int32;
             }
             leaf input-pps {
               type int32;
             }
             leaf input-drop-bps {
               type int32;
               description
                 "Drop rate at ingress in bits per second ";
             }
             leaf input-drop-pps {
               type int32;
               description
                 "Drop rate at ingress in packets per second ";
             }
             leaf input-bytes {
               type int32;
             }
             leaf input-packets {
               type int32;
             }
             leaf input-drop-bytes {
               type int32;
               description
                 "Drop statistics at ingress in bytes";
             }
             leaf input-drop-packets {
               type int32;
               description
                 "Drop statistics at ingress in packets";
             }
           }
           container local-traffic-statistics {
             description
               "Statistics for locally originated traffic";
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
           container transit-traffic-statistics {
             description
               "Statistics for traffic passing through the Packet Forwarding
               Engine";
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
             container ipv6-transit-statistics {
               leaf input-bytes {
                 type int32;
               }
               leaf input-bps {
                 type int32;
               }
               leaf output-bytes {
                 type int32;
               }
               leaf output-bps {
                 type int32;
               }
               leaf input-packets {
                 type int32;
               }
               leaf input-pps {
                 type int32;
               }
               leaf output-packets {
                 type int32;
               }
               leaf output-pps {
                 type int32;
               }
             }
             container ipv6-total-statistics {
               leaf input-bytes {
                 type int32;
               }
               leaf input-bps {
                 type int32;
               }
               leaf output-bytes {
                 type int32;
               }
               leaf output-bps {
                 type int32;
               }
               leaf input-packets {
                 type int32;
               }
               leaf input-pps {
                 type int32;
               }
               leaf output-packets {
                 type int32;
               }
               leaf output-pps {
                 type int32;
               }
             }
           }
           container keepalive-config {
             description
               "Configured keepalive settings on this interface";
             leaf keepalive-interval {
               type int32;
             }
             leaf keepalive-up-count {
               type int32;
             }
             leaf keepalive-down-count {
               type int32;
             }
           }
           container keepalive-statistics {
             description
               "Keepalive statistics for this interface";
             leaf keepalive-lmi-descriptor {
               type string;
             }
             leaf keepalive-input-count {
               type int32;
             }
             leaf keepalive-input-time {
               type string;
             }
             leaf keepalive-output-count {
               type int32;
             }
             leaf keepalive-output-time {
               type string;
             }
           }
           container ppp-flags {
             leaf iff-ppp-flags-acfc {
               type empty;
             }
             leaf iff-ppp-flags-pfc {
               type empty;
             }
           }
           list ncp-information {
             description
               "Network Control Protocol information";
             leaf ncp-protocol {
               type string;
               description
                 "Network protocol for this NCP instance";
             }
             leaf ncp-state {
               type string;
               description
                 "State of this NCP instance";
             }
           }
           container virtual-circuit-information {
             description
               "Operational information and statistics for a virtual circuit";
             leaf vpi {
               type int32;
               description
                 "Virtual path identifier";
             }
             leaf vci {
               type int32;
               description
                 "Virtual circuit identifier";
             }
             leaf psn-tag {
               type string;
               description
                 "VPI/VCI swapping configuration";
             }
             leaf psn-vpi {
               type int32;
               description
                 "PSN virtual path identifier";
             }
             leaf psn-vci {
               type int32;
               description
                 "PSN virtual circuit identifier";
             }
             leaf trunk {
               type int32;
               description
                 "ATM trunk identifier";
             }
             leaf dlci {
               type int32;
             }
             leaf swapping {
               type string;
               description
                 "VPI/VCI swapping configuration";
             }
             leaf trunk-bandwidth {
               type int32;
               description
                 "ATM trunk bandwidth";
             }
             leaf atm-tm-cbr {
               type empty;
               description
                 "Constant bit rate";
             }
             leaf atm-tm-vbr {
               type empty;
               description
                 "Variable bit rate";
             }
             leaf atm-tm-rtvbr {
               type empty;
               description
                 "Real-time variable bit rate";
             }
             leaf peak {
               type int32;
             }
             leaf sustained {
               type int32;
             }
             leaf burst {
               type int32;
             }
             leaf cdvt {
               type int32;
             }
             leaf queue-limit {
               type int32;
             }
             leaf down-time {
               type int32;
               description
                 "Total down time for this circuit";
             }
             leaf last-down-time {
               type int32;
               description
                 "Time elapsed since circuit last went down";
             }
             leaf ifvc-epd {
               type int32;
               description
                 "Early packet discard threshold";
             }
             leaf ifvc-weight {
               type int32;
               description
                 "Transmit weight";
             }
             leaf ifvc-epd-plp0 {
               type int32;
               description
                 "Early packet discard threshold for PLP 0";
             }
             leaf ifvc-epd-plp1 {
               type int32;
               description
                 "Early packet discard threshold for PLP 1";
             }
             container dlci-statistics {
               description
                 "DLCI statistics for an interface";
               leaf dlci-active {
                 type int32;
                 description
                   "Number of DLCIs in active state";
               }
               leaf dlci-inactive {
                 type int32;
                 description
                   "Number of DLCIs in inactive state";
               }
             }
             container vci-range {
               description
                 "ATM VCI range";
               leaf vpi {
                 type int32;
                 description
                   "Virtual path identifier";
               }
               leaf start-vci {
                 type int32;
                 description
                   "ATM VCI range's start value";
               }
               leaf end-vci {
                 type int32;
                 description
                   "ATM VCI range's end value";
               }
             }
             container ifvc-flags {
               leaf ifvc-down {
                 type empty;
               }
               leaf ifvc-none {
                 type empty;
               }
               leaf ifvc-active {
                 type empty;
               }
               leaf ifvc-closed {
                 type empty;
               }
               leaf ifvc-inverse-arp {
                 type empty;
               }
               leaf ifvc-ilmi {
                 type empty;
               }
               leaf ifvc-oam {
                 type empty;
               }
               leaf ifvc-shaping {
                 type empty;
               }
               leaf ifvc-passiveoam {
                 type empty;
               }
               leaf ifvc-multicast {
                 type empty;
               }
               leaf ifvc-ccc-down {
                 type empty;
               }
               leaf ifvc-configured {
                 type empty;
                 description
                   "DCE-end is configured";
               }
               leaf ifvc-unconfigured {
                 type empty;
                 description
                   "DCE-end is unconfigured";
               }
               leaf generic-value {
                 type int32;
                 description
                   "Hexadecimal value of unknown flag bits";
               }
             }
             container ifvc-multipoint-destination {
               leaf multipoint-address {
                 type string;
                 description
                   "Protocol address of the remote side of this connection";
               }
             }
             container oam-parameters {
               leaf period {
                 type int32;
               }
               leaf up-count {
                 type int32;
               }
               leaf down-count {
                 type int32;
               }
             }
             container oam-statistics {
               description
                 "Container tag for OAM statistics";
               leaf oam-total-received-count {
                 type int32;
               }
               leaf oam-total-transmitted-count {
                 type int32;
               }
               leaf oam-total-received-count-4 {
                 type int32;
               }
               leaf oam-total-transmitted-count-4 {
                 type int32;
               }
               leaf oam-loopback-received-count {
                 type int32;
               }
               leaf oam-loopback-transmitted-count {
                 type int32;
               }
               leaf oam-loopback-received-last {
                 type string;
               }
               leaf oam-loopback-transmitted-last {
                 type string;
               }
               leaf oam-rdi-received-count {
                 type int32;
               }
               leaf oam-rdi-transmitted-count {
                 type int32;
               }
               leaf oam-rdi-received-last {
                 type string;
               }
               leaf oam-rdi-transmitted-last {
                 type string;
               }
               leaf oam-ais-received-count {
                 type int32;
               }
               leaf oam-ais-transmitted-count {
                 type int32;
               }
               leaf oam-ais-received-last {
                 type string;
               }
               leaf oam-ais-transmitted-last {
                 type string;
               }
             }
             container traffic-statistics {
               leaf input-bps {
                 type int32;
               }
               leaf input-pps {
                 type int32;
               }
               leaf output-bps {
                 type int32;
               }
               leaf output-pps {
                 type int32;
               }
               leaf input-packets {
                 type int32;
               }
               leaf output-packets {
                 type int32;
               }
               leaf input-bytes {
                 type int32;
               }
               leaf output-bytes {
                 type int32;
               }
               container ipv6-transit-statistics {
                 leaf input-bytes {
                   type int32;
                 }
                 leaf output-bytes {
                   type int32;
                 }
                 leaf input-packets {
                   type int32;
                 }
                 leaf output-packets {
                   type int32;
                 }
               }
               container ipv6-total-statistics {
                 leaf input-bytes {
                   type int32;
                 }
                 leaf output-bytes {
                   type int32;
                 }
                 leaf input-packets {
                   type int32;
                 }
                 leaf output-packets {
                   type int32;
                 }
               }
             }
             container atm-policer-statistics {
               leaf non-conform-clp0-cells {
                 type int32;
                 description
                   "UPC non-conforming ATM CLP0 cell";
               }
               leaf non-conform-clp1-cells {
                 type int32;
                 description
                   "UPC non-conforming ATM CLP1 cell";
               }
               leaf tagged-cells {
                 type int32;
                 description
                   "UPC tagged cell";
               }
             }
             container atm-statistics {
               leaf vc-queue-drops {
                 type int32;
               }
             }
             container atm-cos-information {
               leaf vc-cos-mode {
                 type string;
                 description
                   "Virtual circuit CoS scheduling mode";
               }
               list atm-cos-queue {
                 container atm-cos-queue-parameters {
                   leaf cos-forwarding-class-name {
                     type string;
                     description
                       "Forwarding class name associated with queue";
                   }
                   leaf cos-queue-number {
                     type int32;
                     description
                       "Queue number";
                   }
                   leaf scheduling-priority {
                     type string;
                     description
                       "Scheduling priority";
                   }
                   leaf transmit-weight-cells {
                     type int32;
                     description
                       "Weight to apply to scheduling as number of cells";
                   }
                   leaf transmit-weight-percent {
                     type int32;
                     description
                       "Weight to apply to scheduling as fill percentage";
                   }
                   leaf epd-threshold {
                     type int32;
                     description
                       "Early packet drop threshold";
                   }
                   leaf epd-threshold-plp0 {
                     type int32;
                     description
                       "Early packet drop threshold for PLP 0";
                   }
                   leaf epd-threshold-plp1 {
                     type int32;
                     description
                       "Early packet drop threshold for PLP 1";
                   }
                   container linear-red-drop-profile {
                     leaf queue-depth {
                       type uint32;
                       description
                         "Instantaneous queue depth";
                     }
                     leaf low-red {
                       type int32;
                       description
                         "Fill level percentage when linear RED is applied 
                         for low PLP";
                     }
                     leaf high-red {
                       type int32;
                       description
                         "Fill level percentage when linear RED is applied 
                         for high PLP";
                     }
                     leaf max-low-red {
                       type int32;
                       description
                         "Fill level percentage with 100% packet drop for 
                         low PLP";
                     }
                     leaf max-high-red {
                       type int32;
                       description
                         "Fill level percentage with 100% packet drop for 
                         high PLP";
                     }
                   }
                 }
                 container atm-cos-queue-statistics {
                   leaf atm-output-bytes {
                     type int32;
                   }
                   leaf atm-output-packets {
                     type int32;
                   }
                   leaf atm-packet-drops {
                     type int32;
                   }
                 }
                 container atm-cos-plp-statistics {
                   leaf atm-plp0-output-bytes {
                     type int32;
                   }
                   leaf atm-plp1-output-bytes {
                     type int32;
                   }
                   leaf atm-plp0-output-packets {
                     type int32;
                   }
                   leaf atm-plp1-output-packets {
                     type int32;
                   }
                   leaf atm-plp0-byte-drops {
                     type int32;
                   }
                   leaf atm-plp1-byte-drops {
                     type int32;
                   }
                   leaf atm-plp0-packet-drops {
                     type int32;
                   }
                   leaf atm-plp1-packet-drops {
                     type int32;
                   }
                 }
               }
             }
             container in-arp-statistics {
               description
                 "Container tag for ARP statistics";
               leaf received-count {
                 type int32;
                 description
                   "Number of ARPs received";
               }
               leaf transmitted-count {
                 type int32;
                 description
                   "Number of ARPs sent";
               }
               leaf denied-count {
                 type int32;
                 description
                   "Number of ARPs denied";
               }
               leaf operation-not-supported-count {
                 type int32;
                 description
                   "Number of ARPs with operation not supported";
               }
               leaf bad-packet-length-count {
                 type int32;
                 description
                   "Number of ARPs with bad packet length";
               }
               leaf bad-protocol-count {
                 type int32;
                 description
                   "Number of ARPs with bad protocol";
               }
               leaf bad-protocol-length-count {
                 type int32;
                 description
                   "Number of ARPs with bad protocol length";
               }
               leaf bad-hardware-length-count {
                 type int32;
                 description
                   "Number of ARPs with bad hardware length";
               }
               leaf dropped-count {
                 type int32;
                 description
                   "Number of ARPs dropped";
               }
               leaf last-received {
                 type string;
                 description
                   "Time an ARP was last received";
               }
               leaf last-transmitted {
                 type string;
                 description
                   "Time an ARP was last sent";
               }
             }
           }
           list filter-information {
             leaf-list filter-input {
               type string;
               description
                 "Name of the input filter";
             }
             leaf-list filter-input-precedence {
               type uint32;
               description
                 "Precedence of the input filter";
             }
             leaf-list filter-output {
               type string;
               description
                 "Name of the output filter";
             }
             leaf-list filter-output-precedence {
               type uint32;
               description
                 "Precedence of the output filter";
             }
           }
           list address-family {
             key "address-family-name";
             leaf compression-device-name {
               type string;
               description
                 "Name of the link service device";
             }
             leaf address-family-name {
               type string;
             }
             leaf multilink-bundle-name {
               type string;
               description
                 "Name of the multilink bundle for this address family";
             }
             leaf as-bundle-name {
               type string;
               description
                 "Name of the aggregated SONET bundle for this address 
                 family";
             }
             leaf ae-bundle-name {
               type string;
               description
                 "Name of the aggregated Ethernet bundle";
             }
             leaf es-sa-name {
               type string;
               description
                 "Name of the IPSec security association for this address 
                 family";
             }
             leaf mtu {
               type string;
               description
                 "MTU size on this interface";
             }
             leaf maximum-labels {
               type uint32;
               description
                 "Maximum labels on MPLS iffamily";
             }
             leaf generation {
               type int32;
               description
                 "Generation number used to distinguish between successive 
                 instances of this interface";
             }
             leaf route-table {
               type int32;
             }
             leaf vpls-mesh-group {
               type string;
             }
             leaf es-sa-fail-count {
               type int32;
               description
                 "Number of failures for IPSec security association for this
                 family";
             }
             leaf es-sa-xmt-seq-num {
               type int32;
               description
                 "Transmit sequence number of IPSec security association 
                 family";
             }
             leaf es-sa-recv-seq-num {
               type int32;
               description
                 "Receive sequence number of IPSec security association 
                 family";
             }
             leaf evpn-multihomed-status {
               type string;
             }
             leaf evpn-mh-esi-sh-label {
               type string;
             }
             leaf iff-next-hop {
               type int32;
               description
                 "Interface family next-hop";
             }
             leaf iff-vpls-status {
               type string;
               description
                 "Interface family vpls status";
             }
             leaf max-local-cache {
               type uint32;
               description
                 "Max local nh cache size";
             }
             leaf new-hold-limit {
               type uint32;
               description
                 "Max limit on new unresolved nh";
             }
             leaf intf-curr-cnt {
               type uint32;
               description
                 "Current nh total cache size on this interface";
             }
             leaf intf-unresolved-cnt {
               type uint32;
               description
                 "Current new unresolved nh cache size on this interface";
             }
             leaf intf-dropcnt {
               type uint32;
               description
                 "Current interface nh drop count";
             }
             leaf mlppp-service-interface {
               type string;
               description
                 "Name of the multilink service interface for this address 
                 family";
             }
             leaf mlppp-service-dev-pool {
               type string;
               description
                 "Name of the multilink service device pool for this address
                 family";
             }
             leaf mlppp-dynamic-profile {
               type string;
               description
                 "Name of the multilink dynamic profile for this address 
                 family";
             }
             leaf arp-respond-any-local-address {
               type string;
               description
                 "Respond to ARP requests for any local address";
             }
             leaf local-bias-information {
               type string;
             }
             leaf ft-iff-dest-port {
               type uint32;
               description
                 "Destination UDP port to be used for this family";
             }
             container address-family-flags {
               leaf ifff-none {
                 type empty;
               }
               leaf ifff-primary {
                 type empty;
               }
               leaf ifff-redirects {
                 type empty;
               }
               leaf ifff-no-redirects {
                 type empty;
               }
               leaf ifff-no-neighbor-learn {
                 type empty;
               }
               leaf ifff-targeted-broadcast {
                 type empty;
               }
               leaf ifff-sendbcast-pkt-to-re {
                 type empty;
               }
               leaf ifff-hard-down {
                 type empty;
               }
               leaf ifff-down {
                 type empty;
               }
               leaf ifff-up {
                 type empty;
               }
               leaf ifff-func1 {
                 type empty;
               }
               leaf ifff-func2 {
                 type empty;
               }
               leaf ifff-is-primary {
                 type empty;
               }
               leaf ifff-recv-options {
                 type empty;
               }
               leaf ifff-recv-ttl-exceeded {
                 type empty;
               }
               leaf ifff-dst-class-usage {
                 type empty;
               }
               leaf ifff-src-class-input {
                 type empty;
               }
               leaf ifff-src-class-output {
                 type empty;
               }
               leaf ifff-mtu-user-conf {
                 type empty;
               }
               leaf ifff-mac-validate-strict {
                 type empty;
               }
               leaf ifff-mac-validate-loose {
                 type empty;
               }
               leaf ifff-rpf-check {
                 type empty;
               }
               leaf ifff-rpf-loose-mode {
                 type empty;
               }
               leaf ifff-sample-input {
                 type empty;
               }
               leaf ifff-sample-output {
                 type empty;
               }
               leaf ifff-no-asynch-notification {
                 type empty;
               }
               leaf ifff-negotiate-address {
                 type empty;
               }
               leaf ifff-port-mode-trunk {
                 type empty;
               }
               leaf ifff-inter-switch-link {
                 type empty;
               }
               leaf ifff-mtu-protocol-adj {
                 type empty;
               }
               leaf ifff-unnumbered {
                 type empty;
               }
               leaf ifff-tcc-mpls {
                 type empty;
               }
               leaf ifff-tcc-inet {
                 type empty;
               }
               leaf ifff-tcc-inet6 {
                 type empty;
               }
               leaf ifff-tcc-iso {
                 type empty;
               }
               leaf ifff-port-mode-isid-trunk {
                 type empty;
               }
               leaf generic-value {
                 type int32;
                 description
                   "Hexadecimal value of unknown flag bits";
               }
             }
             list address-family-unnumbered {
               description
                 "Information about an unnumbered address family";
               leaf unnumbered-family-donor-interface-name {
                 type string;
                 description
                   "Donor interface name";
               }
               leaf unnumbered-family-donor-interface-index {
                 type string;
                 description
                   "Donor interface index";
               }
               leaf unnumbered-family-preferred-source-address {
                 type string;
                 description
                   "Unnumbered interface preferred source address";
               }
             }
             container pppoe-underlying-information {
               description
                 "PPPoE Underlying information";
               list pppoe-underlying-interface {
                 leaf dynamic-profile {
                   type string;
                   description
                     "Dynamic Profile name";
                 }
                 leaf service-name-table {
                   type string;
                   description
                     "Name of Service Name Table";
                 }
                 leaf max-sessions {
                   type int32;
                   description
                     "Maximum number of PPPoE sessions";
                 }
                 leaf max-sessions-vsa-ignore {
                   type string;
                   description
                     "Ignore max-sessions VSA";
                 }
                 leaf duplicate-protection {
                   type string;
                   description
                     "Duplicate protection mode";
                 }
                 leaf short-cycle-protection {
                   type string;
                   description
                     "Short cycle protection mode";
                 }
                 leaf direct-connect {
                   type string;
                   description
                     "Direct connect mode";
                 }
                 leaf ac-name {
                   type string;
                   description
                     "Access Concentrator name";
                 }
                 leaf underlying-interface-name {
                   type string;
                   description
                     "Underlying interface name";
                 }
                 leaf underlying-interface-index {
                   type string;
                   description
                     "Underlying interface index";
                 }
                 leaf encapsulation-type-identifier {
                   type string;
                   description
                     "Encapsulation type identifier";
                 }
                 leaf state {
                   type string;
                   description
                     "State";
                 }
                 leaf active-sessions {
                   type int32;
                   description
                     "Number of active PPPoE sessions";
                 }
                 leaf aci-autosensing {
                   type string;
                   description
                     "ACI VLAN Autosensing mode";
                 }
                 leaf line-identity-autosensing {
                   type string;
                   description
                     "Line Identity Autosensing mode";
                 }
               }
             }
             list filter-information {
               leaf-list filter-input {
                 type string;
                 description
                   "Name of the input filter";
               }
               leaf-list filter-input-precedence {
                 type uint32;
                 description
                   "Precedence of the input filter";
               }
               leaf-list filter-output {
                 type string;
                 description
                   "Name of the output filter";
               }
               leaf-list filter-output-precedence {
                 type uint32;
                 description
                   "Precedence of the output filter";
               }
             }
             list policer-information {
               description
                 "Interface policer information";
               leaf policer-input {
                 type string;
                 description
                   "Name of the input policer";
               }
               leaf policer-output {
                 type string;
                 description
                   "Name of the output policer";
               }
             }
             list interface-address {
               leaf-list interface-address.heading {
                 type string;
               }
               leaf ifa-destination {
                 type string;
                 description
                   "Protocol address of the remote side of this connection";
               }
               leaf ifa-local {
                 type string;
                 description
                   "Protocol address on this interface";
               }
               leaf ifa-broadcast {
                 type string;
                 description
                   "Network broadcast address";
               }
               leaf ifa-primary-dns {
                 type string;
                 description
                   "Primary DNS server address";
               }
               leaf ifa-primary-nbns {
                 type string;
                 description
                   "Primary Netbios Name server address";
               }
               leaf ifa-secondary-dns {
                 type string;
                 description
                   "Secondary DNS server address";
               }
               leaf ifa-secondary-nbns {
                 type string;
                 description
                   "Secondary Netbios Name server address";
               }
               leaf ifa-address-pool {
                 type string;
                 description
                   "Address pool name";
               }
               leaf generation {
                 type int32;
                 description
                   "Generation number used to distinguish between successive
                   instances of this interface";
               }
               container ifa-flags {
                 leaf ifaf-none {
                   type empty;
                 }
                 leaf ifaf-primary {
                   type empty;
                 }
                 leaf ifaf-preferred {
                   type empty;
                 }
                 leaf ifaf-master-only {
                   type empty;
                 }
                 leaf ifaf-down {
                   type empty;
                 }
                 leaf ifaf-kernel {
                   type empty;
                 }
                 leaf ifaf-current-default {
                   type empty;
                 }
                 leaf ifaf-current-preferred {
                   type empty;
                 }
                 leaf ifaf-current-primary {
                   type empty;
                 }
                 leaf ifaf-duplicate {
                   type empty;
                 }
                 leaf ifaf-webauth-http {
                   type empty;
                 }
                 leaf generic-value {
                   type int32;
                   description
                     "Hexadecimal value of unknown flag bits";
                 }
               }
               container in6-addr-flags {
                 leaf in6-anycast {
                   type empty;
                 }
                 leaf in6-tentative {
                   type empty;
                 }
                 leaf in6-duplicate {
                   type empty;
                 }
                 leaf in6-detached {
                   type empty;
                 }
                 leaf in6-deprecated {
                   type empty;
                 }
                 leaf in6-nodad {
                   type empty;
                 }
                 leaf in6-temporary {
                   type empty;
                 }
                 leaf in6-autoconf {
                   type empty;
                 }
                 leaf in6-nopfxmgmt {
                   type empty;
                 }
               }
             }
             container mac-validate-statistics {
               description
                 "SRC MAC validate statistics";
               leaf mac-validate-packets {
                 type int32;
                 description
                   "Number of packets that have failed the mac-validate 
                   check";
               }
               leaf mac-validate-bytes {
                 type int32;
                 description
                   "Number of bytes that have failed the mac-validate check";
               }
             }
             container route-rpf-statistics {
               description
                 "Unicast reverse-path forwarding (RPF) statistics";
               leaf route-rpf-packets {
                 type int32;
                 description
                   "Number of packets that have failed the RPF check";
               }
               leaf route-rpf-bytes {
                 type int32;
                 description
                   "Number of bytes that have failed the RPF check";
               }
             }
             container destination-class-statistics {
               description
                 "Destination class usage (DCU) statistics";
               list destination-class {
                 description
                   "DCU statistics for a single class";
                 leaf dcu-class-name {
                   type string;
                   description
                     "Name of DCU class";
                 }
                 leaf dcu-class-packets {
                   type int32;
                   description
                     "Number of packets counted by DCU for this class";
                 }
                 leaf dcu-class-bytes {
                   type int32;
                   description
                     "Number of bytes counted by DCU for this class";
                 }
                 leaf dcu-class-pps {
                   type int32;
                   description
                     "Packet-per-seconds counted by DCU for this class";
                 }
                 leaf dcu-class-bps {
                   type int32;
                   description
                     "Bit-per-seconds counted by DCU for this class";
                 }
               }
             }
             container source-class-statistics {
               description
                 "Source class usage (SCU) statistics";
               list source-class {
                 description
                   "SCU statistics for a single class";
                 leaf scu-class-name {
                   type string;
                   description
                     "Name of SCU class";
                 }
                 leaf scu-class-packets {
                   type int32;
                   description
                     "Number of packets counted by SCU for this class";
                 }
                 leaf scu-class-bytes {
                   type int32;
                   description
                     "Number of bytes counted by SCU for this class";
                 }
                 leaf scu-class-pps {
                   type int32;
                   description
                     "Packet-per-seconds counted by SCU for this class";
                 }
                 leaf scu-class-bps {
                   type int32;
                   description
                     "Bit-per-seconds counted by SCU for this class";
                 }
               }
             }
           }
           list bridge-iff-properties {
             description
               "Information about Ethernet-switching address family";
           }
           container l2circuit-info {
             leaf out-of-sequence {
               type int32;
             }
             leaf denied-packets {
               type int32;
             }
             leaf cell-bundle-size {
               type int32;
             }
             leaf cell-bundle-timeout {
               type int32;
             }
             leaf cell-timeout-count {
               type int32;
             }
           }
           container irb-domain {
             leaf irb-routing-instance {
               type string;
               description
                 "Name of the Routing Instance";
             }
             leaf irb-bridge {
               type string;
               description
                 "Name of the Bridging Domain";
             }
           }
           container media-information {
             description
               "Information about media alarms";
             leaf media-type {
               type string;
               description
                 "Type of media this information is for";
             }
             list media-alarm {
               leaf media-alarm-name {
                 type string;
               }
               leaf media-alarm-count {
                 type int32;
               }
               leaf media-alarm-seconds {
                 type int32;
               }
               leaf media-alarm-state {
                 type string;
               }
               leaf ce-counter-name {
                 type string;
                 description
                   "Circuit Emulation counter information";
               }
               leaf ce-counter-packets {
                 type int32;
                 description
                   "Circuit Emulation number of packets";
               }
               leaf ce-counter-bytes {
                 type int32;
                 description
                   "Circuit Emulation number of bytes";
               }
               leaf ce-counter-count {
                 type int32;
                 description
                   "Circuit Emulation number of event occurrences";
               }
             }
             leaf ds1-timeslots {
               type string;
             }
             leaf ds1-line-encoding {
               type string;
             }
             leaf ds1-byte-encoding {
               type string;
             }
             leaf ds1-data-inversion {
               type string;
             }
             leaf idle-cycle-flag {
               type string;
             }
             leaf start-end-flag {
               type string;
             }
             leaf ds0-byte-encoding {
               type string;
             }
             leaf ds0-data-inversion {
               type string;
             }
             leaf e3-data-inversion {
               type string;
             }
             leaf ds1-buildout {
               type string;
               description
                 "Number of feet";
             }
           }
           container vtep-info {
             leaf vtep-type {
               type string;
               description
                 "Type of VXLAN endpoint";
             }
             leaf vtep-address {
               type string;
               description
                 "Protocol address of the connection";
             }
             leaf vtep-l2-routing-instance {
               type string;
               description
                 "Name of the layer-2 routing instance";
             }
             leaf vtep-l3-routing-instance {
               type string;
               description
                 "Name of the layer-3 routing instance";
             }
           }
           container ft-info {
             leaf ft-encap {
               type string;
               description
                 "Type of encap used for FTI";
             }
             leaf ft-dest-port {
               type int32;
               description
                 "Destnation UDP port used in encap";
             }
             leaf ft-vnid {
               type int32;
               description
                 "VNI value used in encap";
             }
             leaf ft-src-addr {
               type string;
               description
                 "Source address used for encap";
             }
             leaf ft-dst-addr {
               type string;
               description
                 "Destination address used for encap";
             }
           }
           container rbeb-info {
             leaf rbeb-address {
               type string;
               description
                 "Protocol address of the connection";
             }
             leaf rbeb-l2-routing-instance {
               type string;
               description
                 "Name of the layer-2 routing instance";
             }
           }
           list macsec-statistics {
             description
               "Information about MAC Security statistics details";
             leaf interface-name {
               type string;
               description
                 "Class-of-service interface name";
             }
             leaf encrypted-packets {
               type uint64;
               description
                 "Macsec encrypted packets sent";
             }
             leaf encrypted-bytes {
               type uint64;
               description
                 "Macsec encrypted bytes sent";
             }
             leaf protected-packets {
               type uint64;
               description
                 "Macsec packets sent with only integrity protection";
             }
             leaf protected-bytes {
               type uint64;
               description
                 "Macsec bytes sent with only integrity protection";
             }
             leaf ok-packets {
               type uint64;
               description
                 "Macsec packets accepted";
             }
             leaf decrypted-bytes {
               type uint64;
               description
                 "Macsec received bytes decrypted";
             }
             leaf decrypted-packets {
               type uint64;
               description
                 "Macsec received packets decrypted";
             }
             leaf validated-packets {
               type uint64;
               description
                 "Macsec received packets validated";
             }
             leaf validated-bytes {
               type uint64;
               description
                 "Macsec received bytes validated";
             }
             leaf untagged-packets {
               type uint64;
               description
                 "Macsec untagged packets";
             }
             leaf toolong-packets {
               type uint64;
               description
                 "Macsec too long packets transmitted on a secure channel";
             }
             leaf control-packets {
               type uint64;
               description
                 "Macsec control packets received on a secure channel";
             }
             leaf tagged-miss-packets {
               type uint64;
               description
                 "Macsec tagged miss packets received on a secure channel";
             }
             leaf untagged-hit-packets {
               type uint64;
               description
                 "Macsec untagged hit packets received on a secure channel";
             }
             leaf notag-packets {
               type uint64;
               description
                 "Macsec no tag packets received on a secure channel";
             }
             leaf badtag-packets {
               type uint64;
               description
                 "Macsec bad tag packets received on a secure channel";
             }
             leaf unknown-sci-packets {
               type uint64;
               description
                 "Macsec unknown sci packets received on a secure channel";
             }
             leaf no-sci-packets {
               type uint64;
               description
                 "Macsec no sci packets received on a secure channel";
             }
             leaf control-pass-packets {
               type uint64;
               description
                 "Macsec allowed control packets received on a secure 
                 channel";
             }
             leaf uncontrol-pass-packets {
               type uint64;
               description
                 "Macsec allowed uncontrol packets received on a secure 
                 channel";
             }
             leaf control-fail-packets {
               type uint64;
               description
                 "Macsec dropped control packets received on a secure 
                 channel";
             }
             leaf uncontrol-fail-packets {
               type uint64;
               description
                 "Macsec dropped uncontrol packets received on a secure 
                 channel";
             }
             leaf hit-dropped-packets {
               type uint64;
               description
                 "Macsec hit dropped packets received on a security channel";
             }
             leaf notusing-sa-packets {
               type uint64;
               description
                 "Macsec not using sa packets received on a security channel";
             }
             leaf unused-sa-packets {
               type uint64;
               description
                 "Macsec unused sa packets received on a security channel";
             }
             leaf late-packets {
               type uint64;
               description
                 "Macsec late packets dropped on a security channel";
             }
             leaf delayed-packets {
               type uint64;
               description
                 "Macsec delayed packets accepted on a security channel";
             }
             leaf unchecked-packets {
               type uint64;
               description
                 "Macsec unchecked packets accepted on a security channel";
             }
             leaf notvalid-packets {
               type uint64;
               description
                 "Macsec not valid packets dropped on a security channel";
             }
             leaf invalid-packets {
               type uint64;
               description
                 "Macsec invalid packets accepted on a security channel";
             }
             list secure-channel-sent {
               leaf encrypted-packets {
                 type uint64;
                 description
                   "Macsec encrypted packets sent";
               }
               leaf encrypted-bytes {
                 type uint64;
                 description
                   "Macsec encrypted bytes sent";
               }
               leaf protected-packets {
                 type uint64;
                 description
                   "Macsec packets sent with only integrity protection";
               }
               leaf protected-bytes {
                 type uint64;
                 description
                   "Macsec bytes sent with only integrity protection";
               }
             }
             list secure-association-sent {
               leaf encrypted-packets {
                 type uint64;
                 description
                   "Macsec encrypted packets sent";
               }
               leaf encrypted-bytes {
                 type uint64;
                 description
                   "Macsec encrypted bytes sent";
               }
               leaf protected-packets {
                 type uint64;
                 description
                   "Macsec packets sent with only integrity protection";
               }
               leaf protected-bytes {
                 type uint64;
                 description
                   "Macsec bytes sent with only integrity protection";
               }
             }
             list secure-channel-received {
               leaf ok-packets {
                 type uint64;
                 description
                   "Macsec packets accepted";
               }
               leaf decrypted-packets {
                 type uint64;
                 description
                   "Macsec received packets decrypted";
               }
               leaf decrypted-bytes {
                 type uint64;
                 description
                   "Macsec received bytes decrypted";
               }
               leaf validated-packets {
                 type uint64;
                 description
                   "Macsec received packets validated";
               }
               leaf validated-bytes {
                 type uint64;
                 description
                   "Macsec received bytes validated";
               }
             }
             list secure-association-received {
               leaf ok-packets {
                 type uint64;
                 description
                   "Macsec packets accepted";
               }
               leaf decrypted-packets {
                 type uint64;
                 description
                   "Macsec received packets decrypted";
               }
               leaf decrypted-bytes {
                 type uint64;
                 description
                   "Macsec received bytes decrypted";
               }
               leaf validated-packets {
                 type uint64;
                 description
                   "Macsec received packets validated";
               }
               leaf validated-bytes {
                 type uint64;
                 description
                   "Macsec received bytes validated";
               }
             }
             list macsec-error-information {
               list secure-channel-sent-errors {
                 leaf untagged-packets {
                   type uint64;
                   description
                     "Macsec untagged packets";
                 }
                 leaf toolong-packets {
                   type uint64;
                   description
                     "Macsec too long packets transmitted on a secure 
                     channel";
                 }
               }
               list secure-channel-received-errors {
                 leaf control-packets {
                   type uint64;
                   description
                     "Macsec control packets received on a secure channel";
                 }
                 leaf tagged-miss-packets {
                   type uint64;
                   description
                     "Macsec tagged miss packets received on a secure 
                     channel";
                 }
                 leaf untagged-hit-packets {
                   type uint64;
                   description
                     "Macsec untagged hit packets received on a secure 
                     channel";
                 }
                 leaf untagged-packets {
                   type uint64;
                   description
                     "Macsec untagged packets";
                 }
                 leaf notag-packets {
                   type uint64;
                   description
                     "Macsec no tag packets received on a secure channel";
                 }
                 leaf badtag-packets {
                   type uint64;
                   description
                     "Macsec bad tag packets received on a secure channel";
                 }
                 leaf unknown-sci-packets {
                   type uint64;
                   description
                     "Macsec unknown sci packets received on a secure 
                     channel";
                 }
                 leaf no-sci-packets {
                   type uint64;
                   description
                     "Macsec no sci packets received on a secure channel";
                 }
                 leaf control-pass-packets {
                   type uint64;
                   description
                     "Macsec allowed control packets received on a secure 
                     channel";
                 }
                 leaf control-fail-packets {
                   type uint64;
                   description
                     "Macsec dropped control packets received on a secure 
                     channel";
                 }
                 leaf uncontrol-pass-packets {
                   type uint64;
                   description
                     "Macsec allowed uncontrol packets received on a secure 
                     channel";
                 }
                 leaf uncontrol-fail-packets {
                   type uint64;
                   description
                     "Macsec dropped uncontrol packets received on a secure 
                     channel";
                 }
               }
               list secure-channel-received-extended {
                 leaf hit-dropped-packets {
                   type uint64;
                   description
                     "Macsec hit dropped packets received on a security 
                     channel";
                 }
                 leaf invalid-packets {
                   type uint64;
                   description
                     "Macsec invalid packets accepted on a security channel";
                 }
                 leaf late-packets {
                   type uint64;
                   description
                     "Macsec late packets dropped on a security channel";
                 }
                 leaf delayed-packets {
                   type uint64;
                   description
                     "Macsec delayed packets accepted on a security channel";
                 }
                 leaf unchecked-packets {
                   type uint64;
                   description
                     "Macsec unchecked packets accepted on a security 
                     channel";
                 }
                 leaf notvalid-packets {
                   type uint64;
                   description
                     "Macsec not valid packets dropped on a security channel";
                 }
                 leaf notusing-sa-packets {
                   type uint64;
                   description
                     "Macsec not using sa packets received on a security 
                     channel";
                 }
                 leaf unused-sa-packets {
                   type uint64;
                   description
                     "Macsec unused sa packets received on a security 
                     channel";
                 }
                 leaf untagged-hit-packets {
                   type uint64;
                   description
                     "Macsec untagged hit packets received on a secure 
                     channel";
                 }
               }
             }
           }
           container multilink-bundle-status {
             description
               "Multilink bundle status";
             leaf rx-sequence-number {
               type string;
               description
                 "Received sequence number";
             }
             leaf tx-sequence-number {
               type string;
               description
                 "Transmitted sequence number";
             }
             leaf packet-drops {
               type int32;
               description
                 "Number of packets dropped";
             }
             leaf packet-drop-bytes {
               type int32;
               description
                 "Number of bytes in dropped packets";
             }
             leaf fragment-drops {
               type int32;
               description
                 "Number of fragments dropped";
             }
             leaf fragment-drop-bytes {
               type int32;
               description
                 "Number of bytes in dropped fragments";
             }
             leaf mrru-exceeded {
               type int32;
               description
                 "Number of assembled packets that exceeded MRRU";
             }
             leaf processing-errors {
               type int32;
               description
                 "Number of errors encountered in assembling packets";
             }
             leaf fragment-timeout {
               type int32;
               description
                 "Fragments timed out during assembly";
             }
             leaf sequence-number-missing {
               type int32;
               description
                 "Gap detected in sequence numbers";
             }
             leaf out-of-order-sequence-number {
               type int32;
               description
                 "Fragments with an out-of-order sequence number";
             }
             leaf out-of-range-sequence-number {
               type int32;
               description
                 "Fragments with an out-of-range sequence number";
             }
             leaf packet-buffer-overflow {
               type int32;
               description
                 "Number of times the packet data buffer overflowed";
             }
             leaf fragment-buffer-overflow {
               type int32;
               description
                 "Number of times the fragment data buffer overflowed";
             }
           }
           container multilink-bundle-class {
             description
               "Multilink class status";
             leaf multilink-class-id {
               type int32;
               description
                 "Multilink class ID";
             }
             leaf rx-sequence-number {
               type string;
               description
                 "Received sequence number";
             }
             leaf tx-sequence-number {
               type string;
               description
                 "Transmitted sequence number";
             }
             leaf packet-drops {
               type int32;
               description
                 "Number of packets dropped";
             }
             leaf packet-drop-bytes {
               type int32;
               description
                 "Number of bytes in dropped packets";
             }
             leaf fragment-drops {
               type int32;
               description
                 "Number of fragments dropped";
             }
             leaf fragment-drop-bytes {
               type int32;
               description
                 "Number of bytes in dropped fragments";
             }
             leaf mrru-exceeded {
               type int32;
               description
                 "Number of assembled packets that exceeded MRRU";
             }
             leaf processing-errors {
               type int32;
               description
                 "Number of errors encountered in assembling packets";
             }
             leaf fragment-timeout {
               type int32;
               description
                 "Fragments timed out during assembly";
             }
             leaf sequence-number-missing {
               type int32;
               description
                 "Gap detected in sequence numbers";
             }
             leaf out-of-order-sequence-number {
               type int32;
               description
                 "Fragments with an out-of-order sequence number";
             }
             leaf out-of-range-sequence-number {
               type int32;
               description
                 "Fragments with an out-of-range sequence number";
             }
             leaf packet-buffer-overflow {
               type int32;
               description
                 "Number of times the packet data buffer overflowed";
             }
             leaf fragment-buffer-overflow {
               type int32;
               description
                 "Number of times the fragment data buffer overflowed";
             }
             leaf multilink-class-drop-timeout {
               type int32;
               description
                 "Drop timeout for multilink class (milliseconds)";
             }
           }
           container lag-traffic-statistics {
             container lag-bundle {
               leaf input-packets {
                 type int32;
               }
               leaf input-pps {
                 type int32;
               }
               leaf input-bytes {
                 type int32;
               }
               leaf input-bps {
                 type int32;
               }
               leaf output-packets {
                 type int32;
               }
               leaf output-pps {
                 type int32;
               }
               leaf output-bytes {
                 type int32;
               }
               leaf output-bps {
                 type int32;
               }
             }
             container lag-adaptive-statistics {
               leaf adaptive-adjusts {
                 type int32;
               }
               leaf adaptive-scans {
                 type int32;
               }
               leaf adaptive-updates {
                 type int32;
               }
             }
             container lag-multicast-statistics {
               leaf lag-multicast-statistics-header {
                 type empty;
               }
               container lag-ipv4-multicast-statistics {
                 leaf input-packets {
                   type int32;
                 }
                 leaf input-pps {
                   type int32;
                 }
                 leaf input-bytes {
                   type int32;
                 }
                 leaf input-bps {
                   type int32;
                 }
                 leaf output-packets {
                   type int32;
                 }
                 leaf output-pps {
                   type int32;
                 }
                 leaf output-bytes {
                   type int32;
                 }
                 leaf output-bps {
                   type int32;
                 }
               }
               container lag-ipv6-multicast-statistics {
                 leaf input-packets {
                   type int32;
                 }
                 leaf input-pps {
                   type int32;
                 }
                 leaf input-bytes {
                   type int32;
                 }
                 leaf input-bps {
                   type int32;
                 }
                 leaf output-packets {
                   type int32;
                 }
                 leaf output-pps {
                   type int32;
                 }
                 leaf output-bytes {
                   type int32;
                 }
                 leaf output-bps {
                   type int32;
                 }
               }
             }
             container aggregate-member-info {
               leaf aggregate-member-count {
                 type uint32;
               }
             }
             list lag-link {
               key "name";
               leaf name {
                 type string;
                 description
                   "Name of this item";
               }
               leaf down {
                 type empty;
                 description
                   "Link is down";
               }
               leaf input-packets {
                 type int32;
               }
               leaf input-pps {
                 type int32;
               }
               leaf input-bytes {
                 type int32;
               }
               leaf input-bps {
                 type int32;
               }
               leaf output-packets {
                 type int32;
               }
               leaf output-pps {
                 type int32;
               }
               leaf output-bytes {
                 type int32;
               }
               leaf output-bps {
                 type int32;
               }
             }
             list lag-bfd-view {
               key "name";
               leaf name {
                 type string;
                 description
                   "Name of this item";
               }
               leaf link-usability {
                 type string;
               }
             }
             list lag-targeting-summary {
               leaf targeting-intf-name {
                 type string;
               }
               leaf targeting-intf-type {
                 type string;
               }
               leaf targeting-intf-link-state {
                 type string;
               }
             }
             list lag-marker {
               key "name";
               leaf name {
                 type string;
                 description
                   "Name of this item";
               }
               leaf marker-rx-packets {
                 type string;
               }
               leaf marker-response-tx-packets {
                 type string;
               }
               leaf unknown-rx-packets {
                 type string;
                 description
                   "Number of unknown type packets received";
               }
               leaf illegal-rx-packets {
                 type string;
                 description
                   "Number of ill formed packets received";
               }
             }
             list lag-lacp-statistics {
               key "name";
               leaf name {
                 type string;
                 description
                   "Name of this item";
               }
               leaf lacp-rx-packets {
                 type string;
                 description
                   "Number of LACP packets received";
               }
               leaf lacp-tx-packets {
                 type string;
                 description
                   "Number of LACP packets transmitted";
               }
               leaf unknown-rx-packets {
                 type string;
                 description
                   "Number of unknown type packets received";
               }
               leaf illegal-rx-packets {
                 type string;
                 description
                   "Number of ill formed packets received";
               }
             }
             list if-distribution-list-information {
               leaf list-type {
                 type string;
               }
               leaf list-status {
                 type string;
               }
               list if-list {
                 leaf if-child-name {
                   type string;
                 }
                 leaf if-status {
                   type string;
                 }
               }
             }
             list lag-link-protection-subgrp {
               key "name";
               leaf name {
                 type string;
                 description
                   "Name of this item";
               }
               leaf lag-link-protection-subgrp-name {
                 type string;
               }
               leaf lag-link-protection-subgrp-state {
                 type string;
               }
             }
             list lag-lacp-info {
               key "name";
               description
                 "LACP information";
               leaf name {
                 type string;
                 description
                   "Name of this item";
               }
               leaf lacp-role {
                 type string;
                 description
                   "Whether it is an actor or partner";
               }
               leaf lacp-sys-priority {
                 type string;
                 description
                   "System priority";
               }
               leaf lacp-system-id {
                 type string;
                 description
                   "LACP system identifier";
               }
               leaf lacp-port-priority {
                 type string;
                 description
                   "Priority of the port";
               }
               leaf lacp-port-number {
                 type string;
                 description
                   "Port number";
               }
               leaf lacp-port-key {
                 type string;
                 description
                   "Operational key of the port";
               }
             }
             list lag-lacp-state {
               key "name";
               description
                 "LACP protocol state information";
               leaf name {
                 type string;
                 description
                   "Name of this item";
               }
               leaf lacp-role {
                 type string;
                 description
                   "Whether it is an actor or partner";
               }
               leaf lacp-expired {
                 type string;
                 description
                   "State of the receive lacp machine is EXPIRED?";
               }
               leaf lacp-defaulted {
                 type string;
                 description
                   "State of the receive lacp machine is DEFAULTED?";
               }
               leaf lacp-distributing {
                 type string;
                 description
                   "State of the mux lacp machine is DISTRIBUTING?";
               }
               leaf lacp-collecting {
                 type string;
                 description
                   "State of the mux lacp machine is COLLECTING?";
               }
               leaf lacp-synchronization {
                 type string;
                 description
                   "Actor view of partner information is in sync";
               }
               leaf lacp-aggregation {
                 type string;
                 description
                   "Actor view of partner information is in sync";
               }
               leaf lacp-timeout {
                 type string;
                 description
                   "Configured as either fast or slow periodic";
               }
               leaf lacp-activity {
                 type string;
                 description
                   "Configured as either active or passive";
               }
             }
             list lag-lacp-protocol {
               key "name";
               description
                 "LACP protocol information";
               leaf name {
                 type string;
                 description
                   "Name of this item";
               }
               leaf lacp-receive-state {
                 type string;
                 description
                   "State of the receive lacp machine";
               }
               leaf lacp-transmit-state {
                 type string;
                 description
                   "State of the transmit lacp machine";
               }
               leaf lacp-mux-state {
                 type string;
                 description
                   "State of the mux lacp machine";
               }
             }
             list lag-lacp-bfd {
               key "name";
               description
                 "BFD protocol information";
               leaf name {
                 type string;
                 description
                   "Name of this item";
               }
               leaf lacp-bfd-state {
                 type string;
                 description
                   "State of the BFD session";
               }
             }
             list lacp-hold-up-information {
               key "name";
               description
                 "LACP hold-up information";
               leaf name {
                 type string;
                 description
                   "Name of this item";
               }
               leaf status {
                 type string;
               }
               leaf restart-count {
                 type int32;
               }
               leaf time-to-expire {
                 type int32;
               }
               leaf start-time {
                 type string;
               }
             }
           }
           container layer2-input-policer-statistics {
             description
               "Layer 2 input policer statistics for interface";
             leaf policer-low-iq2-frames {
               type int32;
               description
                 "Number of loss priority low frames";
             }
             leaf policer-medium-low-iq2-frames {
               type int32;
               description
                 "Number of loss priority medium low frames";
             }
             leaf policer-medium-high-iq2-frames {
               type int32;
               description
                 "Number of loss priority medium high frames";
             }
             leaf policer-high-iq2-frames {
               type int32;
               description
                 "Number of loss priority high frames";
             }
             leaf policer-dropped-iq2-frames {
               type int32;
               description
                 "Number of dropped frames";
             }
             leaf policer-low-bytes {
               type int32;
               description
                 "Number of loss priority low bytes";
             }
             leaf policer-low-frames {
               type int32;
               description
                 "Number of loss priority low frames";
             }
             leaf policer-low-rate {
               type int32;
               description
                 "Rate of loss priority low pkts";
             }
             leaf policer-medium-high-bytes {
               type int32;
               description
                 "Number of loss priority medium high bytes";
             }
             leaf policer-medium-high-frames {
               type int32;
               description
                 "Number of loss priority medium high frames";
             }
             leaf policer-medium-high-rate {
               type int32;
               description
                 "Rate of loss priority medium high rate";
             }
             leaf policer-high-bytes {
               type int32;
               description
                 "Number of loss priority high bytes";
             }
             leaf policer-high-frames {
               type int32;
               description
                 "Number of loss priority high frames";
             }
             leaf policer-high-rate {
               type int32;
               description
                 "Rate of loss priority high rate";
             }
             leaf policer-dropped-bytes {
               type int32;
               description
                 "Number of dropped bytes";
             }
             leaf policer-dropped-frames {
               type int32;
               description
                 "Number of dropped frames";
             }
             leaf policer-dropped-rate {
               type int32;
               description
                 "Number of dropped rate";
             }
             leaf policer-medium-low-frames {
               type int32;
               description
                 "Number of loss priority medium low frames";
             }
             leaf policer-medium-low-bytes {
               type int32;
               description
                 "Number of loss priority medium low bytes";
             }
             leaf policer-medium-low-rate {
               type int32;
               description
                 "Rate of loss priority medium low pkts";
             }
           }
           container layer2-output-policer-statistics {
             description
               "Layer 2 output policer statistics for interface";
             leaf policer-low-iq2-frames {
               type int32;
               description
                 "Number of loss priority low frames";
             }
             leaf policer-medium-low-iq2-frames {
               type int32;
               description
                 "Number of loss priority medium low frames";
             }
             leaf policer-medium-high-iq2-frames {
               type int32;
               description
                 "Number of loss priority medium high frames";
             }
             leaf policer-high-iq2-frames {
               type int32;
               description
                 "Number of loss priority high frames";
             }
             leaf policer-dropped-iq2-frames {
               type int32;
               description
                 "Number of dropped frames";
             }
             leaf policer-low-bytes {
               type int32;
               description
                 "Number of loss priority low bytes";
             }
             leaf policer-low-frames {
               type int32;
               description
                 "Number of loss priority low frames";
             }
             leaf policer-low-rate {
               type int32;
               description
                 "Rate of loss priority low pkts";
             }
             leaf policer-medium-high-bytes {
               type int32;
               description
                 "Number of loss priority medium high bytes";
             }
             leaf policer-medium-high-frames {
               type int32;
               description
                 "Number of loss priority medium high frames";
             }
             leaf policer-medium-high-rate {
               type int32;
               description
                 "Rate of loss priority medium high rate";
             }
             leaf policer-high-bytes {
               type int32;
               description
                 "Number of loss priority high bytes";
             }
             leaf policer-high-frames {
               type int32;
               description
                 "Number of loss priority high frames";
             }
             leaf policer-high-rate {
               type int32;
               description
                 "Rate of loss priority high rate";
             }
             leaf policer-dropped-bytes {
               type int32;
               description
                 "Number of dropped bytes";
             }
             leaf policer-dropped-frames {
               type int32;
               description
                 "Number of dropped frames";
             }
             leaf policer-dropped-rate {
               type int32;
               description
                 "Number of dropped rate";
             }
             leaf policer-medium-low-frames {
               type int32;
               description
                 "Number of loss priority medium low frames";
             }
             leaf policer-medium-low-bytes {
               type int32;
               description
                 "Number of loss priority medium low bytes";
             }
             leaf policer-medium-low-rate {
               type int32;
               description
                 "Rate of loss priority medium low pkts";
             }
           }
           container atm-input-policer-statistics {
             description
               "ATM input Policer Statistics for interface";
             leaf atm-policer-traffic-count-cells {
               type int32;
               description
                 "Stats for counted ATM Cells";
             }
             leaf atm-policer-traffic-discard-cells {
               type int32;
               description
                 "Stats for discarded ATM Cells";
             }
             leaf atm-policer-traffic-discard-tag-cells {
               type int32;
               description
                 "Stats for discard-tag ATM Cells";
             }
           }
           container mac-policer-information {
             leaf mac-address {
               type jt:mac-addr;
             }
             leaf mac-entry-type {
               type string;
             }
             leaf receive-bytes {
               type int32;
             }
             leaf transmit-bytes {
               type int32;
             }
             leaf receive-frames {
               type int32;
             }
             leaf transmit-frames {
               type int32;
             }
             container ether-policer-list {
               list ether-policer-record {
                 leaf policer-type {
                   type string;
                 }
                 leaf out-of-spec-frames {
                   type int32;
                 }
                 leaf out-of-spec-bytes {
                   type int32;
                 }
               }
             }
           }
         }
         container active-alarms-otn {
           leaf type-otn {
             type string;
             description
               "OTN type for associated interface alarms";
           }
           container interface-alarms {
             description
               "Container tag for interface alarms";
             leaf alarm-not-present {
               type empty;
               description
                 "No alarm indicated";
             }
             leaf sonet-alarm-lol {
               type empty;
               description
                 "Loss of light alarm";
             }
             leaf sonet-alarm-pll {
               type empty;
               description
                 "PLL lock alarm";
             }
             leaf sonet-alarm-lof {
               type empty;
               description
                 "Loss of frame alarm";
             }
             leaf sonet-alarm-los {
               type empty;
               description
                 "Loss of signal alarm";
             }
             leaf sonet-alarm-sef {
               type empty;
               description
                 "Severely errored frame alarm";
             }
             leaf sonet-alarm-lais {
               type empty;
               description
                 "Line AIS alarm";
             }
             leaf sonet-alarm-pais {
               type empty;
               description
                 "Path AIS alarm";
             }
             leaf sonet-alarm-lop {
               type empty;
               description
                 "Loss of pointer alarm";
             }
             leaf sonet-alarm-berr-sd {
               type empty;
               description
                 "Bit error rate alarm, defect";
             }
             leaf sonet-alarm-berr-sf {
               type empty;
               description
                 "Bit error rate alarm, fault";
             }
             leaf sonet-alarm-lrdi {
               type empty;
               description
                 "Line remote defect indicator alarm";
             }
             leaf sonet-alarm-prdi {
               type empty;
               description
                 "Path remote defect indicator alarm";
             }
             leaf sonet-alarm-rei {
               type empty;
               description
                 "Path remote error indicator alarm";
             }
             leaf sonet-alarm-uneq {
               type empty;
               description
                 "Unequipped alarm";
             }
             leaf sonet-alarm-pmis {
               type empty;
               description
                 "Path payload level mismatch alarm";
             }
             leaf sonet-alarm-loc {
               type empty;
               description
                 "Loss of cell delineation alarm";
             }
             leaf sonet-alarm-vais {
               type empty;
               description
                 "VT AIS alarm";
             }
             leaf sonet-alarm-vlop {
               type empty;
               description
                 "VT loss of pointer alarm";
             }
             leaf sonet-alarm-vrdi {
               type empty;
               description
                 "VT remote defect indicator alarm";
             }
             leaf sonet-alarm-vuneq {
               type empty;
               description
                 "VT unequipped alarm";
             }
             leaf sonet-alarm-vmis {
               type empty;
               description
                 "VT label mismatch alarm";
             }
             leaf sonet-alarm-vloc {
               type empty;
               description
                 "VT loss of cell delineation alarm";
             }
             leaf sdh-alarm-lol {
               type empty;
               description
                 "Loss of light alarm";
             }
             leaf sdh-alarm-pll {
               type empty;
               description
                 "PLL lock alarm";
             }
             leaf sdh-alarm-lof {
               type empty;
               description
                 "Loss of frame alarm";
             }
             leaf sdh-alarm-los {
               type empty;
               description
                 "Loss of signal alarm";
             }
             leaf sdh-alarm-oof {
               type empty;
               description
                 "Out of frame alarm";
             }
             leaf sdh-alarm-msais {
               type empty;
               description
                 "Multiplex section AIS alarm";
             }
             leaf sdh-alarm-hpais {
               type empty;
               description
                 "High order path AIS alarm";
             }
             leaf sdh-alarm-lop {
               type empty;
               description
                 "Loss of pointer alarm";
             }
             leaf sdh-alarm-berr-sd {
               type empty;
               description
                 "Bit error rate alarm, defect";
             }
             leaf sdh-alarm-berr-sf {
               type empty;
               description
                 "Bit error rate alarm, fault";
             }
             leaf sdh-alarm-msferf {
               type empty;
               description
                 "Multiplex section far-end remote failure alarm";
             }
             leaf sdh-alarm-hpferf {
               type empty;
               description
                 "High order path far-end remote failure alarm";
             }
             leaf sdh-alarm-hpfebe {
               type empty;
               description
                 "High order path far-end block error alarm";
             }
             leaf sdh-alarm-hpuneq {
               type empty;
               description
                 "High order path unequipped alarm";
             }
             leaf sdh-alarm-hpplm {
               type empty;
               description
                 "High order path payload level mismatch alarm";
             }
             leaf sdh-alarm-loc {
               type empty;
               description
                 "Loss of cell delineation alarm";
             }
             leaf sdh-alarm-tuais {
               type empty;
               description
                 "TU AIS alarm";
             }
             leaf sdh-alarm-tulop {
               type empty;
               description
                 "TU loss of pointer alarm";
             }
             leaf sdh-alarm-turdi {
               type empty;
               description
                 "TU remote defect indicator alarm";
             }
             leaf sdh-alarm-tuuneq {
               type empty;
               description
                 "TU unequipped alarm";
             }
             leaf sdh-alarm-tumis {
               type empty;
               description
                 "TU label mismatch error";
             }
             leaf sdh-alarm-tuloc {
               type empty;
               description
                 "TU loss of cell delineation alarm";
             }
             leaf ds3-alarm-pll {
               type empty;
               description
                 "PLL lock alarm";
             }
             leaf ds3-alarm-ais {
               type empty;
               description
                 "AIS alarm";
             }
             leaf ds3-alarm-lof {
               type empty;
               description
                 "Loss of frame alarm";
             }
             leaf ds3-alarm-los {
               type empty;
               description
                 "Loss of signal alarm";
             }
             leaf ds3-alarm-lcv {
               type empty;
               description
                 "Line code violation alarm";
             }
             leaf ds3-alarm-exz {
               type empty;
               description
                 "Excessive zeros alarm";
             }
             leaf ds3-alarm-ferf {
               type empty;
               description
                 "Far-end receive failure alarm";
             }
             leaf ds3-alarm-ylw {
               type empty;
               description
                 "Yellow alarm";
             }
             leaf ds3-alarm-idle {
               type empty;
               description
                 "Idle alarm";
             }
             leaf ds1-alarm-ais {
               type empty;
               description
                 "AIS alarm";
             }
             leaf ds1-alarm-lof {
               type empty;
               description
                 "Loss of frame alarm";
             }
             leaf ds1-alarm-los {
               type empty;
               description
                 "Loss of signal alarm";
             }
             leaf ds1-alarm-ylw {
               type empty;
               description
                 "Yellow alarm";
             }
             leaf ds1-alarm-crc-major {
               type empty;
               description
                 "CRC errors crossed major threshold";
             }
             leaf ds1-alarm-crc-minor {
               type empty;
               description
                 "CRC errors crossed minor threshold";
             }
             leaf dsl-alarm-lof {
               type empty;
               description
                 "Loss of frame alarm";
             }
             leaf dsl-alarm-los {
               type empty;
               description
                 "Loss of signal alarm";
             }
             leaf dsl-alarm-lom {
               type empty;
               description
                 "Loss of multiframe alarm";
             }
             leaf dsl-alarm-locdi {
               type empty;
               description
                 "Loss of cell delineation alarm for interleaved channel";
             }
             leaf dsl-alarm-locdni {
               type empty;
               description
                 "Loss of cell delineation alarm for non-interleaved channel";
             }
             leaf dsl-alarm-lop {
               type empty;
               description
                 "Loss of power alarm";
             }
             leaf dsl-alarm-far-lof {
               type empty;
               description
                 "Far-end loss-of-frame alarm";
             }
             leaf dsl-alarm-far-los {
               type empty;
               description
                 "Far-end loss-of-signal alarm";
             }
             leaf dsl-alarm-far-locdi {
               type empty;
               description
                 "Far-end loss-of-cell-delineation alarm for interleaved 
                 channel";
             }
             leaf dsl-alarm-far-locdni {
               type empty;
               description
                 "Far-end loss-of-cell-delineation alarm for non-interleaved
                 channel";
             }
             leaf fibrechannel-alarm-link-down {
               type empty;
               description
                 "Link alive failure";
             }
             leaf ethernet-alarm-link-down {
               type empty;
               description
                 "Link alive failure";
             }
             leaf ethernet-alarm-link-local-fault {
               type empty;
               description
                 "Link local fault";
             }
             leaf ethernet-alarm-link-remote-fault {
               type empty;
               description
                 "Link remote fault";
             }
             leaf ethernet-alarm-lcdp {
               type empty;
               description
                 "Loss of code-group delineation";
             }
             leaf isdn-alarm-los {
               type empty;
               description
                 "Loss of signal alarm";
             }
             leaf isdn-alarm-lof {
               type empty;
               description
                 "Loss of frame alarm";
             }
             leaf shdsl-alarm-losd {
               type empty;
               description
                 "Loss of signal alarm";
             }
             leaf shdsl-alarm-losw {
               type empty;
               description
                 "Loss of sync word alarm";
             }
             leaf shdsl-alarm-line1-losd {
               type empty;
               description
                 "Loss of signal (line 1) alarm";
             }
             leaf shdsl-alarm-line1-losw {
               type empty;
               description
                 "Loss of sync word (line 1) alarm";
             }
             leaf shdsl-alarm-line2-losd {
               type empty;
               description
                 "Loss of signal (line 2) alarm";
             }
             leaf shdsl-alarm-line2-losw {
               type empty;
               description
                 "Loss of sync word (line 2) alarm";
             }
             leaf shdsl-efm-alarm-losd {
               type empty;
               description
                 "Loss of signal alarm";
             }
             leaf shdsl-efm-alarm-losw {
               type empty;
               description
                 "Loss of sync word alarm";
             }
             leaf otn-alarm-los {
               type empty;
               description
                 "Loss of signal alarm";
             }
             leaf otn-alarm-lof {
               type empty;
               description
                 "Loss of frame alarm";
             }
             leaf otn-alarm-lom {
               type empty;
               description
                 "Loss of multiframe alarm";
             }
             leaf otn-alarm-wavelength-lock {
               type empty;
               description
                 "Loss of Wavelength Lock alarm";
             }
             leaf otn-alarm-otu-ais {
               type empty;
               description
                 "OTU Alarm Indication Signal alarm";
             }
             leaf otn-alarm-otu-bdi {
               type empty;
               description
                 "OTU Background Block Error alarm";
             }
             leaf otn-alarm-otu-ttim {
               type empty;
               description
                 "OTU Trail Trace Identifier Mismatch alarm";
             }
             leaf otn-alarm-otu-iae {
               type empty;
               description
                 "OTU Incoming Alignment alarm";
             }
             leaf otn-alarm-otu-sd {
               type empty;
               description
                 "OTU Signal Degrade alarm";
             }
             leaf otn-alarm-otu-sf {
               type empty;
               description
                 "OTU Signal Fail alarm";
             }
             leaf otn-alarm-otu-biae {
               type empty;
               description
                 "OTU Backward Incoming Alignment alarm";
             }
             leaf otn-alarm-otu-tsf {
               type empty;
               description
                 "OTU Trail Signal Fail alarm";
             }
             leaf otn-alarm-otu-ssf {
               type empty;
               description
                 "OTU Server Signal Fail alarm";
             }
             leaf otn-alarm-otu-fec-excessive {
               type empty;
               description
                 "OTU FEC Excessive alarm";
             }
             leaf otn-alarm-otu-fec-degraded {
               type empty;
               description
                 "OTU FEC Degraded alarm";
             }
             leaf otn-alarm-otu-fe-fec-degraded {
               type empty;
               description
                 "OTU FE FEC Degraded/Excessive alarm";
             }
             leaf otn-alarm-otu-threshold-bbe {
               type empty;
               description
                 "OTU Background Block Error threshold alarm";
             }
             leaf otn-alarm-otu-threshold-es {
               type empty;
               description
                 "OTU Errored Seconds threshold alarm";
             }
             leaf otn-alarm-otu-threshold-ses {
               type empty;
               description
                 "OTU Severely Errored Seconds threshold alarm";
             }
             leaf otn-alarm-otu-threshold-uas {
               type empty;
               description
                 "OTU Unavailable Seconds threshold alarm";
             }
             leaf otn-alarm-odu-ais {
               type empty;
               description
                 "ODU  Alarm Indiaction Signal alarm";
             }
             leaf otn-alarm-odu-oci {
               type empty;
               description
                 "ODU Open Connection Indication alarm";
             }
             leaf otn-alarm-odu-lck {
               type empty;
               description
                 "ODU Locked alarm";
             }
             leaf otn-alarm-odu-bdi {
               type empty;
               description
                 "ODU Backward Defect Indication alarm";
             }
             leaf otn-alarm-odu-ttim {
               type empty;
               description
                 "ODU Trail Trace Identifier Mismatch alarm";
             }
             leaf otn-alarm-odu-sd {
               type empty;
               description
                 "ODU Signal Degrade alarm";
             }
             leaf otn-alarm-odu-sf {
               type empty;
               description
                 "ODU Signal Fail alarm";
             }
             leaf otn-alarm-odu-iae {
               type empty;
               description
                 "ODU Incoming Alignment alarm";
             }
             leaf otn-alarm-odu-ltc {
               type empty;
               description
                 "ODU Loss of Tandem Connection alarm";
             }
             leaf otn-alarm-odu-csf {
               type empty;
               description
                 "ODU Client Signal Fail alarm";
             }
             leaf otn-alarm-odu-tsf {
               type empty;
               description
                 "ODU Trail Signal Fail alarm";
             }
             leaf otn-alarm-odu-ssf {
               type empty;
               description
                 "ODU Server Signal Fail alarm";
             }
             leaf otn-alarm-odu-rx-aps-change {
               type empty;
               description
                 "ODU Rx Aps Change alarm";
             }
             leaf otn-alarm-odu-threshold-bbe {
               type empty;
               description
                 "ODU Background Block Error threshold alarm";
             }
             leaf otn-alarm-odu-threshold-es {
               type empty;
               description
                 "ODU Errored Seconds threshold alarm";
             }
             leaf otn-alarm-odu-threshold-ses {
               type empty;
               description
                 "ODU Severely Errored Seconds threshold alarm";
             }
             leaf otn-alarm-odu-threshold-uas {
               type empty;
               description
                 "ODU Unavailable Seconds threshold alarm";
             }
             leaf otn-alarm-opu-pmi {
               type empty;
               description
                 "OPU Payload Mismatch alarm";
             }
             leaf otn-alarm-pre-fec-sd {
               type empty;
               description
                 "Pre-FEC SD alarm";
             }
             leaf otn-alarm-fe-pre-fec-sd {
               type empty;
               description
                 "Far end pre-FEC SD alarm";
             }
             leaf optics-alarms-mod-fault {
               type empty;
               description
                 "Module Fault alarm";
             }
             leaf optics-alarms-lol {
               type empty;
               description
                 "Loss of Lock alarm";
             }
             leaf optics-alarms-los {
               type empty;
               description
                 "Loss of Signal alarms";
             }
             leaf optics-alarms-lof {
               type empty;
               description
                 "Loss of frame alarm";
             }
             leaf optics-alarms-lom {
               type empty;
               description
                 "Loss of multi-frame alarm";
             }
             leaf optics-alarms-otu-bdi {
               type empty;
               description
                 "Backward defect indiacation alarm";
             }
             leaf optics-alarms-rmsf {
               type empty;
               description
                 "Rx Modem sysnc fault alarm";
             }
             leaf optics-alarms-rmlol {
               type empty;
               description
                 "Rx Modem loss of lock alarm";
             }
             leaf optics-alarms-rloa {
               type empty;
               description
                 "Rx loss of alignment alarm";
             }
             leaf optics-alarms-mbclf {
               type empty;
               description
                 "Modulator Bias control loop fail alarm";
             }
             leaf optics-alarms-itlaf {
               type empty;
               description
                 "ITLA Fault alarm";
             }
             leaf optics-alarms-daccf {
               type empty;
               description
                 "DAC Calibration Fault alarm";
             }
             leaf optics-alarms-adccf {
               type empty;
               description
                 "ADC Calibration Fault alarm";
             }
             leaf optics-alarms-fec-degrade {
               type empty;
               description
                 "FEC Degrade alarm";
             }
             leaf optics-alarms-fec-excessive {
               type empty;
               description
                 "FEC Excessive alarm";
             }
             leaf optics-alarms-fe-fec-degrade {
               type empty;
               description
                 "Far-end FEC Degrade alarm";
             }
             leaf optics-alarms-fe-fec-excessive {
               type empty;
               description
                 "Far-end FEC Excessive alarm";
             }
             leaf ima-alarm-startup-fe {
               type empty;
               description
                 "IMA group startup far-end alarm";
             }
             leaf ima-alarm-config-abort {
               type empty;
               description
                 "IMA group config abort alarm";
             }
             leaf ima-alarm-config-abort-fe {
               type empty;
               description
                 "IMA group config abort far-end alarm";
             }
             leaf ima-alarm-insufficient-links {
               type empty;
               description
                 "IMA group insufficient links alarm";
             }
             leaf ima-alarm-insufficient-links-fe {
               type empty;
               description
                 "IMA group insufficient links far-end alarm";
             }
             leaf ima-alarm-blocked {
               type empty;
               description
                 "IMA group blocked alarm";
             }
             leaf ima-alarm-blocked-fe {
               type empty;
               description
                 "IMA group blocked far-end alarm";
             }
             leaf ima-alarm-timing-mismatch {
               type empty;
               description
                 "IMA group timing mismatch alarm";
             }
             leaf ima-alarm-version-mismatch {
               type empty;
               description
                 "IMA group version mismatch alarm";
             }
             leaf ima-alarm-lif {
               type empty;
               description
                 "IMA link loss of IMA frame alarm";
             }
             leaf ima-alarm-lods {
               type empty;
               description
                 "IMA link out of delay synchronization alarm";
             }
             leaf ima-alarm-rdi {
               type empty;
               description
                 "IMA link remote defect indicator alarm";
             }
             leaf ima-alarm-tx-misconnected {
               type empty;
               description
                 "IMA link tx misconnected alarm";
             }
             leaf ima-alarm-rx-misconnected {
               type empty;
               description
                 "IMA link rx misconnected alarm";
             }
             leaf ima-alarm-fault {
               type empty;
               description
                 "IMA link fault alarm";
             }
             leaf ima-alarm-tx-unusable-fe {
               type empty;
               description
                 "IMA link Tx unusable far-end alarm";
             }
             leaf ima-alarm-rx-unusable-fe {
               type empty;
               description
                 "IMA link Tx unusable far-end alarm";
             }
             leaf generic-value {
               type int32;
               description
                 "Hexadecimal value of unknown flag bits";
             }
           }
         }
         container active-defects-otn {
           leaf type-otn {
             type string;
             description
               "OTN type for associated interface alarms";
           }
           container interface-alarms {
             description
               "Container tag for interface alarms";
             leaf alarm-not-present {
               type empty;
               description
                 "No alarm indicated";
             }
             leaf sonet-alarm-lol {
               type empty;
               description
                 "Loss of light alarm";
             }
             leaf sonet-alarm-pll {
               type empty;
               description
                 "PLL lock alarm";
             }
             leaf sonet-alarm-lof {
               type empty;
               description
                 "Loss of frame alarm";
             }
             leaf sonet-alarm-los {
               type empty;
               description
                 "Loss of signal alarm";
             }
             leaf sonet-alarm-sef {
               type empty;
               description
                 "Severely errored frame alarm";
             }
             leaf sonet-alarm-lais {
               type empty;
               description
                 "Line AIS alarm";
             }
             leaf sonet-alarm-pais {
               type empty;
               description
                 "Path AIS alarm";
             }
             leaf sonet-alarm-lop {
               type empty;
               description
                 "Loss of pointer alarm";
             }
             leaf sonet-alarm-berr-sd {
               type empty;
               description
                 "Bit error rate alarm, defect";
             }
             leaf sonet-alarm-berr-sf {
               type empty;
               description
                 "Bit error rate alarm, fault";
             }
             leaf sonet-alarm-lrdi {
               type empty;
               description
                 "Line remote defect indicator alarm";
             }
             leaf sonet-alarm-prdi {
               type empty;
               description
                 "Path remote defect indicator alarm";
             }
             leaf sonet-alarm-rei {
               type empty;
               description
                 "Path remote error indicator alarm";
             }
             leaf sonet-alarm-uneq {
               type empty;
               description
                 "Unequipped alarm";
             }
             leaf sonet-alarm-pmis {
               type empty;
               description
                 "Path payload level mismatch alarm";
             }
             leaf sonet-alarm-loc {
               type empty;
               description
                 "Loss of cell delineation alarm";
             }
             leaf sonet-alarm-vais {
               type empty;
               description
                 "VT AIS alarm";
             }
             leaf sonet-alarm-vlop {
               type empty;
               description
                 "VT loss of pointer alarm";
             }
             leaf sonet-alarm-vrdi {
               type empty;
               description
                 "VT remote defect indicator alarm";
             }
             leaf sonet-alarm-vuneq {
               type empty;
               description
                 "VT unequipped alarm";
             }
             leaf sonet-alarm-vmis {
               type empty;
               description
                 "VT label mismatch alarm";
             }
             leaf sonet-alarm-vloc {
               type empty;
               description
                 "VT loss of cell delineation alarm";
             }
             leaf sdh-alarm-lol {
               type empty;
               description
                 "Loss of light alarm";
             }
             leaf sdh-alarm-pll {
               type empty;
               description
                 "PLL lock alarm";
             }
             leaf sdh-alarm-lof {
               type empty;
               description
                 "Loss of frame alarm";
             }
             leaf sdh-alarm-los {
               type empty;
               description
                 "Loss of signal alarm";
             }
             leaf sdh-alarm-oof {
               type empty;
               description
                 "Out of frame alarm";
             }
             leaf sdh-alarm-msais {
               type empty;
               description
                 "Multiplex section AIS alarm";
             }
             leaf sdh-alarm-hpais {
               type empty;
               description
                 "High order path AIS alarm";
             }
             leaf sdh-alarm-lop {
               type empty;
               description
                 "Loss of pointer alarm";
             }
             leaf sdh-alarm-berr-sd {
               type empty;
               description
                 "Bit error rate alarm, defect";
             }
             leaf sdh-alarm-berr-sf {
               type empty;
               description
                 "Bit error rate alarm, fault";
             }
             leaf sdh-alarm-msferf {
               type empty;
               description
                 "Multiplex section far-end remote failure alarm";
             }
             leaf sdh-alarm-hpferf {
               type empty;
               description
                 "High order path far-end remote failure alarm";
             }
             leaf sdh-alarm-hpfebe {
               type empty;
               description
                 "High order path far-end block error alarm";
             }
             leaf sdh-alarm-hpuneq {
               type empty;
               description
                 "High order path unequipped alarm";
             }
             leaf sdh-alarm-hpplm {
               type empty;
               description
                 "High order path payload level mismatch alarm";
             }
             leaf sdh-alarm-loc {
               type empty;
               description
                 "Loss of cell delineation alarm";
             }
             leaf sdh-alarm-tuais {
               type empty;
               description
                 "TU AIS alarm";
             }
             leaf sdh-alarm-tulop {
               type empty;
               description
                 "TU loss of pointer alarm";
             }
             leaf sdh-alarm-turdi {
               type empty;
               description
                 "TU remote defect indicator alarm";
             }
             leaf sdh-alarm-tuuneq {
               type empty;
               description
                 "TU unequipped alarm";
             }
             leaf sdh-alarm-tumis {
               type empty;
               description
                 "TU label mismatch error";
             }
             leaf sdh-alarm-tuloc {
               type empty;
               description
                 "TU loss of cell delineation alarm";
             }
             leaf ds3-alarm-pll {
               type empty;
               description
                 "PLL lock alarm";
             }
             leaf ds3-alarm-ais {
               type empty;
               description
                 "AIS alarm";
             }
             leaf ds3-alarm-lof {
               type empty;
               description
                 "Loss of frame alarm";
             }
             leaf ds3-alarm-los {
               type empty;
               description
                 "Loss of signal alarm";
             }
             leaf ds3-alarm-lcv {
               type empty;
               description
                 "Line code violation alarm";
             }
             leaf ds3-alarm-exz {
               type empty;
               description
                 "Excessive zeros alarm";
             }
             leaf ds3-alarm-ferf {
               type empty;
               description
                 "Far-end receive failure alarm";
             }
             leaf ds3-alarm-ylw {
               type empty;
               description
                 "Yellow alarm";
             }
             leaf ds3-alarm-idle {
               type empty;
               description
                 "Idle alarm";
             }
             leaf ds1-alarm-ais {
               type empty;
               description
                 "AIS alarm";
             }
             leaf ds1-alarm-lof {
               type empty;
               description
                 "Loss of frame alarm";
             }
             leaf ds1-alarm-los {
               type empty;
               description
                 "Loss of signal alarm";
             }
             leaf ds1-alarm-ylw {
               type empty;
               description
                 "Yellow alarm";
             }
             leaf ds1-alarm-crc-major {
               type empty;
               description
                 "CRC errors crossed major threshold";
             }
             leaf ds1-alarm-crc-minor {
               type empty;
               description
                 "CRC errors crossed minor threshold";
             }
             leaf dsl-alarm-lof {
               type empty;
               description
                 "Loss of frame alarm";
             }
             leaf dsl-alarm-los {
               type empty;
               description
                 "Loss of signal alarm";
             }
             leaf dsl-alarm-lom {
               type empty;
               description
                 "Loss of multiframe alarm";
             }
             leaf dsl-alarm-locdi {
               type empty;
               description
                 "Loss of cell delineation alarm for interleaved channel";
             }
             leaf dsl-alarm-locdni {
               type empty;
               description
                 "Loss of cell delineation alarm for non-interleaved channel";
             }
             leaf dsl-alarm-lop {
               type empty;
               description
                 "Loss of power alarm";
             }
             leaf dsl-alarm-far-lof {
               type empty;
               description
                 "Far-end loss-of-frame alarm";
             }
             leaf dsl-alarm-far-los {
               type empty;
               description
                 "Far-end loss-of-signal alarm";
             }
             leaf dsl-alarm-far-locdi {
               type empty;
               description
                 "Far-end loss-of-cell-delineation alarm for interleaved 
                 channel";
             }
             leaf dsl-alarm-far-locdni {
               type empty;
               description
                 "Far-end loss-of-cell-delineation alarm for non-interleaved
                 channel";
             }
             leaf fibrechannel-alarm-link-down {
               type empty;
               description
                 "Link alive failure";
             }
             leaf ethernet-alarm-link-down {
               type empty;
               description
                 "Link alive failure";
             }
             leaf ethernet-alarm-link-local-fault {
               type empty;
               description
                 "Link local fault";
             }
             leaf ethernet-alarm-link-remote-fault {
               type empty;
               description
                 "Link remote fault";
             }
             leaf ethernet-alarm-lcdp {
               type empty;
               description
                 "Loss of code-group delineation";
             }
             leaf isdn-alarm-los {
               type empty;
               description
                 "Loss of signal alarm";
             }
             leaf isdn-alarm-lof {
               type empty;
               description
                 "Loss of frame alarm";
             }
             leaf shdsl-alarm-losd {
               type empty;
               description
                 "Loss of signal alarm";
             }
             leaf shdsl-alarm-losw {
               type empty;
               description
                 "Loss of sync word alarm";
             }
             leaf shdsl-alarm-line1-losd {
               type empty;
               description
                 "Loss of signal (line 1) alarm";
             }
             leaf shdsl-alarm-line1-losw {
               type empty;
               description
                 "Loss of sync word (line 1) alarm";
             }
             leaf shdsl-alarm-line2-losd {
               type empty;
               description
                 "Loss of signal (line 2) alarm";
             }
             leaf shdsl-alarm-line2-losw {
               type empty;
               description
                 "Loss of sync word (line 2) alarm";
             }
             leaf shdsl-efm-alarm-losd {
               type empty;
               description
                 "Loss of signal alarm";
             }
             leaf shdsl-efm-alarm-losw {
               type empty;
               description
                 "Loss of sync word alarm";
             }
             leaf otn-alarm-los {
               type empty;
               description
                 "Loss of signal alarm";
             }
             leaf otn-alarm-lof {
               type empty;
               description
                 "Loss of frame alarm";
             }
             leaf otn-alarm-lom {
               type empty;
               description
                 "Loss of multiframe alarm";
             }
             leaf otn-alarm-wavelength-lock {
               type empty;
               description
                 "Loss of Wavelength Lock alarm";
             }
             leaf otn-alarm-otu-ais {
               type empty;
               description
                 "OTU Alarm Indication Signal alarm";
             }
             leaf otn-alarm-otu-bdi {
               type empty;
               description
                 "OTU Background Block Error alarm";
             }
             leaf otn-alarm-otu-ttim {
               type empty;
               description
                 "OTU Trail Trace Identifier Mismatch alarm";
             }
             leaf otn-alarm-otu-iae {
               type empty;
               description
                 "OTU Incoming Alignment alarm";
             }
             leaf otn-alarm-otu-sd {
               type empty;
               description
                 "OTU Signal Degrade alarm";
             }
             leaf otn-alarm-otu-sf {
               type empty;
               description
                 "OTU Signal Fail alarm";
             }
             leaf otn-alarm-otu-biae {
               type empty;
               description
                 "OTU Backward Incoming Alignment alarm";
             }
             leaf otn-alarm-otu-tsf {
               type empty;
               description
                 "OTU Trail Signal Fail alarm";
             }
             leaf otn-alarm-otu-ssf {
               type empty;
               description
                 "OTU Server Signal Fail alarm";
             }
             leaf otn-alarm-otu-fec-excessive {
               type empty;
               description
                 "OTU FEC Excessive alarm";
             }
             leaf otn-alarm-otu-fec-degraded {
               type empty;
               description
                 "OTU FEC Degraded alarm";
             }
             leaf otn-alarm-otu-fe-fec-degraded {
               type empty;
               description
                 "OTU FE FEC Degraded/Excessive alarm";
             }
             leaf otn-alarm-otu-threshold-bbe {
               type empty;
               description
                 "OTU Background Block Error threshold alarm";
             }
             leaf otn-alarm-otu-threshold-es {
               type empty;
               description
                 "OTU Errored Seconds threshold alarm";
             }
             leaf otn-alarm-otu-threshold-ses {
               type empty;
               description
                 "OTU Severely Errored Seconds threshold alarm";
             }
             leaf otn-alarm-otu-threshold-uas {
               type empty;
               description
                 "OTU Unavailable Seconds threshold alarm";
             }
             leaf otn-alarm-odu-ais {
               type empty;
               description
                 "ODU  Alarm Indiaction Signal alarm";
             }
             leaf otn-alarm-odu-oci {
               type empty;
               description
                 "ODU Open Connection Indication alarm";
             }
             leaf otn-alarm-odu-lck {
               type empty;
               description
                 "ODU Locked alarm";
             }
             leaf otn-alarm-odu-bdi {
               type empty;
               description
                 "ODU Backward Defect Indication alarm";
             }
             leaf otn-alarm-odu-ttim {
               type empty;
               description
                 "ODU Trail Trace Identifier Mismatch alarm";
             }
             leaf otn-alarm-odu-sd {
               type empty;
               description
                 "ODU Signal Degrade alarm";
             }
             leaf otn-alarm-odu-sf {
               type empty;
               description
                 "ODU Signal Fail alarm";
             }
             leaf otn-alarm-odu-iae {
               type empty;
               description
                 "ODU Incoming Alignment alarm";
             }
             leaf otn-alarm-odu-ltc {
               type empty;
               description
                 "ODU Loss of Tandem Connection alarm";
             }
             leaf otn-alarm-odu-csf {
               type empty;
               description
                 "ODU Client Signal Fail alarm";
             }
             leaf otn-alarm-odu-tsf {
               type empty;
               description
                 "ODU Trail Signal Fail alarm";
             }
             leaf otn-alarm-odu-ssf {
               type empty;
               description
                 "ODU Server Signal Fail alarm";
             }
             leaf otn-alarm-odu-rx-aps-change {
               type empty;
               description
                 "ODU Rx Aps Change alarm";
             }
             leaf otn-alarm-odu-threshold-bbe {
               type empty;
               description
                 "ODU Background Block Error threshold alarm";
             }
             leaf otn-alarm-odu-threshold-es {
               type empty;
               description
                 "ODU Errored Seconds threshold alarm";
             }
             leaf otn-alarm-odu-threshold-ses {
               type empty;
               description
                 "ODU Severely Errored Seconds threshold alarm";
             }
             leaf otn-alarm-odu-threshold-uas {
               type empty;
               description
                 "ODU Unavailable Seconds threshold alarm";
             }
             leaf otn-alarm-opu-pmi {
               type empty;
               description
                 "OPU Payload Mismatch alarm";
             }
             leaf otn-alarm-pre-fec-sd {
               type empty;
               description
                 "Pre-FEC SD alarm";
             }
             leaf otn-alarm-fe-pre-fec-sd {
               type empty;
               description
                 "Far end pre-FEC SD alarm";
             }
             leaf optics-alarms-mod-fault {
               type empty;
               description
                 "Module Fault alarm";
             }
             leaf optics-alarms-lol {
               type empty;
               description
                 "Loss of Lock alarm";
             }
             leaf optics-alarms-los {
               type empty;
               description
                 "Loss of Signal alarms";
             }
             leaf optics-alarms-lof {
               type empty;
               description
                 "Loss of frame alarm";
             }
             leaf optics-alarms-lom {
               type empty;
               description
                 "Loss of multi-frame alarm";
             }
             leaf optics-alarms-otu-bdi {
               type empty;
               description
                 "Backward defect indiacation alarm";
             }
             leaf optics-alarms-rmsf {
               type empty;
               description
                 "Rx Modem sysnc fault alarm";
             }
             leaf optics-alarms-rmlol {
               type empty;
               description
                 "Rx Modem loss of lock alarm";
             }
             leaf optics-alarms-rloa {
               type empty;
               description
                 "Rx loss of alignment alarm";
             }
             leaf optics-alarms-mbclf {
               type empty;
               description
                 "Modulator Bias control loop fail alarm";
             }
             leaf optics-alarms-itlaf {
               type empty;
               description
                 "ITLA Fault alarm";
             }
             leaf optics-alarms-daccf {
               type empty;
               description
                 "DAC Calibration Fault alarm";
             }
             leaf optics-alarms-adccf {
               type empty;
               description
                 "ADC Calibration Fault alarm";
             }
             leaf optics-alarms-fec-degrade {
               type empty;
               description
                 "FEC Degrade alarm";
             }
             leaf optics-alarms-fec-excessive {
               type empty;
               description
                 "FEC Excessive alarm";
             }
             leaf optics-alarms-fe-fec-degrade {
               type empty;
               description
                 "Far-end FEC Degrade alarm";
             }
             leaf optics-alarms-fe-fec-excessive {
               type empty;
               description
                 "Far-end FEC Excessive alarm";
             }
             leaf ima-alarm-startup-fe {
               type empty;
               description
                 "IMA group startup far-end alarm";
             }
             leaf ima-alarm-config-abort {
               type empty;
               description
                 "IMA group config abort alarm";
             }
             leaf ima-alarm-config-abort-fe {
               type empty;
               description
                 "IMA group config abort far-end alarm";
             }
             leaf ima-alarm-insufficient-links {
               type empty;
               description
                 "IMA group insufficient links alarm";
             }
             leaf ima-alarm-insufficient-links-fe {
               type empty;
               description
                 "IMA group insufficient links far-end alarm";
             }
             leaf ima-alarm-blocked {
               type empty;
               description
                 "IMA group blocked alarm";
             }
             leaf ima-alarm-blocked-fe {
               type empty;
               description
                 "IMA group blocked far-end alarm";
             }
             leaf ima-alarm-timing-mismatch {
               type empty;
               description
                 "IMA group timing mismatch alarm";
             }
             leaf ima-alarm-version-mismatch {
               type empty;
               description
                 "IMA group version mismatch alarm";
             }
             leaf ima-alarm-lif {
               type empty;
               description
                 "IMA link loss of IMA frame alarm";
             }
             leaf ima-alarm-lods {
               type empty;
               description
                 "IMA link out of delay synchronization alarm";
             }
             leaf ima-alarm-rdi {
               type empty;
               description
                 "IMA link remote defect indicator alarm";
             }
             leaf ima-alarm-tx-misconnected {
               type empty;
               description
                 "IMA link tx misconnected alarm";
             }
             leaf ima-alarm-rx-misconnected {
               type empty;
               description
                 "IMA link rx misconnected alarm";
             }
             leaf ima-alarm-fault {
               type empty;
               description
                 "IMA link fault alarm";
             }
             leaf ima-alarm-tx-unusable-fe {
               type empty;
               description
                 "IMA link Tx unusable far-end alarm";
             }
             leaf ima-alarm-rx-unusable-fe {
               type empty;
               description
                 "IMA link Tx unusable far-end alarm";
             }
             leaf generic-value {
               type int32;
               description
                 "Hexadecimal value of unknown flag bits";
             }
           }
         }
         container active-alarms-optics {
           leaf type-optics {
             type string;
             description
               "Optics type for associated interface alarms";
           }
           container interface-alarms {
             description
               "Container tag for interface alarms";
             leaf alarm-not-present {
               type empty;
               description
                 "No alarm indicated";
             }
             leaf sonet-alarm-lol {
               type empty;
               description
                 "Loss of light alarm";
             }
             leaf sonet-alarm-pll {
               type empty;
               description
                 "PLL lock alarm";
             }
             leaf sonet-alarm-lof {
               type empty;
               description
                 "Loss of frame alarm";
             }
             leaf sonet-alarm-los {
               type empty;
               description
                 "Loss of signal alarm";
             }
             leaf sonet-alarm-sef {
               type empty;
               description
                 "Severely errored frame alarm";
             }
             leaf sonet-alarm-lais {
               type empty;
               description
                 "Line AIS alarm";
             }
             leaf sonet-alarm-pais {
               type empty;
               description
                 "Path AIS alarm";
             }
             leaf sonet-alarm-lop {
               type empty;
               description
                 "Loss of pointer alarm";
             }
             leaf sonet-alarm-berr-sd {
               type empty;
               description
                 "Bit error rate alarm, defect";
             }
             leaf sonet-alarm-berr-sf {
               type empty;
               description
                 "Bit error rate alarm, fault";
             }
             leaf sonet-alarm-lrdi {
               type empty;
               description
                 "Line remote defect indicator alarm";
             }
             leaf sonet-alarm-prdi {
               type empty;
               description
                 "Path remote defect indicator alarm";
             }
             leaf sonet-alarm-rei {
               type empty;
               description
                 "Path remote error indicator alarm";
             }
             leaf sonet-alarm-uneq {
               type empty;
               description
                 "Unequipped alarm";
             }
             leaf sonet-alarm-pmis {
               type empty;
               description
                 "Path payload level mismatch alarm";
             }
             leaf sonet-alarm-loc {
               type empty;
               description
                 "Loss of cell delineation alarm";
             }
             leaf sonet-alarm-vais {
               type empty;
               description
                 "VT AIS alarm";
             }
             leaf sonet-alarm-vlop {
               type empty;
               description
                 "VT loss of pointer alarm";
             }
             leaf sonet-alarm-vrdi {
               type empty;
               description
                 "VT remote defect indicator alarm";
             }
             leaf sonet-alarm-vuneq {
               type empty;
               description
                 "VT unequipped alarm";
             }
             leaf sonet-alarm-vmis {
               type empty;
               description
                 "VT label mismatch alarm";
             }
             leaf sonet-alarm-vloc {
               type empty;
               description
                 "VT loss of cell delineation alarm";
             }
             leaf sdh-alarm-lol {
               type empty;
               description
                 "Loss of light alarm";
             }
             leaf sdh-alarm-pll {
               type empty;
               description
                 "PLL lock alarm";
             }
             leaf sdh-alarm-lof {
               type empty;
               description
                 "Loss of frame alarm";
             }
             leaf sdh-alarm-los {
               type empty;
               description
                 "Loss of signal alarm";
             }
             leaf sdh-alarm-oof {
               type empty;
               description
                 "Out of frame alarm";
             }
             leaf sdh-alarm-msais {
               type empty;
               description
                 "Multiplex section AIS alarm";
             }
             leaf sdh-alarm-hpais {
               type empty;
               description
                 "High order path AIS alarm";
             }
             leaf sdh-alarm-lop {
               type empty;
               description
                 "Loss of pointer alarm";
             }
             leaf sdh-alarm-berr-sd {
               type empty;
               description
                 "Bit error rate alarm, defect";
             }
             leaf sdh-alarm-berr-sf {
               type empty;
               description
                 "Bit error rate alarm, fault";
             }
             leaf sdh-alarm-msferf {
               type empty;
               description
                 "Multiplex section far-end remote failure alarm";
             }
             leaf sdh-alarm-hpferf {
               type empty;
               description
                 "High order path far-end remote failure alarm";
             }
             leaf sdh-alarm-hpfebe {
               type empty;
               description
                 "High order path far-end block error alarm";
             }
             leaf sdh-alarm-hpuneq {
               type empty;
               description
                 "High order path unequipped alarm";
             }
             leaf sdh-alarm-hpplm {
               type empty;
               description
                 "High order path payload level mismatch alarm";
             }
             leaf sdh-alarm-loc {
               type empty;
               description
                 "Loss of cell delineation alarm";
             }
             leaf sdh-alarm-tuais {
               type empty;
               description
                 "TU AIS alarm";
             }
             leaf sdh-alarm-tulop {
               type empty;
               description
                 "TU loss of pointer alarm";
             }
             leaf sdh-alarm-turdi {
               type empty;
               description
                 "TU remote defect indicator alarm";
             }
             leaf sdh-alarm-tuuneq {
               type empty;
               description
                 "TU unequipped alarm";
             }
             leaf sdh-alarm-tumis {
               type empty;
               description
                 "TU label mismatch error";
             }
             leaf sdh-alarm-tuloc {
               type empty;
               description
                 "TU loss of cell delineation alarm";
             }
             leaf ds3-alarm-pll {
               type empty;
               description
                 "PLL lock alarm";
             }
             leaf ds3-alarm-ais {
               type empty;
               description
                 "AIS alarm";
             }
             leaf ds3-alarm-lof {
               type empty;
               description
                 "Loss of frame alarm";
             }
             leaf ds3-alarm-los {
               type empty;
               description
                 "Loss of signal alarm";
             }
             leaf ds3-alarm-lcv {
               type empty;
               description
                 "Line code violation alarm";
             }
             leaf ds3-alarm-exz {
               type empty;
               description
                 "Excessive zeros alarm";
             }
             leaf ds3-alarm-ferf {
               type empty;
               description
                 "Far-end receive failure alarm";
             }
             leaf ds3-alarm-ylw {
               type empty;
               description
                 "Yellow alarm";
             }
             leaf ds3-alarm-idle {
               type empty;
               description
                 "Idle alarm";
             }
             leaf ds1-alarm-ais {
               type empty;
               description
                 "AIS alarm";
             }
             leaf ds1-alarm-lof {
               type empty;
               description
                 "Loss of frame alarm";
             }
             leaf ds1-alarm-los {
               type empty;
               description
                 "Loss of signal alarm";
             }
             leaf ds1-alarm-ylw {
               type empty;
               description
                 "Yellow alarm";
             }
             leaf ds1-alarm-crc-major {
               type empty;
               description
                 "CRC errors crossed major threshold";
             }
             leaf ds1-alarm-crc-minor {
               type empty;
               description
                 "CRC errors crossed minor threshold";
             }
             leaf dsl-alarm-lof {
               type empty;
               description
                 "Loss of frame alarm";
             }
             leaf dsl-alarm-los {
               type empty;
               description
                 "Loss of signal alarm";
             }
             leaf dsl-alarm-lom {
               type empty;
               description
                 "Loss of multiframe alarm";
             }
             leaf dsl-alarm-locdi {
               type empty;
               description
                 "Loss of cell delineation alarm for interleaved channel";
             }
             leaf dsl-alarm-locdni {
               type empty;
               description
                 "Loss of cell delineation alarm for non-interleaved channel";
             }
             leaf dsl-alarm-lop {
               type empty;
               description
                 "Loss of power alarm";
             }
             leaf dsl-alarm-far-lof {
               type empty;
               description
                 "Far-end loss-of-frame alarm";
             }
             leaf dsl-alarm-far-los {
               type empty;
               description
                 "Far-end loss-of-signal alarm";
             }
             leaf dsl-alarm-far-locdi {
               type empty;
               description
                 "Far-end loss-of-cell-delineation alarm for interleaved 
                 channel";
             }
             leaf dsl-alarm-far-locdni {
               type empty;
               description
                 "Far-end loss-of-cell-delineation alarm for non-interleaved
                 channel";
             }
             leaf fibrechannel-alarm-link-down {
               type empty;
               description
                 "Link alive failure";
             }
             leaf ethernet-alarm-link-down {
               type empty;
               description
                 "Link alive failure";
             }
             leaf ethernet-alarm-link-local-fault {
               type empty;
               description
                 "Link local fault";
             }
             leaf ethernet-alarm-link-remote-fault {
               type empty;
               description
                 "Link remote fault";
             }
             leaf ethernet-alarm-lcdp {
               type empty;
               description
                 "Loss of code-group delineation";
             }
             leaf isdn-alarm-los {
               type empty;
               description
                 "Loss of signal alarm";
             }
             leaf isdn-alarm-lof {
               type empty;
               description
                 "Loss of frame alarm";
             }
             leaf shdsl-alarm-losd {
               type empty;
               description
                 "Loss of signal alarm";
             }
             leaf shdsl-alarm-losw {
               type empty;
               description
                 "Loss of sync word alarm";
             }
             leaf shdsl-alarm-line1-losd {
               type empty;
               description
                 "Loss of signal (line 1) alarm";
             }
             leaf shdsl-alarm-line1-losw {
               type empty;
               description
                 "Loss of sync word (line 1) alarm";
             }
             leaf shdsl-alarm-line2-losd {
               type empty;
               description
                 "Loss of signal (line 2) alarm";
             }
             leaf shdsl-alarm-line2-losw {
               type empty;
               description
                 "Loss of sync word (line 2) alarm";
             }
             leaf shdsl-efm-alarm-losd {
               type empty;
               description
                 "Loss of signal alarm";
             }
             leaf shdsl-efm-alarm-losw {
               type empty;
               description
                 "Loss of sync word alarm";
             }
             leaf otn-alarm-los {
               type empty;
               description
                 "Loss of signal alarm";
             }
             leaf otn-alarm-lof {
               type empty;
               description
                 "Loss of frame alarm";
             }
             leaf otn-alarm-lom {
               type empty;
               description
                 "Loss of multiframe alarm";
             }
             leaf otn-alarm-wavelength-lock {
               type empty;
               description
                 "Loss of Wavelength Lock alarm";
             }
             leaf otn-alarm-otu-ais {
               type empty;
               description
                 "OTU Alarm Indication Signal alarm";
             }
             leaf otn-alarm-otu-bdi {
               type empty;
               description
                 "OTU Background Block Error alarm";
             }
             leaf otn-alarm-otu-ttim {
               type empty;
               description
                 "OTU Trail Trace Identifier Mismatch alarm";
             }
             leaf otn-alarm-otu-iae {
               type empty;
               description
                 "OTU Incoming Alignment alarm";
             }
             leaf otn-alarm-otu-sd {
               type empty;
               description
                 "OTU Signal Degrade alarm";
             }
             leaf otn-alarm-otu-sf {
               type empty;
               description
                 "OTU Signal Fail alarm";
             }
             leaf otn-alarm-otu-biae {
               type empty;
               description
                 "OTU Backward Incoming Alignment alarm";
             }
             leaf otn-alarm-otu-tsf {
               type empty;
               description
                 "OTU Trail Signal Fail alarm";
             }
             leaf otn-alarm-otu-ssf {
               type empty;
               description
                 "OTU Server Signal Fail alarm";
             }
             leaf otn-alarm-otu-fec-excessive {
               type empty;
               description
                 "OTU FEC Excessive alarm";
             }
             leaf otn-alarm-otu-fec-degraded {
               type empty;
               description
                 "OTU FEC Degraded alarm";
             }
             leaf otn-alarm-otu-fe-fec-degraded {
               type empty;
               description
                 "OTU FE FEC Degraded/Excessive alarm";
             }
             leaf otn-alarm-otu-threshold-bbe {
               type empty;
               description
                 "OTU Background Block Error threshold alarm";
             }
             leaf otn-alarm-otu-threshold-es {
               type empty;
               description
                 "OTU Errored Seconds threshold alarm";
             }
             leaf otn-alarm-otu-threshold-ses {
               type empty;
               description
                 "OTU Severely Errored Seconds threshold alarm";
             }
             leaf otn-alarm-otu-threshold-uas {
               type empty;
               description
                 "OTU Unavailable Seconds threshold alarm";
             }
             leaf otn-alarm-odu-ais {
               type empty;
               description
                 "ODU  Alarm Indiaction Signal alarm";
             }
             leaf otn-alarm-odu-oci {
               type empty;
               description
                 "ODU Open Connection Indication alarm";
             }
             leaf otn-alarm-odu-lck {
               type empty;
               description
                 "ODU Locked alarm";
             }
             leaf otn-alarm-odu-bdi {
               type empty;
               description
                 "ODU Backward Defect Indication alarm";
             }
             leaf otn-alarm-odu-ttim {
               type empty;
               description
                 "ODU Trail Trace Identifier Mismatch alarm";
             }
             leaf otn-alarm-odu-sd {
               type empty;
               description
                 "ODU Signal Degrade alarm";
             }
             leaf otn-alarm-odu-sf {
               type empty;
               description
                 "ODU Signal Fail alarm";
             }
             leaf otn-alarm-odu-iae {
               type empty;
               description
                 "ODU Incoming Alignment alarm";
             }
             leaf otn-alarm-odu-ltc {
               type empty;
               description
                 "ODU Loss of Tandem Connection alarm";
             }
             leaf otn-alarm-odu-csf {
               type empty;
               description
                 "ODU Client Signal Fail alarm";
             }
             leaf otn-alarm-odu-tsf {
               type empty;
               description
                 "ODU Trail Signal Fail alarm";
             }
             leaf otn-alarm-odu-ssf {
               type empty;
               description
                 "ODU Server Signal Fail alarm";
             }
             leaf otn-alarm-odu-rx-aps-change {
               type empty;
               description
                 "ODU Rx Aps Change alarm";
             }
             leaf otn-alarm-odu-threshold-bbe {
               type empty;
               description
                 "ODU Background Block Error threshold alarm";
             }
             leaf otn-alarm-odu-threshold-es {
               type empty;
               description
                 "ODU Errored Seconds threshold alarm";
             }
             leaf otn-alarm-odu-threshold-ses {
               type empty;
               description
                 "ODU Severely Errored Seconds threshold alarm";
             }
             leaf otn-alarm-odu-threshold-uas {
               type empty;
               description
                 "ODU Unavailable Seconds threshold alarm";
             }
             leaf otn-alarm-opu-pmi {
               type empty;
               description
                 "OPU Payload Mismatch alarm";
             }
             leaf otn-alarm-pre-fec-sd {
               type empty;
               description
                 "Pre-FEC SD alarm";
             }
             leaf otn-alarm-fe-pre-fec-sd {
               type empty;
               description
                 "Far end pre-FEC SD alarm";
             }
             leaf optics-alarms-mod-fault {
               type empty;
               description
                 "Module Fault alarm";
             }
             leaf optics-alarms-lol {
               type empty;
               description
                 "Loss of Lock alarm";
             }
             leaf optics-alarms-los {
               type empty;
               description
                 "Loss of Signal alarms";
             }
             leaf optics-alarms-lof {
               type empty;
               description
                 "Loss of frame alarm";
             }
             leaf optics-alarms-lom {
               type empty;
               description
                 "Loss of multi-frame alarm";
             }
             leaf optics-alarms-otu-bdi {
               type empty;
               description
                 "Backward defect indiacation alarm";
             }
             leaf optics-alarms-rmsf {
               type empty;
               description
                 "Rx Modem sysnc fault alarm";
             }
             leaf optics-alarms-rmlol {
               type empty;
               description
                 "Rx Modem loss of lock alarm";
             }
             leaf optics-alarms-rloa {
               type empty;
               description
                 "Rx loss of alignment alarm";
             }
             leaf optics-alarms-mbclf {
               type empty;
               description
                 "Modulator Bias control loop fail alarm";
             }
             leaf optics-alarms-itlaf {
               type empty;
               description
                 "ITLA Fault alarm";
             }
             leaf optics-alarms-daccf {
               type empty;
               description
                 "DAC Calibration Fault alarm";
             }
             leaf optics-alarms-adccf {
               type empty;
               description
                 "ADC Calibration Fault alarm";
             }
             leaf optics-alarms-fec-degrade {
               type empty;
               description
                 "FEC Degrade alarm";
             }
             leaf optics-alarms-fec-excessive {
               type empty;
               description
                 "FEC Excessive alarm";
             }
             leaf optics-alarms-fe-fec-degrade {
               type empty;
               description
                 "Far-end FEC Degrade alarm";
             }
             leaf optics-alarms-fe-fec-excessive {
               type empty;
               description
                 "Far-end FEC Excessive alarm";
             }
             leaf ima-alarm-startup-fe {
               type empty;
               description
                 "IMA group startup far-end alarm";
             }
             leaf ima-alarm-config-abort {
               type empty;
               description
                 "IMA group config abort alarm";
             }
             leaf ima-alarm-config-abort-fe {
               type empty;
               description
                 "IMA group config abort far-end alarm";
             }
             leaf ima-alarm-insufficient-links {
               type empty;
               description
                 "IMA group insufficient links alarm";
             }
             leaf ima-alarm-insufficient-links-fe {
               type empty;
               description
                 "IMA group insufficient links far-end alarm";
             }
             leaf ima-alarm-blocked {
               type empty;
               description
                 "IMA group blocked alarm";
             }
             leaf ima-alarm-blocked-fe {
               type empty;
               description
                 "IMA group blocked far-end alarm";
             }
             leaf ima-alarm-timing-mismatch {
               type empty;
               description
                 "IMA group timing mismatch alarm";
             }
             leaf ima-alarm-version-mismatch {
               type empty;
               description
                 "IMA group version mismatch alarm";
             }
             leaf ima-alarm-lif {
               type empty;
               description
                 "IMA link loss of IMA frame alarm";
             }
             leaf ima-alarm-lods {
               type empty;
               description
                 "IMA link out of delay synchronization alarm";
             }
             leaf ima-alarm-rdi {
               type empty;
               description
                 "IMA link remote defect indicator alarm";
             }
             leaf ima-alarm-tx-misconnected {
               type empty;
               description
                 "IMA link tx misconnected alarm";
             }
             leaf ima-alarm-rx-misconnected {
               type empty;
               description
                 "IMA link rx misconnected alarm";
             }
             leaf ima-alarm-fault {
               type empty;
               description
                 "IMA link fault alarm";
             }
             leaf ima-alarm-tx-unusable-fe {
               type empty;
               description
                 "IMA link Tx unusable far-end alarm";
             }
             leaf ima-alarm-rx-unusable-fe {
               type empty;
               description
                 "IMA link Tx unusable far-end alarm";
             }
             leaf generic-value {
               type int32;
               description
                 "Hexadecimal value of unknown flag bits";
             }
           }
         }
         container active-defects-optics {
           leaf type-optics {
             type string;
             description
               "Optics type for associated interface alarms";
           }
           container interface-alarms {
             description
               "Container tag for interface alarms";
             leaf alarm-not-present {
               type empty;
               description
                 "No alarm indicated";
             }
             leaf sonet-alarm-lol {
               type empty;
               description
                 "Loss of light alarm";
             }
             leaf sonet-alarm-pll {
               type empty;
               description
                 "PLL lock alarm";
             }
             leaf sonet-alarm-lof {
               type empty;
               description
                 "Loss of frame alarm";
             }
             leaf sonet-alarm-los {
               type empty;
               description
                 "Loss of signal alarm";
             }
             leaf sonet-alarm-sef {
               type empty;
               description
                 "Severely errored frame alarm";
             }
             leaf sonet-alarm-lais {
               type empty;
               description
                 "Line AIS alarm";
             }
             leaf sonet-alarm-pais {
               type empty;
               description
                 "Path AIS alarm";
             }
             leaf sonet-alarm-lop {
               type empty;
               description
                 "Loss of pointer alarm";
             }
             leaf sonet-alarm-berr-sd {
               type empty;
               description
                 "Bit error rate alarm, defect";
             }
             leaf sonet-alarm-berr-sf {
               type empty;
               description
                 "Bit error rate alarm, fault";
             }
             leaf sonet-alarm-lrdi {
               type empty;
               description
                 "Line remote defect indicator alarm";
             }
             leaf sonet-alarm-prdi {
               type empty;
               description
                 "Path remote defect indicator alarm";
             }
             leaf sonet-alarm-rei {
               type empty;
               description
                 "Path remote error indicator alarm";
             }
             leaf sonet-alarm-uneq {
               type empty;
               description
                 "Unequipped alarm";
             }
             leaf sonet-alarm-pmis {
               type empty;
               description
                 "Path payload level mismatch alarm";
             }
             leaf sonet-alarm-loc {
               type empty;
               description
                 "Loss of cell delineation alarm";
             }
             leaf sonet-alarm-vais {
               type empty;
               description
                 "VT AIS alarm";
             }
             leaf sonet-alarm-vlop {
               type empty;
               description
                 "VT loss of pointer alarm";
             }
             leaf sonet-alarm-vrdi {
               type empty;
               description
                 "VT remote defect indicator alarm";
             }
             leaf sonet-alarm-vuneq {
               type empty;
               description
                 "VT unequipped alarm";
             }
             leaf sonet-alarm-vmis {
               type empty;
               description
                 "VT label mismatch alarm";
             }
             leaf sonet-alarm-vloc {
               type empty;
               description
                 "VT loss of cell delineation alarm";
             }
             leaf sdh-alarm-lol {
               type empty;
               description
                 "Loss of light alarm";
             }
             leaf sdh-alarm-pll {
               type empty;
               description
                 "PLL lock alarm";
             }
             leaf sdh-alarm-lof {
               type empty;
               description
                 "Loss of frame alarm";
             }
             leaf sdh-alarm-los {
               type empty;
               description
                 "Loss of signal alarm";
             }
             leaf sdh-alarm-oof {
               type empty;
               description
                 "Out of frame alarm";
             }
             leaf sdh-alarm-msais {
               type empty;
               description
                 "Multiplex section AIS alarm";
             }
             leaf sdh-alarm-hpais {
               type empty;
               description
                 "High order path AIS alarm";
             }
             leaf sdh-alarm-lop {
               type empty;
               description
                 "Loss of pointer alarm";
             }
             leaf sdh-alarm-berr-sd {
               type empty;
               description
                 "Bit error rate alarm, defect";
             }
             leaf sdh-alarm-berr-sf {
               type empty;
               description
                 "Bit error rate alarm, fault";
             }
             leaf sdh-alarm-msferf {
               type empty;
               description
                 "Multiplex section far-end remote failure alarm";
             }
             leaf sdh-alarm-hpferf {
               type empty;
               description
                 "High order path far-end remote failure alarm";
             }
             leaf sdh-alarm-hpfebe {
               type empty;
               description
                 "High order path far-end block error alarm";
             }
             leaf sdh-alarm-hpuneq {
               type empty;
               description
                 "High order path unequipped alarm";
             }
             leaf sdh-alarm-hpplm {
               type empty;
               description
                 "High order path payload level mismatch alarm";
             }
             leaf sdh-alarm-loc {
               type empty;
               description
                 "Loss of cell delineation alarm";
             }
             leaf sdh-alarm-tuais {
               type empty;
               description
                 "TU AIS alarm";
             }
             leaf sdh-alarm-tulop {
               type empty;
               description
                 "TU loss of pointer alarm";
             }
             leaf sdh-alarm-turdi {
               type empty;
               description
                 "TU remote defect indicator alarm";
             }
             leaf sdh-alarm-tuuneq {
               type empty;
               description
                 "TU unequipped alarm";
             }
             leaf sdh-alarm-tumis {
               type empty;
               description
                 "TU label mismatch error";
             }
             leaf sdh-alarm-tuloc {
               type empty;
               description
                 "TU loss of cell delineation alarm";
             }
             leaf ds3-alarm-pll {
               type empty;
               description
                 "PLL lock alarm";
             }
             leaf ds3-alarm-ais {
               type empty;
               description
                 "AIS alarm";
             }
             leaf ds3-alarm-lof {
               type empty;
               description
                 "Loss of frame alarm";
             }
             leaf ds3-alarm-los {
               type empty;
               description
                 "Loss of signal alarm";
             }
             leaf ds3-alarm-lcv {
               type empty;
               description
                 "Line code violation alarm";
             }
             leaf ds3-alarm-exz {
               type empty;
               description
                 "Excessive zeros alarm";
             }
             leaf ds3-alarm-ferf {
               type empty;
               description
                 "Far-end receive failure alarm";
             }
             leaf ds3-alarm-ylw {
               type empty;
               description
                 "Yellow alarm";
             }
             leaf ds3-alarm-idle {
               type empty;
               description
                 "Idle alarm";
             }
             leaf ds1-alarm-ais {
               type empty;
               description
                 "AIS alarm";
             }
             leaf ds1-alarm-lof {
               type empty;
               description
                 "Loss of frame alarm";
             }
             leaf ds1-alarm-los {
               type empty;
               description
                 "Loss of signal alarm";
             }
             leaf ds1-alarm-ylw {
               type empty;
               description
                 "Yellow alarm";
             }
             leaf ds1-alarm-crc-major {
               type empty;
               description
                 "CRC errors crossed major threshold";
             }
             leaf ds1-alarm-crc-minor {
               type empty;
               description
                 "CRC errors crossed minor threshold";
             }
             leaf dsl-alarm-lof {
               type empty;
               description
                 "Loss of frame alarm";
             }
             leaf dsl-alarm-los {
               type empty;
               description
                 "Loss of signal alarm";
             }
             leaf dsl-alarm-lom {
               type empty;
               description
                 "Loss of multiframe alarm";
             }
             leaf dsl-alarm-locdi {
               type empty;
               description
                 "Loss of cell delineation alarm for interleaved channel";
             }
             leaf dsl-alarm-locdni {
               type empty;
               description
                 "Loss of cell delineation alarm for non-interleaved channel";
             }
             leaf dsl-alarm-lop {
               type empty;
               description
                 "Loss of power alarm";
             }
             leaf dsl-alarm-far-lof {
               type empty;
               description
                 "Far-end loss-of-frame alarm";
             }
             leaf dsl-alarm-far-los {
               type empty;
               description
                 "Far-end loss-of-signal alarm";
             }
             leaf dsl-alarm-far-locdi {
               type empty;
               description
                 "Far-end loss-of-cell-delineation alarm for interleaved 
                 channel";
             }
             leaf dsl-alarm-far-locdni {
               type empty;
               description
                 "Far-end loss-of-cell-delineation alarm for non-interleaved
                 channel";
             }
             leaf fibrechannel-alarm-link-down {
               type empty;
               description
                 "Link alive failure";
             }
             leaf ethernet-alarm-link-down {
               type empty;
               description
                 "Link alive failure";
             }
             leaf ethernet-alarm-link-local-fault {
               type empty;
               description
                 "Link local fault";
             }
             leaf ethernet-alarm-link-remote-fault {
               type empty;
               description
                 "Link remote fault";
             }
             leaf ethernet-alarm-lcdp {
               type empty;
               description
                 "Loss of code-group delineation";
             }
             leaf isdn-alarm-los {
               type empty;
               description
                 "Loss of signal alarm";
             }
             leaf isdn-alarm-lof {
               type empty;
               description
                 "Loss of frame alarm";
             }
             leaf shdsl-alarm-losd {
               type empty;
               description
                 "Loss of signal alarm";
             }
             leaf shdsl-alarm-losw {
               type empty;
               description
                 "Loss of sync word alarm";
             }
             leaf shdsl-alarm-line1-losd {
               type empty;
               description
                 "Loss of signal (line 1) alarm";
             }
             leaf shdsl-alarm-line1-losw {
               type empty;
               description
                 "Loss of sync word (line 1) alarm";
             }
             leaf shdsl-alarm-line2-losd {
               type empty;
               description
                 "Loss of signal (line 2) alarm";
             }
             leaf shdsl-alarm-line2-losw {
               type empty;
               description
                 "Loss of sync word (line 2) alarm";
             }
             leaf shdsl-efm-alarm-losd {
               type empty;
               description
                 "Loss of signal alarm";
             }
             leaf shdsl-efm-alarm-losw {
               type empty;
               description
                 "Loss of sync word alarm";
             }
             leaf otn-alarm-los {
               type empty;
               description
                 "Loss of signal alarm";
             }
             leaf otn-alarm-lof {
               type empty;
               description
                 "Loss of frame alarm";
             }
             leaf otn-alarm-lom {
               type empty;
               description
                 "Loss of multiframe alarm";
             }
             leaf otn-alarm-wavelength-lock {
               type empty;
               description
                 "Loss of Wavelength Lock alarm";
             }
             leaf otn-alarm-otu-ais {
               type empty;
               description
                 "OTU Alarm Indication Signal alarm";
             }
             leaf otn-alarm-otu-bdi {
               type empty;
               description
                 "OTU Background Block Error alarm";
             }
             leaf otn-alarm-otu-ttim {
               type empty;
               description
                 "OTU Trail Trace Identifier Mismatch alarm";
             }
             leaf otn-alarm-otu-iae {
               type empty;
               description
                 "OTU Incoming Alignment alarm";
             }
             leaf otn-alarm-otu-sd {
               type empty;
               description
                 "OTU Signal Degrade alarm";
             }
             leaf otn-alarm-otu-sf {
               type empty;
               description
                 "OTU Signal Fail alarm";
             }
             leaf otn-alarm-otu-biae {
               type empty;
               description
                 "OTU Backward Incoming Alignment alarm";
             }
             leaf otn-alarm-otu-tsf {
               type empty;
               description
                 "OTU Trail Signal Fail alarm";
             }
             leaf otn-alarm-otu-ssf {
               type empty;
               description
                 "OTU Server Signal Fail alarm";
             }
             leaf otn-alarm-otu-fec-excessive {
               type empty;
               description
                 "OTU FEC Excessive alarm";
             }
             leaf otn-alarm-otu-fec-degraded {
               type empty;
               description
                 "OTU FEC Degraded alarm";
             }
             leaf otn-alarm-otu-fe-fec-degraded {
               type empty;
               description
                 "OTU FE FEC Degraded/Excessive alarm";
             }
             leaf otn-alarm-otu-threshold-bbe {
               type empty;
               description
                 "OTU Background Block Error threshold alarm";
             }
             leaf otn-alarm-otu-threshold-es {
               type empty;
               description
                 "OTU Errored Seconds threshold alarm";
             }
             leaf otn-alarm-otu-threshold-ses {
               type empty;
               description
                 "OTU Severely Errored Seconds threshold alarm";
             }
             leaf otn-alarm-otu-threshold-uas {
               type empty;
               description
                 "OTU Unavailable Seconds threshold alarm";
             }
             leaf otn-alarm-odu-ais {
               type empty;
               description
                 "ODU  Alarm Indiaction Signal alarm";
             }
             leaf otn-alarm-odu-oci {
               type empty;
               description
                 "ODU Open Connection Indication alarm";
             }
             leaf otn-alarm-odu-lck {
               type empty;
               description
                 "ODU Locked alarm";
             }
             leaf otn-alarm-odu-bdi {
               type empty;
               description
                 "ODU Backward Defect Indication alarm";
             }
             leaf otn-alarm-odu-ttim {
               type empty;
               description
                 "ODU Trail Trace Identifier Mismatch alarm";
             }
             leaf otn-alarm-odu-sd {
               type empty;
               description
                 "ODU Signal Degrade alarm";
             }
             leaf otn-alarm-odu-sf {
               type empty;
               description
                 "ODU Signal Fail alarm";
             }
             leaf otn-alarm-odu-iae {
               type empty;
               description
                 "ODU Incoming Alignment alarm";
             }
             leaf otn-alarm-odu-ltc {
               type empty;
               description
                 "ODU Loss of Tandem Connection alarm";
             }
             leaf otn-alarm-odu-csf {
               type empty;
               description
                 "ODU Client Signal Fail alarm";
             }
             leaf otn-alarm-odu-tsf {
               type empty;
               description
                 "ODU Trail Signal Fail alarm";
             }
             leaf otn-alarm-odu-ssf {
               type empty;
               description
                 "ODU Server Signal Fail alarm";
             }
             leaf otn-alarm-odu-rx-aps-change {
               type empty;
               description
                 "ODU Rx Aps Change alarm";
             }
             leaf otn-alarm-odu-threshold-bbe {
               type empty;
               description
                 "ODU Background Block Error threshold alarm";
             }
             leaf otn-alarm-odu-threshold-es {
               type empty;
               description
                 "ODU Errored Seconds threshold alarm";
             }
             leaf otn-alarm-odu-threshold-ses {
               type empty;
               description
                 "ODU Severely Errored Seconds threshold alarm";
             }
             leaf otn-alarm-odu-threshold-uas {
               type empty;
               description
                 "ODU Unavailable Seconds threshold alarm";
             }
             leaf otn-alarm-opu-pmi {
               type empty;
               description
                 "OPU Payload Mismatch alarm";
             }
             leaf otn-alarm-pre-fec-sd {
               type empty;
               description
                 "Pre-FEC SD alarm";
             }
             leaf otn-alarm-fe-pre-fec-sd {
               type empty;
               description
                 "Far end pre-FEC SD alarm";
             }
             leaf optics-alarms-mod-fault {
               type empty;
               description
                 "Module Fault alarm";
             }
             leaf optics-alarms-lol {
               type empty;
               description
                 "Loss of Lock alarm";
             }
             leaf optics-alarms-los {
               type empty;
               description
                 "Loss of Signal alarms";
             }
             leaf optics-alarms-lof {
               type empty;
               description
                 "Loss of frame alarm";
             }
             leaf optics-alarms-lom {
               type empty;
               description
                 "Loss of multi-frame alarm";
             }
             leaf optics-alarms-otu-bdi {
               type empty;
               description
                 "Backward defect indiacation alarm";
             }
             leaf optics-alarms-rmsf {
               type empty;
               description
                 "Rx Modem sysnc fault alarm";
             }
             leaf optics-alarms-rmlol {
               type empty;
               description
                 "Rx Modem loss of lock alarm";
             }
             leaf optics-alarms-rloa {
               type empty;
               description
                 "Rx loss of alignment alarm";
             }
             leaf optics-alarms-mbclf {
               type empty;
               description
                 "Modulator Bias control loop fail alarm";
             }
             leaf optics-alarms-itlaf {
               type empty;
               description
                 "ITLA Fault alarm";
             }
             leaf optics-alarms-daccf {
               type empty;
               description
                 "DAC Calibration Fault alarm";
             }
             leaf optics-alarms-adccf {
               type empty;
               description
                 "ADC Calibration Fault alarm";
             }
             leaf optics-alarms-fec-degrade {
               type empty;
               description
                 "FEC Degrade alarm";
             }
             leaf optics-alarms-fec-excessive {
               type empty;
               description
                 "FEC Excessive alarm";
             }
             leaf optics-alarms-fe-fec-degrade {
               type empty;
               description
                 "Far-end FEC Degrade alarm";
             }
             leaf optics-alarms-fe-fec-excessive {
               type empty;
               description
                 "Far-end FEC Excessive alarm";
             }
             leaf ima-alarm-startup-fe {
               type empty;
               description
                 "IMA group startup far-end alarm";
             }
             leaf ima-alarm-config-abort {
               type empty;
               description
                 "IMA group config abort alarm";
             }
             leaf ima-alarm-config-abort-fe {
               type empty;
               description
                 "IMA group config abort far-end alarm";
             }
             leaf ima-alarm-insufficient-links {
               type empty;
               description
                 "IMA group insufficient links alarm";
             }
             leaf ima-alarm-insufficient-links-fe {
               type empty;
               description
                 "IMA group insufficient links far-end alarm";
             }
             leaf ima-alarm-blocked {
               type empty;
               description
                 "IMA group blocked alarm";
             }
             leaf ima-alarm-blocked-fe {
               type empty;
               description
                 "IMA group blocked far-end alarm";
             }
             leaf ima-alarm-timing-mismatch {
               type empty;
               description
                 "IMA group timing mismatch alarm";
             }
             leaf ima-alarm-version-mismatch {
               type empty;
               description
                 "IMA group version mismatch alarm";
             }
             leaf ima-alarm-lif {
               type empty;
               description
                 "IMA link loss of IMA frame alarm";
             }
             leaf ima-alarm-lods {
               type empty;
               description
                 "IMA link out of delay synchronization alarm";
             }
             leaf ima-alarm-rdi {
               type empty;
               description
                 "IMA link remote defect indicator alarm";
             }
             leaf ima-alarm-tx-misconnected {
               type empty;
               description
                 "IMA link tx misconnected alarm";
             }
             leaf ima-alarm-rx-misconnected {
               type empty;
               description
                 "IMA link rx misconnected alarm";
             }
             leaf ima-alarm-fault {
               type empty;
               description
                 "IMA link fault alarm";
             }
             leaf ima-alarm-tx-unusable-fe {
               type empty;
               description
                 "IMA link Tx unusable far-end alarm";
             }
             leaf ima-alarm-rx-unusable-fe {
               type empty;
               description
                 "IMA link Tx unusable far-end alarm";
             }
             leaf generic-value {
               type int32;
               description
                 "Hexadecimal value of unknown flag bits";
             }
           }
         }
         container optics-defect-information {
           list media-alarm {
             leaf media-alarm-name {
               type string;
             }
             leaf media-alarm-seconds {
               type int32;
             }
             leaf media-alarm-count {
               type int32;
             }
             leaf media-alarm-state {
               type string;
             }
           }
         }
         container optics-fec-information {
           list media-alarm {
             leaf media-alarm-name {
               type string;
             }
             leaf media-alarm-seconds {
               type int32;
             }
             leaf media-alarm-count {
               type int32;
             }
             leaf media-alarm-state {
               type string;
             }
           }
         }
         container active-alerts-otn {
           leaf type-otn {
             type string;
             description
               "OTN type for associated interface alarms";
           }
           container interface-alarms {
             description
               "Container tag for interface alarms";
             leaf alarm-not-present {
               type empty;
               description
                 "No alarm indicated";
             }
             leaf sonet-alarm-lol {
               type empty;
               description
                 "Loss of light alarm";
             }
             leaf sonet-alarm-pll {
               type empty;
               description
                 "PLL lock alarm";
             }
             leaf sonet-alarm-lof {
               type empty;
               description
                 "Loss of frame alarm";
             }
             leaf sonet-alarm-los {
               type empty;
               description
                 "Loss of signal alarm";
             }
             leaf sonet-alarm-sef {
               type empty;
               description
                 "Severely errored frame alarm";
             }
             leaf sonet-alarm-lais {
               type empty;
               description
                 "Line AIS alarm";
             }
             leaf sonet-alarm-pais {
               type empty;
               description
                 "Path AIS alarm";
             }
             leaf sonet-alarm-lop {
               type empty;
               description
                 "Loss of pointer alarm";
             }
             leaf sonet-alarm-berr-sd {
               type empty;
               description
                 "Bit error rate alarm, defect";
             }
             leaf sonet-alarm-berr-sf {
               type empty;
               description
                 "Bit error rate alarm, fault";
             }
             leaf sonet-alarm-lrdi {
               type empty;
               description
                 "Line remote defect indicator alarm";
             }
             leaf sonet-alarm-prdi {
               type empty;
               description
                 "Path remote defect indicator alarm";
             }
             leaf sonet-alarm-rei {
               type empty;
               description
                 "Path remote error indicator alarm";
             }
             leaf sonet-alarm-uneq {
               type empty;
               description
                 "Unequipped alarm";
             }
             leaf sonet-alarm-pmis {
               type empty;
               description
                 "Path payload level mismatch alarm";
             }
             leaf sonet-alarm-loc {
               type empty;
               description
                 "Loss of cell delineation alarm";
             }
             leaf sonet-alarm-vais {
               type empty;
               description
                 "VT AIS alarm";
             }
             leaf sonet-alarm-vlop {
               type empty;
               description
                 "VT loss of pointer alarm";
             }
             leaf sonet-alarm-vrdi {
               type empty;
               description
                 "VT remote defect indicator alarm";
             }
             leaf sonet-alarm-vuneq {
               type empty;
               description
                 "VT unequipped alarm";
             }
             leaf sonet-alarm-vmis {
               type empty;
               description
                 "VT label mismatch alarm";
             }
             leaf sonet-alarm-vloc {
               type empty;
               description
                 "VT loss of cell delineation alarm";
             }
             leaf sdh-alarm-lol {
               type empty;
               description
                 "Loss of light alarm";
             }
             leaf sdh-alarm-pll {
               type empty;
               description
                 "PLL lock alarm";
             }
             leaf sdh-alarm-lof {
               type empty;
               description
                 "Loss of frame alarm";
             }
             leaf sdh-alarm-los {
               type empty;
               description
                 "Loss of signal alarm";
             }
             leaf sdh-alarm-oof {
               type empty;
               description
                 "Out of frame alarm";
             }
             leaf sdh-alarm-msais {
               type empty;
               description
                 "Multiplex section AIS alarm";
             }
             leaf sdh-alarm-hpais {
               type empty;
               description
                 "High order path AIS alarm";
             }
             leaf sdh-alarm-lop {
               type empty;
               description
                 "Loss of pointer alarm";
             }
             leaf sdh-alarm-berr-sd {
               type empty;
               description
                 "Bit error rate alarm, defect";
             }
             leaf sdh-alarm-berr-sf {
               type empty;
               description
                 "Bit error rate alarm, fault";
             }
             leaf sdh-alarm-msferf {
               type empty;
               description
                 "Multiplex section far-end remote failure alarm";
             }
             leaf sdh-alarm-hpferf {
               type empty;
               description
                 "High order path far-end remote failure alarm";
             }
             leaf sdh-alarm-hpfebe {
               type empty;
               description
                 "High order path far-end block error alarm";
             }
             leaf sdh-alarm-hpuneq {
               type empty;
               description
                 "High order path unequipped alarm";
             }
             leaf sdh-alarm-hpplm {
               type empty;
               description
                 "High order path payload level mismatch alarm";
             }
             leaf sdh-alarm-loc {
               type empty;
               description
                 "Loss of cell delineation alarm";
             }
             leaf sdh-alarm-tuais {
               type empty;
               description
                 "TU AIS alarm";
             }
             leaf sdh-alarm-tulop {
               type empty;
               description
                 "TU loss of pointer alarm";
             }
             leaf sdh-alarm-turdi {
               type empty;
               description
                 "TU remote defect indicator alarm";
             }
             leaf sdh-alarm-tuuneq {
               type empty;
               description
                 "TU unequipped alarm";
             }
             leaf sdh-alarm-tumis {
               type empty;
               description
                 "TU label mismatch error";
             }
             leaf sdh-alarm-tuloc {
               type empty;
               description
                 "TU loss of cell delineation alarm";
             }
             leaf ds3-alarm-pll {
               type empty;
               description
                 "PLL lock alarm";
             }
             leaf ds3-alarm-ais {
               type empty;
               description
                 "AIS alarm";
             }
             leaf ds3-alarm-lof {
               type empty;
               description
                 "Loss of frame alarm";
             }
             leaf ds3-alarm-los {
               type empty;
               description
                 "Loss of signal alarm";
             }
             leaf ds3-alarm-lcv {
               type empty;
               description
                 "Line code violation alarm";
             }
             leaf ds3-alarm-exz {
               type empty;
               description
                 "Excessive zeros alarm";
             }
             leaf ds3-alarm-ferf {
               type empty;
               description
                 "Far-end receive failure alarm";
             }
             leaf ds3-alarm-ylw {
               type empty;
               description
                 "Yellow alarm";
             }
             leaf ds3-alarm-idle {
               type empty;
               description
                 "Idle alarm";
             }
             leaf ds1-alarm-ais {
               type empty;
               description
                 "AIS alarm";
             }
             leaf ds1-alarm-lof {
               type empty;
               description
                 "Loss of frame alarm";
             }
             leaf ds1-alarm-los {
               type empty;
               description
                 "Loss of signal alarm";
             }
             leaf ds1-alarm-ylw {
               type empty;
               description
                 "Yellow alarm";
             }
             leaf ds1-alarm-crc-major {
               type empty;
               description
                 "CRC errors crossed major threshold";
             }
             leaf ds1-alarm-crc-minor {
               type empty;
               description
                 "CRC errors crossed minor threshold";
             }
             leaf dsl-alarm-lof {
               type empty;
               description
                 "Loss of frame alarm";
             }
             leaf dsl-alarm-los {
               type empty;
               description
                 "Loss of signal alarm";
             }
             leaf dsl-alarm-lom {
               type empty;
               description
                 "Loss of multiframe alarm";
             }
             leaf dsl-alarm-locdi {
               type empty;
               description
                 "Loss of cell delineation alarm for interleaved channel";
             }
             leaf dsl-alarm-locdni {
               type empty;
               description
                 "Loss of cell delineation alarm for non-interleaved channel";
             }
             leaf dsl-alarm-lop {
               type empty;
               description
                 "Loss of power alarm";
             }
             leaf dsl-alarm-far-lof {
               type empty;
               description
                 "Far-end loss-of-frame alarm";
             }
             leaf dsl-alarm-far-los {
               type empty;
               description
                 "Far-end loss-of-signal alarm";
             }
             leaf dsl-alarm-far-locdi {
               type empty;
               description
                 "Far-end loss-of-cell-delineation alarm for interleaved 
                 channel";
             }
             leaf dsl-alarm-far-locdni {
               type empty;
               description
                 "Far-end loss-of-cell-delineation alarm for non-interleaved
                 channel";
             }
             leaf fibrechannel-alarm-link-down {
               type empty;
               description
                 "Link alive failure";
             }
             leaf ethernet-alarm-link-down {
               type empty;
               description
                 "Link alive failure";
             }
             leaf ethernet-alarm-link-local-fault {
               type empty;
               description
                 "Link local fault";
             }
             leaf ethernet-alarm-link-remote-fault {
               type empty;
               description
                 "Link remote fault";
             }
             leaf ethernet-alarm-lcdp {
               type empty;
               description
                 "Loss of code-group delineation";
             }
             leaf isdn-alarm-los {
               type empty;
               description
                 "Loss of signal alarm";
             }
             leaf isdn-alarm-lof {
               type empty;
               description
                 "Loss of frame alarm";
             }
             leaf shdsl-alarm-losd {
               type empty;
               description
                 "Loss of signal alarm";
             }
             leaf shdsl-alarm-losw {
               type empty;
               description
                 "Loss of sync word alarm";
             }
             leaf shdsl-alarm-line1-losd {
               type empty;
               description
                 "Loss of signal (line 1) alarm";
             }
             leaf shdsl-alarm-line1-losw {
               type empty;
               description
                 "Loss of sync word (line 1) alarm";
             }
             leaf shdsl-alarm-line2-losd {
               type empty;
               description
                 "Loss of signal (line 2) alarm";
             }
             leaf shdsl-alarm-line2-losw {
               type empty;
               description
                 "Loss of sync word (line 2) alarm";
             }
             leaf shdsl-efm-alarm-losd {
               type empty;
               description
                 "Loss of signal alarm";
             }
             leaf shdsl-efm-alarm-losw {
               type empty;
               description
                 "Loss of sync word alarm";
             }
             leaf otn-alarm-los {
               type empty;
               description
                 "Loss of signal alarm";
             }
             leaf otn-alarm-lof {
               type empty;
               description
                 "Loss of frame alarm";
             }
             leaf otn-alarm-lom {
               type empty;
               description
                 "Loss of multiframe alarm";
             }
             leaf otn-alarm-wavelength-lock {
               type empty;
               description
                 "Loss of Wavelength Lock alarm";
             }
             leaf otn-alarm-otu-ais {
               type empty;
               description
                 "OTU Alarm Indication Signal alarm";
             }
             leaf otn-alarm-otu-bdi {
               type empty;
               description
                 "OTU Background Block Error alarm";
             }
             leaf otn-alarm-otu-ttim {
               type empty;
               description
                 "OTU Trail Trace Identifier Mismatch alarm";
             }
             leaf otn-alarm-otu-iae {
               type empty;
               description
                 "OTU Incoming Alignment alarm";
             }
             leaf otn-alarm-otu-sd {
               type empty;
               description
                 "OTU Signal Degrade alarm";
             }
             leaf otn-alarm-otu-sf {
               type empty;
               description
                 "OTU Signal Fail alarm";
             }
             leaf otn-alarm-otu-biae {
               type empty;
               description
                 "OTU Backward Incoming Alignment alarm";
             }
             leaf otn-alarm-otu-tsf {
               type empty;
               description
                 "OTU Trail Signal Fail alarm";
             }
             leaf otn-alarm-otu-ssf {
               type empty;
               description
                 "OTU Server Signal Fail alarm";
             }
             leaf otn-alarm-otu-fec-excessive {
               type empty;
               description
                 "OTU FEC Excessive alarm";
             }
             leaf otn-alarm-otu-fec-degraded {
               type empty;
               description
                 "OTU FEC Degraded alarm";
             }
             leaf otn-alarm-otu-fe-fec-degraded {
               type empty;
               description
                 "OTU FE FEC Degraded/Excessive alarm";
             }
             leaf otn-alarm-otu-threshold-bbe {
               type empty;
               description
                 "OTU Background Block Error threshold alarm";
             }
             leaf otn-alarm-otu-threshold-es {
               type empty;
               description
                 "OTU Errored Seconds threshold alarm";
             }
             leaf otn-alarm-otu-threshold-ses {
               type empty;
               description
                 "OTU Severely Errored Seconds threshold alarm";
             }
             leaf otn-alarm-otu-threshold-uas {
               type empty;
               description
                 "OTU Unavailable Seconds threshold alarm";
             }
             leaf otn-alarm-odu-ais {
               type empty;
               description
                 "ODU  Alarm Indiaction Signal alarm";
             }
             leaf otn-alarm-odu-oci {
               type empty;
               description
                 "ODU Open Connection Indication alarm";
             }
             leaf otn-alarm-odu-lck {
               type empty;
               description
                 "ODU Locked alarm";
             }
             leaf otn-alarm-odu-bdi {
               type empty;
               description
                 "ODU Backward Defect Indication alarm";
             }
             leaf otn-alarm-odu-ttim {
               type empty;
               description
                 "ODU Trail Trace Identifier Mismatch alarm";
             }
             leaf otn-alarm-odu-sd {
               type empty;
               description
                 "ODU Signal Degrade alarm";
             }
             leaf otn-alarm-odu-sf {
               type empty;
               description
                 "ODU Signal Fail alarm";
             }
             leaf otn-alarm-odu-iae {
               type empty;
               description
                 "ODU Incoming Alignment alarm";
             }
             leaf otn-alarm-odu-ltc {
               type empty;
               description
                 "ODU Loss of Tandem Connection alarm";
             }
             leaf otn-alarm-odu-csf {
               type empty;
               description
                 "ODU Client Signal Fail alarm";
             }
             leaf otn-alarm-odu-tsf {
               type empty;
               description
                 "ODU Trail Signal Fail alarm";
             }
             leaf otn-alarm-odu-ssf {
               type empty;
               description
                 "ODU Server Signal Fail alarm";
             }
             leaf otn-alarm-odu-rx-aps-change {
               type empty;
               description
                 "ODU Rx Aps Change alarm";
             }
             leaf otn-alarm-odu-threshold-bbe {
               type empty;
               description
                 "ODU Background Block Error threshold alarm";
             }
             leaf otn-alarm-odu-threshold-es {
               type empty;
               description
                 "ODU Errored Seconds threshold alarm";
             }
             leaf otn-alarm-odu-threshold-ses {
               type empty;
               description
                 "ODU Severely Errored Seconds threshold alarm";
             }
             leaf otn-alarm-odu-threshold-uas {
               type empty;
               description
                 "ODU Unavailable Seconds threshold alarm";
             }
             leaf otn-alarm-opu-pmi {
               type empty;
               description
                 "OPU Payload Mismatch alarm";
             }
             leaf otn-alarm-pre-fec-sd {
               type empty;
               description
                 "Pre-FEC SD alarm";
             }
             leaf otn-alarm-fe-pre-fec-sd {
               type empty;
               description
                 "Far end pre-FEC SD alarm";
             }
             leaf optics-alarms-mod-fault {
               type empty;
               description
                 "Module Fault alarm";
             }
             leaf optics-alarms-lol {
               type empty;
               description
                 "Loss of Lock alarm";
             }
             leaf optics-alarms-los {
               type empty;
               description
                 "Loss of Signal alarms";
             }
             leaf optics-alarms-lof {
               type empty;
               description
                 "Loss of frame alarm";
             }
             leaf optics-alarms-lom {
               type empty;
               description
                 "Loss of multi-frame alarm";
             }
             leaf optics-alarms-otu-bdi {
               type empty;
               description
                 "Backward defect indiacation alarm";
             }
             leaf optics-alarms-rmsf {
               type empty;
               description
                 "Rx Modem sysnc fault alarm";
             }
             leaf optics-alarms-rmlol {
               type empty;
               description
                 "Rx Modem loss of lock alarm";
             }
             leaf optics-alarms-rloa {
               type empty;
               description
                 "Rx loss of alignment alarm";
             }
             leaf optics-alarms-mbclf {
               type empty;
               description
                 "Modulator Bias control loop fail alarm";
             }
             leaf optics-alarms-itlaf {
               type empty;
               description
                 "ITLA Fault alarm";
             }
             leaf optics-alarms-daccf {
               type empty;
               description
                 "DAC Calibration Fault alarm";
             }
             leaf optics-alarms-adccf {
               type empty;
               description
                 "ADC Calibration Fault alarm";
             }
             leaf optics-alarms-fec-degrade {
               type empty;
               description
                 "FEC Degrade alarm";
             }
             leaf optics-alarms-fec-excessive {
               type empty;
               description
                 "FEC Excessive alarm";
             }
             leaf optics-alarms-fe-fec-degrade {
               type empty;
               description
                 "Far-end FEC Degrade alarm";
             }
             leaf optics-alarms-fe-fec-excessive {
               type empty;
               description
                 "Far-end FEC Excessive alarm";
             }
             leaf ima-alarm-startup-fe {
               type empty;
               description
                 "IMA group startup far-end alarm";
             }
             leaf ima-alarm-config-abort {
               type empty;
               description
                 "IMA group config abort alarm";
             }
             leaf ima-alarm-config-abort-fe {
               type empty;
               description
                 "IMA group config abort far-end alarm";
             }
             leaf ima-alarm-insufficient-links {
               type empty;
               description
                 "IMA group insufficient links alarm";
             }
             leaf ima-alarm-insufficient-links-fe {
               type empty;
               description
                 "IMA group insufficient links far-end alarm";
             }
             leaf ima-alarm-blocked {
               type empty;
               description
                 "IMA group blocked alarm";
             }
             leaf ima-alarm-blocked-fe {
               type empty;
               description
                 "IMA group blocked far-end alarm";
             }
             leaf ima-alarm-timing-mismatch {
               type empty;
               description
                 "IMA group timing mismatch alarm";
             }
             leaf ima-alarm-version-mismatch {
               type empty;
               description
                 "IMA group version mismatch alarm";
             }
             leaf ima-alarm-lif {
               type empty;
               description
                 "IMA link loss of IMA frame alarm";
             }
             leaf ima-alarm-lods {
               type empty;
               description
                 "IMA link out of delay synchronization alarm";
             }
             leaf ima-alarm-rdi {
               type empty;
               description
                 "IMA link remote defect indicator alarm";
             }
             leaf ima-alarm-tx-misconnected {
               type empty;
               description
                 "IMA link tx misconnected alarm";
             }
             leaf ima-alarm-rx-misconnected {
               type empty;
               description
                 "IMA link rx misconnected alarm";
             }
             leaf ima-alarm-fault {
               type empty;
               description
                 "IMA link fault alarm";
             }
             leaf ima-alarm-tx-unusable-fe {
               type empty;
               description
                 "IMA link Tx unusable far-end alarm";
             }
             leaf ima-alarm-rx-unusable-fe {
               type empty;
               description
                 "IMA link Tx unusable far-end alarm";
             }
             leaf generic-value {
               type int32;
               description
                 "Hexadecimal value of unknown flag bits";
             }
           }
         }
         container links {
           description
             "Aggregated SONET/SDH link information";
           list link-entry {
             description
               "SONET/SDH link information";
             leaf link-id {
               type int32;
               description
                 "Link id for aggregated SONET/SDH interface";
             }
             leaf sonet-rx-overhead {
               type string;
             }
             leaf sonet-tx-overhead {
               type string;
             }
             leaf sonet-rx-path-trace {
               type string;
               description
                 "Received SONET path trace";
             }
             leaf sonet-tx-path-trace {
               type string;
               description
                 "Transmitted SONET path trace";
             }
             leaf sonet-payload-pointer-curptr {
               type string;
               description
                 "Value of the SONET/SDH payload pointer, derived from the 
                 H1 and H2 overhead bytes";
             }
             leaf sonet-payload-pointer-ptrinc-count {
               type string;
               description
                 "Number of times the value of the SONET/SDH payload pointer
                 had positive justification";
             }
             leaf sonet-payload-pointer-ptrdec-count {
               type string;
               description
                 "Number of times the value of the SONET/SDH payload pointer
                 had negative justification";
             }
             leaf sonet-payload-pointer-newptr-ndf-count {
               type string;
               description
                 "Number of times a new payload pointer was created with the
                 New Data Found flag set";
             }
             container active-alarms {
               leaf type {
                 type string;
                 description
                   "Media type for associated interface alarms";
               }
               container interface-alarms {
                 description
                   "Container tag for interface alarms";
                 leaf alarm-not-present {
                   type empty;
                   description
                     "No alarm indicated";
                 }
                 leaf sonet-alarm-lol {
                   type empty;
                   description
                     "Loss of light alarm";
                 }
                 leaf sonet-alarm-pll {
                   type empty;
                   description
                     "PLL lock alarm";
                 }
                 leaf sonet-alarm-lof {
                   type empty;
                   description
                     "Loss of frame alarm";
                 }
                 leaf sonet-alarm-los {
                   type empty;
                   description
                     "Loss of signal alarm";
                 }
                 leaf sonet-alarm-sef {
                   type empty;
                   description
                     "Severely errored frame alarm";
                 }
                 leaf sonet-alarm-lais {
                   type empty;
                   description
                     "Line AIS alarm";
                 }
                 leaf sonet-alarm-pais {
                   type empty;
                   description
                     "Path AIS alarm";
                 }
                 leaf sonet-alarm-lop {
                   type empty;
                   description
                     "Loss of pointer alarm";
                 }
                 leaf sonet-alarm-berr-sd {
                   type empty;
                   description
                     "Bit error rate alarm, defect";
                 }
                 leaf sonet-alarm-berr-sf {
                   type empty;
                   description
                     "Bit error rate alarm, fault";
                 }
                 leaf sonet-alarm-lrdi {
                   type empty;
                   description
                     "Line remote defect indicator alarm";
                 }
                 leaf sonet-alarm-prdi {
                   type empty;
                   description
                     "Path remote defect indicator alarm";
                 }
                 leaf sonet-alarm-rei {
                   type empty;
                   description
                     "Path remote error indicator alarm";
                 }
                 leaf sonet-alarm-uneq {
                   type empty;
                   description
                     "Unequipped alarm";
                 }
                 leaf sonet-alarm-pmis {
                   type empty;
                   description
                     "Path payload level mismatch alarm";
                 }
                 leaf sonet-alarm-loc {
                   type empty;
                   description
                     "Loss of cell delineation alarm";
                 }
                 leaf sonet-alarm-vais {
                   type empty;
                   description
                     "VT AIS alarm";
                 }
                 leaf sonet-alarm-vlop {
                   type empty;
                   description
                     "VT loss of pointer alarm";
                 }
                 leaf sonet-alarm-vrdi {
                   type empty;
                   description
                     "VT remote defect indicator alarm";
                 }
                 leaf sonet-alarm-vuneq {
                   type empty;
                   description
                     "VT unequipped alarm";
                 }
                 leaf sonet-alarm-vmis {
                   type empty;
                   description
                     "VT label mismatch alarm";
                 }
                 leaf sonet-alarm-vloc {
                   type empty;
                   description
                     "VT loss of cell delineation alarm";
                 }
                 leaf sdh-alarm-lol {
                   type empty;
                   description
                     "Loss of light alarm";
                 }
                 leaf sdh-alarm-pll {
                   type empty;
                   description
                     "PLL lock alarm";
                 }
                 leaf sdh-alarm-lof {
                   type empty;
                   description
                     "Loss of frame alarm";
                 }
                 leaf sdh-alarm-los {
                   type empty;
                   description
                     "Loss of signal alarm";
                 }
                 leaf sdh-alarm-oof {
                   type empty;
                   description
                     "Out of frame alarm";
                 }
                 leaf sdh-alarm-msais {
                   type empty;
                   description
                     "Multiplex section AIS alarm";
                 }
                 leaf sdh-alarm-hpais {
                   type empty;
                   description
                     "High order path AIS alarm";
                 }
                 leaf sdh-alarm-lop {
                   type empty;
                   description
                     "Loss of pointer alarm";
                 }
                 leaf sdh-alarm-berr-sd {
                   type empty;
                   description
                     "Bit error rate alarm, defect";
                 }
                 leaf sdh-alarm-berr-sf {
                   type empty;
                   description
                     "Bit error rate alarm, fault";
                 }
                 leaf sdh-alarm-msferf {
                   type empty;
                   description
                     "Multiplex section far-end remote failure alarm";
                 }
                 leaf sdh-alarm-hpferf {
                   type empty;
                   description
                     "High order path far-end remote failure alarm";
                 }
                 leaf sdh-alarm-hpfebe {
                   type empty;
                   description
                     "High order path far-end block error alarm";
                 }
                 leaf sdh-alarm-hpuneq {
                   type empty;
                   description
                     "High order path unequipped alarm";
                 }
                 leaf sdh-alarm-hpplm {
                   type empty;
                   description
                     "High order path payload level mismatch alarm";
                 }
                 leaf sdh-alarm-loc {
                   type empty;
                   description
                     "Loss of cell delineation alarm";
                 }
                 leaf sdh-alarm-tuais {
                   type empty;
                   description
                     "TU AIS alarm";
                 }
                 leaf sdh-alarm-tulop {
                   type empty;
                   description
                     "TU loss of pointer alarm";
                 }
                 leaf sdh-alarm-turdi {
                   type empty;
                   description
                     "TU remote defect indicator alarm";
                 }
                 leaf sdh-alarm-tuuneq {
                   type empty;
                   description
                     "TU unequipped alarm";
                 }
                 leaf sdh-alarm-tumis {
                   type empty;
                   description
                     "TU label mismatch error";
                 }
                 leaf sdh-alarm-tuloc {
                   type empty;
                   description
                     "TU loss of cell delineation alarm";
                 }
                 leaf ds3-alarm-pll {
                   type empty;
                   description
                     "PLL lock alarm";
                 }
                 leaf ds3-alarm-ais {
                   type empty;
                   description
                     "AIS alarm";
                 }
                 leaf ds3-alarm-lof {
                   type empty;
                   description
                     "Loss of frame alarm";
                 }
                 leaf ds3-alarm-los {
                   type empty;
                   description
                     "Loss of signal alarm";
                 }
                 leaf ds3-alarm-lcv {
                   type empty;
                   description
                     "Line code violation alarm";
                 }
                 leaf ds3-alarm-exz {
                   type empty;
                   description
                     "Excessive zeros alarm";
                 }
                 leaf ds3-alarm-ferf {
                   type empty;
                   description
                     "Far-end receive failure alarm";
                 }
                 leaf ds3-alarm-ylw {
                   type empty;
                   description
                     "Yellow alarm";
                 }
                 leaf ds3-alarm-idle {
                   type empty;
                   description
                     "Idle alarm";
                 }
                 leaf ds1-alarm-ais {
                   type empty;
                   description
                     "AIS alarm";
                 }
                 leaf ds1-alarm-lof {
                   type empty;
                   description
                     "Loss of frame alarm";
                 }
                 leaf ds1-alarm-los {
                   type empty;
                   description
                     "Loss of signal alarm";
                 }
                 leaf ds1-alarm-ylw {
                   type empty;
                   description
                     "Yellow alarm";
                 }
                 leaf ds1-alarm-crc-major {
                   type empty;
                   description
                     "CRC errors crossed major threshold";
                 }
                 leaf ds1-alarm-crc-minor {
                   type empty;
                   description
                     "CRC errors crossed minor threshold";
                 }
                 leaf dsl-alarm-lof {
                   type empty;
                   description
                     "Loss of frame alarm";
                 }
                 leaf dsl-alarm-los {
                   type empty;
                   description
                     "Loss of signal alarm";
                 }
                 leaf dsl-alarm-lom {
                   type empty;
                   description
                     "Loss of multiframe alarm";
                 }
                 leaf dsl-alarm-locdi {
                   type empty;
                   description
                     "Loss of cell delineation alarm for interleaved channel";
                 }
                 leaf dsl-alarm-locdni {
                   type empty;
                   description
                     "Loss of cell delineation alarm for non-interleaved 
                     channel";
                 }
                 leaf dsl-alarm-lop {
                   type empty;
                   description
                     "Loss of power alarm";
                 }
                 leaf dsl-alarm-far-lof {
                   type empty;
                   description
                     "Far-end loss-of-frame alarm";
                 }
                 leaf dsl-alarm-far-los {
                   type empty;
                   description
                     "Far-end loss-of-signal alarm";
                 }
                 leaf dsl-alarm-far-locdi {
                   type empty;
                   description
                     "Far-end loss-of-cell-delineation alarm for interleaved
                     channel";
                 }
                 leaf dsl-alarm-far-locdni {
                   type empty;
                   description
                     "Far-end loss-of-cell-delineation alarm for 
                     non-interleaved channel";
                 }
                 leaf fibrechannel-alarm-link-down {
                   type empty;
                   description
                     "Link alive failure";
                 }
                 leaf ethernet-alarm-link-down {
                   type empty;
                   description
                     "Link alive failure";
                 }
                 leaf ethernet-alarm-link-local-fault {
                   type empty;
                   description
                     "Link local fault";
                 }
                 leaf ethernet-alarm-link-remote-fault {
                   type empty;
                   description
                     "Link remote fault";
                 }
                 leaf ethernet-alarm-lcdp {
                   type empty;
                   description
                     "Loss of code-group delineation";
                 }
                 leaf isdn-alarm-los {
                   type empty;
                   description
                     "Loss of signal alarm";
                 }
                 leaf isdn-alarm-lof {
                   type empty;
                   description
                     "Loss of frame alarm";
                 }
                 leaf shdsl-alarm-losd {
                   type empty;
                   description
                     "Loss of signal alarm";
                 }
                 leaf shdsl-alarm-losw {
                   type empty;
                   description
                     "Loss of sync word alarm";
                 }
                 leaf shdsl-alarm-line1-losd {
                   type empty;
                   description
                     "Loss of signal (line 1) alarm";
                 }
                 leaf shdsl-alarm-line1-losw {
                   type empty;
                   description
                     "Loss of sync word (line 1) alarm";
                 }
                 leaf shdsl-alarm-line2-losd {
                   type empty;
                   description
                     "Loss of signal (line 2) alarm";
                 }
                 leaf shdsl-alarm-line2-losw {
                   type empty;
                   description
                     "Loss of sync word (line 2) alarm";
                 }
                 leaf shdsl-efm-alarm-losd {
                   type empty;
                   description
                     "Loss of signal alarm";
                 }
                 leaf shdsl-efm-alarm-losw {
                   type empty;
                   description
                     "Loss of sync word alarm";
                 }
                 leaf otn-alarm-los {
                   type empty;
                   description
                     "Loss of signal alarm";
                 }
                 leaf otn-alarm-lof {
                   type empty;
                   description
                     "Loss of frame alarm";
                 }
                 leaf otn-alarm-lom {
                   type empty;
                   description
                     "Loss of multiframe alarm";
                 }
                 leaf otn-alarm-wavelength-lock {
                   type empty;
                   description
                     "Loss of Wavelength Lock alarm";
                 }
                 leaf otn-alarm-otu-ais {
                   type empty;
                   description
                     "OTU Alarm Indication Signal alarm";
                 }
                 leaf otn-alarm-otu-bdi {
                   type empty;
                   description
                     "OTU Background Block Error alarm";
                 }
                 leaf otn-alarm-otu-ttim {
                   type empty;
                   description
                     "OTU Trail Trace Identifier Mismatch alarm";
                 }
                 leaf otn-alarm-otu-iae {
                   type empty;
                   description
                     "OTU Incoming Alignment alarm";
                 }
                 leaf otn-alarm-otu-sd {
                   type empty;
                   description
                     "OTU Signal Degrade alarm";
                 }
                 leaf otn-alarm-otu-sf {
                   type empty;
                   description
                     "OTU Signal Fail alarm";
                 }
                 leaf otn-alarm-otu-biae {
                   type empty;
                   description
                     "OTU Backward Incoming Alignment alarm";
                 }
                 leaf otn-alarm-otu-tsf {
                   type empty;
                   description
                     "OTU Trail Signal Fail alarm";
                 }
                 leaf otn-alarm-otu-ssf {
                   type empty;
                   description
                     "OTU Server Signal Fail alarm";
                 }
                 leaf otn-alarm-otu-fec-excessive {
                   type empty;
                   description
                     "OTU FEC Excessive alarm";
                 }
                 leaf otn-alarm-otu-fec-degraded {
                   type empty;
                   description
                     "OTU FEC Degraded alarm";
                 }
                 leaf otn-alarm-otu-fe-fec-degraded {
                   type empty;
                   description
                     "OTU FE FEC Degraded/Excessive alarm";
                 }
                 leaf otn-alarm-otu-threshold-bbe {
                   type empty;
                   description
                     "OTU Background Block Error threshold alarm";
                 }
                 leaf otn-alarm-otu-threshold-es {
                   type empty;
                   description
                     "OTU Errored Seconds threshold alarm";
                 }
                 leaf otn-alarm-otu-threshold-ses {
                   type empty;
                   description
                     "OTU Severely Errored Seconds threshold alarm";
                 }
                 leaf otn-alarm-otu-threshold-uas {
                   type empty;
                   description
                     "OTU Unavailable Seconds threshold alarm";
                 }
                 leaf otn-alarm-odu-ais {
                   type empty;
                   description
                     "ODU  Alarm Indiaction Signal alarm";
                 }
                 leaf otn-alarm-odu-oci {
                   type empty;
                   description
                     "ODU Open Connection Indication alarm";
                 }
                 leaf otn-alarm-odu-lck {
                   type empty;
                   description
                     "ODU Locked alarm";
                 }
                 leaf otn-alarm-odu-bdi {
                   type empty;
                   description
                     "ODU Backward Defect Indication alarm";
                 }
                 leaf otn-alarm-odu-ttim {
                   type empty;
                   description
                     "ODU Trail Trace Identifier Mismatch alarm";
                 }
                 leaf otn-alarm-odu-sd {
                   type empty;
                   description
                     "ODU Signal Degrade alarm";
                 }
                 leaf otn-alarm-odu-sf {
                   type empty;
                   description
                     "ODU Signal Fail alarm";
                 }
                 leaf otn-alarm-odu-iae {
                   type empty;
                   description
                     "ODU Incoming Alignment alarm";
                 }
                 leaf otn-alarm-odu-ltc {
                   type empty;
                   description
                     "ODU Loss of Tandem Connection alarm";
                 }
                 leaf otn-alarm-odu-csf {
                   type empty;
                   description
                     "ODU Client Signal Fail alarm";
                 }
                 leaf otn-alarm-odu-tsf {
                   type empty;
                   description
                     "ODU Trail Signal Fail alarm";
                 }
                 leaf otn-alarm-odu-ssf {
                   type empty;
                   description
                     "ODU Server Signal Fail alarm";
                 }
                 leaf otn-alarm-odu-rx-aps-change {
                   type empty;
                   description
                     "ODU Rx Aps Change alarm";
                 }
                 leaf otn-alarm-odu-threshold-bbe {
                   type empty;
                   description
                     "ODU Background Block Error threshold alarm";
                 }
                 leaf otn-alarm-odu-threshold-es {
                   type empty;
                   description
                     "ODU Errored Seconds threshold alarm";
                 }
                 leaf otn-alarm-odu-threshold-ses {
                   type empty;
                   description
                     "ODU Severely Errored Seconds threshold alarm";
                 }
                 leaf otn-alarm-odu-threshold-uas {
                   type empty;
                   description
                     "ODU Unavailable Seconds threshold alarm";
                 }
                 leaf otn-alarm-opu-pmi {
                   type empty;
                   description
                     "OPU Payload Mismatch alarm";
                 }
                 leaf otn-alarm-pre-fec-sd {
                   type empty;
                   description
                     "Pre-FEC SD alarm";
                 }
                 leaf otn-alarm-fe-pre-fec-sd {
                   type empty;
                   description
                     "Far end pre-FEC SD alarm";
                 }
                 leaf optics-alarms-mod-fault {
                   type empty;
                   description
                     "Module Fault alarm";
                 }
                 leaf optics-alarms-lol {
                   type empty;
                   description
                     "Loss of Lock alarm";
                 }
                 leaf optics-alarms-los {
                   type empty;
                   description
                     "Loss of Signal alarms";
                 }
                 leaf optics-alarms-lof {
                   type empty;
                   description
                     "Loss of frame alarm";
                 }
                 leaf optics-alarms-lom {
                   type empty;
                   description
                     "Loss of multi-frame alarm";
                 }
                 leaf optics-alarms-otu-bdi {
                   type empty;
                   description
                     "Backward defect indiacation alarm";
                 }
                 leaf optics-alarms-rmsf {
                   type empty;
                   description
                     "Rx Modem sysnc fault alarm";
                 }
                 leaf optics-alarms-rmlol {
                   type empty;
                   description
                     "Rx Modem loss of lock alarm";
                 }
                 leaf optics-alarms-rloa {
                   type empty;
                   description
                     "Rx loss of alignment alarm";
                 }
                 leaf optics-alarms-mbclf {
                   type empty;
                   description
                     "Modulator Bias control loop fail alarm";
                 }
                 leaf optics-alarms-itlaf {
                   type empty;
                   description
                     "ITLA Fault alarm";
                 }
                 leaf optics-alarms-daccf {
                   type empty;
                   description
                     "DAC Calibration Fault alarm";
                 }
                 leaf optics-alarms-adccf {
                   type empty;
                   description
                     "ADC Calibration Fault alarm";
                 }
                 leaf optics-alarms-fec-degrade {
                   type empty;
                   description
                     "FEC Degrade alarm";
                 }
                 leaf optics-alarms-fec-excessive {
                   type empty;
                   description
                     "FEC Excessive alarm";
                 }
                 leaf optics-alarms-fe-fec-degrade {
                   type empty;
                   description
                     "Far-end FEC Degrade alarm";
                 }
                 leaf optics-alarms-fe-fec-excessive {
                   type empty;
                   description
                     "Far-end FEC Excessive alarm";
                 }
                 leaf ima-alarm-startup-fe {
                   type empty;
                   description
                     "IMA group startup far-end alarm";
                 }
                 leaf ima-alarm-config-abort {
                   type empty;
                   description
                     "IMA group config abort alarm";
                 }
                 leaf ima-alarm-config-abort-fe {
                   type empty;
                   description
                     "IMA group config abort far-end alarm";
                 }
                 leaf ima-alarm-insufficient-links {
                   type empty;
                   description
                     "IMA group insufficient links alarm";
                 }
                 leaf ima-alarm-insufficient-links-fe {
                   type empty;
                   description
                     "IMA group insufficient links far-end alarm";
                 }
                 leaf ima-alarm-blocked {
                   type empty;
                   description
                     "IMA group blocked alarm";
                 }
                 leaf ima-alarm-blocked-fe {
                   type empty;
                   description
                     "IMA group blocked far-end alarm";
                 }
                 leaf ima-alarm-timing-mismatch {
                   type empty;
                   description
                     "IMA group timing mismatch alarm";
                 }
                 leaf ima-alarm-version-mismatch {
                   type empty;
                   description
                     "IMA group version mismatch alarm";
                 }
                 leaf ima-alarm-lif {
                   type empty;
                   description
                     "IMA link loss of IMA frame alarm";
                 }
                 leaf ima-alarm-lods {
                   type empty;
                   description
                     "IMA link out of delay synchronization alarm";
                 }
                 leaf ima-alarm-rdi {
                   type empty;
                   description
                     "IMA link remote defect indicator alarm";
                 }
                 leaf ima-alarm-tx-misconnected {
                   type empty;
                   description
                     "IMA link tx misconnected alarm";
                 }
                 leaf ima-alarm-rx-misconnected {
                   type empty;
                   description
                     "IMA link rx misconnected alarm";
                 }
                 leaf ima-alarm-fault {
                   type empty;
                   description
                     "IMA link fault alarm";
                 }
                 leaf ima-alarm-tx-unusable-fe {
                   type empty;
                   description
                     "IMA link Tx unusable far-end alarm";
                 }
                 leaf ima-alarm-rx-unusable-fe {
                   type empty;
                   description
                     "IMA link Tx unusable far-end alarm";
                 }
                 leaf generic-value {
                   type int32;
                   description
                     "Hexadecimal value of unknown flag bits";
                 }
               }
             }
             container active-defects {
               leaf type {
                 type string;
                 description
                   "Media type for associated interface alarms";
               }
               container interface-alarms {
                 description
                   "Container tag for interface alarms";
                 leaf alarm-not-present {
                   type empty;
                   description
                     "No alarm indicated";
                 }
                 leaf sonet-alarm-lol {
                   type empty;
                   description
                     "Loss of light alarm";
                 }
                 leaf sonet-alarm-pll {
                   type empty;
                   description
                     "PLL lock alarm";
                 }
                 leaf sonet-alarm-lof {
                   type empty;
                   description
                     "Loss of frame alarm";
                 }
                 leaf sonet-alarm-los {
                   type empty;
                   description
                     "Loss of signal alarm";
                 }
                 leaf sonet-alarm-sef {
                   type empty;
                   description
                     "Severely errored frame alarm";
                 }
                 leaf sonet-alarm-lais {
                   type empty;
                   description
                     "Line AIS alarm";
                 }
                 leaf sonet-alarm-pais {
                   type empty;
                   description
                     "Path AIS alarm";
                 }
                 leaf sonet-alarm-lop {
                   type empty;
                   description
                     "Loss of pointer alarm";
                 }
                 leaf sonet-alarm-berr-sd {
                   type empty;
                   description
                     "Bit error rate alarm, defect";
                 }
                 leaf sonet-alarm-berr-sf {
                   type empty;
                   description
                     "Bit error rate alarm, fault";
                 }
                 leaf sonet-alarm-lrdi {
                   type empty;
                   description
                     "Line remote defect indicator alarm";
                 }
                 leaf sonet-alarm-prdi {
                   type empty;
                   description
                     "Path remote defect indicator alarm";
                 }
                 leaf sonet-alarm-rei {
                   type empty;
                   description
                     "Path remote error indicator alarm";
                 }
                 leaf sonet-alarm-uneq {
                   type empty;
                   description
                     "Unequipped alarm";
                 }
                 leaf sonet-alarm-pmis {
                   type empty;
                   description
                     "Path payload level mismatch alarm";
                 }
                 leaf sonet-alarm-loc {
                   type empty;
                   description
                     "Loss of cell delineation alarm";
                 }
                 leaf sonet-alarm-vais {
                   type empty;
                   description
                     "VT AIS alarm";
                 }
                 leaf sonet-alarm-vlop {
                   type empty;
                   description
                     "VT loss of pointer alarm";
                 }
                 leaf sonet-alarm-vrdi {
                   type empty;
                   description
                     "VT remote defect indicator alarm";
                 }
                 leaf sonet-alarm-vuneq {
                   type empty;
                   description
                     "VT unequipped alarm";
                 }
                 leaf sonet-alarm-vmis {
                   type empty;
                   description
                     "VT label mismatch alarm";
                 }
                 leaf sonet-alarm-vloc {
                   type empty;
                   description
                     "VT loss of cell delineation alarm";
                 }
                 leaf sdh-alarm-lol {
                   type empty;
                   description
                     "Loss of light alarm";
                 }
                 leaf sdh-alarm-pll {
                   type empty;
                   description
                     "PLL lock alarm";
                 }
                 leaf sdh-alarm-lof {
                   type empty;
                   description
                     "Loss of frame alarm";
                 }
                 leaf sdh-alarm-los {
                   type empty;
                   description
                     "Loss of signal alarm";
                 }
                 leaf sdh-alarm-oof {
                   type empty;
                   description
                     "Out of frame alarm";
                 }
                 leaf sdh-alarm-msais {
                   type empty;
                   description
                     "Multiplex section AIS alarm";
                 }
                 leaf sdh-alarm-hpais {
                   type empty;
                   description
                     "High order path AIS alarm";
                 }
                 leaf sdh-alarm-lop {
                   type empty;
                   description
                     "Loss of pointer alarm";
                 }
                 leaf sdh-alarm-berr-sd {
                   type empty;
                   description
                     "Bit error rate alarm, defect";
                 }
                 leaf sdh-alarm-berr-sf {
                   type empty;
                   description
                     "Bit error rate alarm, fault";
                 }
                 leaf sdh-alarm-msferf {
                   type empty;
                   description
                     "Multiplex section far-end remote failure alarm";
                 }
                 leaf sdh-alarm-hpferf {
                   type empty;
                   description
                     "High order path far-end remote failure alarm";
                 }
                 leaf sdh-alarm-hpfebe {
                   type empty;
                   description
                     "High order path far-end block error alarm";
                 }
                 leaf sdh-alarm-hpuneq {
                   type empty;
                   description
                     "High order path unequipped alarm";
                 }
                 leaf sdh-alarm-hpplm {
                   type empty;
                   description
                     "High order path payload level mismatch alarm";
                 }
                 leaf sdh-alarm-loc {
                   type empty;
                   description
                     "Loss of cell delineation alarm";
                 }
                 leaf sdh-alarm-tuais {
                   type empty;
                   description
                     "TU AIS alarm";
                 }
                 leaf sdh-alarm-tulop {
                   type empty;
                   description
                     "TU loss of pointer alarm";
                 }
                 leaf sdh-alarm-turdi {
                   type empty;
                   description
                     "TU remote defect indicator alarm";
                 }
                 leaf sdh-alarm-tuuneq {
                   type empty;
                   description
                     "TU unequipped alarm";
                 }
                 leaf sdh-alarm-tumis {
                   type empty;
                   description
                     "TU label mismatch error";
                 }
                 leaf sdh-alarm-tuloc {
                   type empty;
                   description
                     "TU loss of cell delineation alarm";
                 }
                 leaf ds3-alarm-pll {
                   type empty;
                   description
                     "PLL lock alarm";
                 }
                 leaf ds3-alarm-ais {
                   type empty;
                   description
                     "AIS alarm";
                 }
                 leaf ds3-alarm-lof {
                   type empty;
                   description
                     "Loss of frame alarm";
                 }
                 leaf ds3-alarm-los {
                   type empty;
                   description
                     "Loss of signal alarm";
                 }
                 leaf ds3-alarm-lcv {
                   type empty;
                   description
                     "Line code violation alarm";
                 }
                 leaf ds3-alarm-exz {
                   type empty;
                   description
                     "Excessive zeros alarm";
                 }
                 leaf ds3-alarm-ferf {
                   type empty;
                   description
                     "Far-end receive failure alarm";
                 }
                 leaf ds3-alarm-ylw {
                   type empty;
                   description
                     "Yellow alarm";
                 }
                 leaf ds3-alarm-idle {
                   type empty;
                   description
                     "Idle alarm";
                 }
                 leaf ds1-alarm-ais {
                   type empty;
                   description
                     "AIS alarm";
                 }
                 leaf ds1-alarm-lof {
                   type empty;
                   description
                     "Loss of frame alarm";
                 }
                 leaf ds1-alarm-los {
                   type empty;
                   description
                     "Loss of signal alarm";
                 }
                 leaf ds1-alarm-ylw {
                   type empty;
                   description
                     "Yellow alarm";
                 }
                 leaf ds1-alarm-crc-major {
                   type empty;
                   description
                     "CRC errors crossed major threshold";
                 }
                 leaf ds1-alarm-crc-minor {
                   type empty;
                   description
                     "CRC errors crossed minor threshold";
                 }
                 leaf dsl-alarm-lof {
                   type empty;
                   description
                     "Loss of frame alarm";
                 }
                 leaf dsl-alarm-los {
                   type empty;
                   description
                     "Loss of signal alarm";
                 }
                 leaf dsl-alarm-lom {
                   type empty;
                   description
                     "Loss of multiframe alarm";
                 }
                 leaf dsl-alarm-locdi {
                   type empty;
                   description
                     "Loss of cell delineation alarm for interleaved channel";
                 }
                 leaf dsl-alarm-locdni {
                   type empty;
                   description
                     "Loss of cell delineation alarm for non-interleaved 
                     channel";
                 }
                 leaf dsl-alarm-lop {
                   type empty;
                   description
                     "Loss of power alarm";
                 }
                 leaf dsl-alarm-far-lof {
                   type empty;
                   description
                     "Far-end loss-of-frame alarm";
                 }
                 leaf dsl-alarm-far-los {
                   type empty;
                   description
                     "Far-end loss-of-signal alarm";
                 }
                 leaf dsl-alarm-far-locdi {
                   type empty;
                   description
                     "Far-end loss-of-cell-delineation alarm for interleaved
                     channel";
                 }
                 leaf dsl-alarm-far-locdni {
                   type empty;
                   description
                     "Far-end loss-of-cell-delineation alarm for 
                     non-interleaved channel";
                 }
                 leaf fibrechannel-alarm-link-down {
                   type empty;
                   description
                     "Link alive failure";
                 }
                 leaf ethernet-alarm-link-down {
                   type empty;
                   description
                     "Link alive failure";
                 }
                 leaf ethernet-alarm-link-local-fault {
                   type empty;
                   description
                     "Link local fault";
                 }
                 leaf ethernet-alarm-link-remote-fault {
                   type empty;
                   description
                     "Link remote fault";
                 }
                 leaf ethernet-alarm-lcdp {
                   type empty;
                   description
                     "Loss of code-group delineation";
                 }
                 leaf isdn-alarm-los {
                   type empty;
                   description
                     "Loss of signal alarm";
                 }
                 leaf isdn-alarm-lof {
                   type empty;
                   description
                     "Loss of frame alarm";
                 }
                 leaf shdsl-alarm-losd {
                   type empty;
                   description
                     "Loss of signal alarm";
                 }
                 leaf shdsl-alarm-losw {
                   type empty;
                   description
                     "Loss of sync word alarm";
                 }
                 leaf shdsl-alarm-line1-losd {
                   type empty;
                   description
                     "Loss of signal (line 1) alarm";
                 }
                 leaf shdsl-alarm-line1-losw {
                   type empty;
                   description
                     "Loss of sync word (line 1) alarm";
                 }
                 leaf shdsl-alarm-line2-losd {
                   type empty;
                   description
                     "Loss of signal (line 2) alarm";
                 }
                 leaf shdsl-alarm-line2-losw {
                   type empty;
                   description
                     "Loss of sync word (line 2) alarm";
                 }
                 leaf shdsl-efm-alarm-losd {
                   type empty;
                   description
                     "Loss of signal alarm";
                 }
                 leaf shdsl-efm-alarm-losw {
                   type empty;
                   description
                     "Loss of sync word alarm";
                 }
                 leaf otn-alarm-los {
                   type empty;
                   description
                     "Loss of signal alarm";
                 }
                 leaf otn-alarm-lof {
                   type empty;
                   description
                     "Loss of frame alarm";
                 }
                 leaf otn-alarm-lom {
                   type empty;
                   description
                     "Loss of multiframe alarm";
                 }
                 leaf otn-alarm-wavelength-lock {
                   type empty;
                   description
                     "Loss of Wavelength Lock alarm";
                 }
                 leaf otn-alarm-otu-ais {
                   type empty;
                   description
                     "OTU Alarm Indication Signal alarm";
                 }
                 leaf otn-alarm-otu-bdi {
                   type empty;
                   description
                     "OTU Background Block Error alarm";
                 }
                 leaf otn-alarm-otu-ttim {
                   type empty;
                   description
                     "OTU Trail Trace Identifier Mismatch alarm";
                 }
                 leaf otn-alarm-otu-iae {
                   type empty;
                   description
                     "OTU Incoming Alignment alarm";
                 }
                 leaf otn-alarm-otu-sd {
                   type empty;
                   description
                     "OTU Signal Degrade alarm";
                 }
                 leaf otn-alarm-otu-sf {
                   type empty;
                   description
                     "OTU Signal Fail alarm";
                 }
                 leaf otn-alarm-otu-biae {
                   type empty;
                   description
                     "OTU Backward Incoming Alignment alarm";
                 }
                 leaf otn-alarm-otu-tsf {
                   type empty;
                   description
                     "OTU Trail Signal Fail alarm";
                 }
                 leaf otn-alarm-otu-ssf {
                   type empty;
                   description
                     "OTU Server Signal Fail alarm";
                 }
                 leaf otn-alarm-otu-fec-excessive {
                   type empty;
                   description
                     "OTU FEC Excessive alarm";
                 }
                 leaf otn-alarm-otu-fec-degraded {
                   type empty;
                   description
                     "OTU FEC Degraded alarm";
                 }
                 leaf otn-alarm-otu-fe-fec-degraded {
                   type empty;
                   description
                     "OTU FE FEC Degraded/Excessive alarm";
                 }
                 leaf otn-alarm-otu-threshold-bbe {
                   type empty;
                   description
                     "OTU Background Block Error threshold alarm";
                 }
                 leaf otn-alarm-otu-threshold-es {
                   type empty;
                   description
                     "OTU Errored Seconds threshold alarm";
                 }
                 leaf otn-alarm-otu-threshold-ses {
                   type empty;
                   description
                     "OTU Severely Errored Seconds threshold alarm";
                 }
                 leaf otn-alarm-otu-threshold-uas {
                   type empty;
                   description
                     "OTU Unavailable Seconds threshold alarm";
                 }
                 leaf otn-alarm-odu-ais {
                   type empty;
                   description
                     "ODU  Alarm Indiaction Signal alarm";
                 }
                 leaf otn-alarm-odu-oci {
                   type empty;
                   description
                     "ODU Open Connection Indication alarm";
                 }
                 leaf otn-alarm-odu-lck {
                   type empty;
                   description
                     "ODU Locked alarm";
                 }
                 leaf otn-alarm-odu-bdi {
                   type empty;
                   description
                     "ODU Backward Defect Indication alarm";
                 }
                 leaf otn-alarm-odu-ttim {
                   type empty;
                   description
                     "ODU Trail Trace Identifier Mismatch alarm";
                 }
                 leaf otn-alarm-odu-sd {
                   type empty;
                   description
                     "ODU Signal Degrade alarm";
                 }
                 leaf otn-alarm-odu-sf {
                   type empty;
                   description
                     "ODU Signal Fail alarm";
                 }
                 leaf otn-alarm-odu-iae {
                   type empty;
                   description
                     "ODU Incoming Alignment alarm";
                 }
                 leaf otn-alarm-odu-ltc {
                   type empty;
                   description
                     "ODU Loss of Tandem Connection alarm";
                 }
                 leaf otn-alarm-odu-csf {
                   type empty;
                   description
                     "ODU Client Signal Fail alarm";
                 }
                 leaf otn-alarm-odu-tsf {
                   type empty;
                   description
                     "ODU Trail Signal Fail alarm";
                 }
                 leaf otn-alarm-odu-ssf {
                   type empty;
                   description
                     "ODU Server Signal Fail alarm";
                 }
                 leaf otn-alarm-odu-rx-aps-change {
                   type empty;
                   description
                     "ODU Rx Aps Change alarm";
                 }
                 leaf otn-alarm-odu-threshold-bbe {
                   type empty;
                   description
                     "ODU Background Block Error threshold alarm";
                 }
                 leaf otn-alarm-odu-threshold-es {
                   type empty;
                   description
                     "ODU Errored Seconds threshold alarm";
                 }
                 leaf otn-alarm-odu-threshold-ses {
                   type empty;
                   description
                     "ODU Severely Errored Seconds threshold alarm";
                 }
                 leaf otn-alarm-odu-threshold-uas {
                   type empty;
                   description
                     "ODU Unavailable Seconds threshold alarm";
                 }
                 leaf otn-alarm-opu-pmi {
                   type empty;
                   description
                     "OPU Payload Mismatch alarm";
                 }
                 leaf otn-alarm-pre-fec-sd {
                   type empty;
                   description
                     "Pre-FEC SD alarm";
                 }
                 leaf otn-alarm-fe-pre-fec-sd {
                   type empty;
                   description
                     "Far end pre-FEC SD alarm";
                 }
                 leaf optics-alarms-mod-fault {
                   type empty;
                   description
                     "Module Fault alarm";
                 }
                 leaf optics-alarms-lol {
                   type empty;
                   description
                     "Loss of Lock alarm";
                 }
                 leaf optics-alarms-los {
                   type empty;
                   description
                     "Loss of Signal alarms";
                 }
                 leaf optics-alarms-lof {
                   type empty;
                   description
                     "Loss of frame alarm";
                 }
                 leaf optics-alarms-lom {
                   type empty;
                   description
                     "Loss of multi-frame alarm";
                 }
                 leaf optics-alarms-otu-bdi {
                   type empty;
                   description
                     "Backward defect indiacation alarm";
                 }
                 leaf optics-alarms-rmsf {
                   type empty;
                   description
                     "Rx Modem sysnc fault alarm";
                 }
                 leaf optics-alarms-rmlol {
                   type empty;
                   description
                     "Rx Modem loss of lock alarm";
                 }
                 leaf optics-alarms-rloa {
                   type empty;
                   description
                     "Rx loss of alignment alarm";
                 }
                 leaf optics-alarms-mbclf {
                   type empty;
                   description
                     "Modulator Bias control loop fail alarm";
                 }
                 leaf optics-alarms-itlaf {
                   type empty;
                   description
                     "ITLA Fault alarm";
                 }
                 leaf optics-alarms-daccf {
                   type empty;
                   description
                     "DAC Calibration Fault alarm";
                 }
                 leaf optics-alarms-adccf {
                   type empty;
                   description
                     "ADC Calibration Fault alarm";
                 }
                 leaf optics-alarms-fec-degrade {
                   type empty;
                   description
                     "FEC Degrade alarm";
                 }
                 leaf optics-alarms-fec-excessive {
                   type empty;
                   description
                     "FEC Excessive alarm";
                 }
                 leaf optics-alarms-fe-fec-degrade {
                   type empty;
                   description
                     "Far-end FEC Degrade alarm";
                 }
                 leaf optics-alarms-fe-fec-excessive {
                   type empty;
                   description
                     "Far-end FEC Excessive alarm";
                 }
                 leaf ima-alarm-startup-fe {
                   type empty;
                   description
                     "IMA group startup far-end alarm";
                 }
                 leaf ima-alarm-config-abort {
                   type empty;
                   description
                     "IMA group config abort alarm";
                 }
                 leaf ima-alarm-config-abort-fe {
                   type empty;
                   description
                     "IMA group config abort far-end alarm";
                 }
                 leaf ima-alarm-insufficient-links {
                   type empty;
                   description
                     "IMA group insufficient links alarm";
                 }
                 leaf ima-alarm-insufficient-links-fe {
                   type empty;
                   description
                     "IMA group insufficient links far-end alarm";
                 }
                 leaf ima-alarm-blocked {
                   type empty;
                   description
                     "IMA group blocked alarm";
                 }
                 leaf ima-alarm-blocked-fe {
                   type empty;
                   description
                     "IMA group blocked far-end alarm";
                 }
                 leaf ima-alarm-timing-mismatch {
                   type empty;
                   description
                     "IMA group timing mismatch alarm";
                 }
                 leaf ima-alarm-version-mismatch {
                   type empty;
                   description
                     "IMA group version mismatch alarm";
                 }
                 leaf ima-alarm-lif {
                   type empty;
                   description
                     "IMA link loss of IMA frame alarm";
                 }
                 leaf ima-alarm-lods {
                   type empty;
                   description
                     "IMA link out of delay synchronization alarm";
                 }
                 leaf ima-alarm-rdi {
                   type empty;
                   description
                     "IMA link remote defect indicator alarm";
                 }
                 leaf ima-alarm-tx-misconnected {
                   type empty;
                   description
                     "IMA link tx misconnected alarm";
                 }
                 leaf ima-alarm-rx-misconnected {
                   type empty;
                   description
                     "IMA link rx misconnected alarm";
                 }
                 leaf ima-alarm-fault {
                   type empty;
                   description
                     "IMA link fault alarm";
                 }
                 leaf ima-alarm-tx-unusable-fe {
                   type empty;
                   description
                     "IMA link Tx unusable far-end alarm";
                 }
                 leaf ima-alarm-rx-unusable-fe {
                   type empty;
                   description
                     "IMA link Tx unusable far-end alarm";
                 }
                 leaf generic-value {
                   type int32;
                   description
                     "Hexadecimal value of unknown flag bits";
                 }
               }
             }
             container sonet-errors {
               list media-alarm {
                 leaf media-alarm-name {
                   type string;
                 }
                 leaf media-alarm-count {
                   type int32;
                 }
               }
             }
             container sonet-physical-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-section-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-line-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-path-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-payload-pointer-information {
               leaf sonet-payload-pointer-curptr {
                 type string;
                 description
                   "Value of the SONET/SDH payload pointer, derived from the
                   H1 and H2 overhead bytes";
               }
               leaf sonet-payload-pointer-ptrinc-count {
                 type string;
                 description
                   "Number of times the value of the SONET/SDH payload 
                   pointer had positive justification";
               }
               leaf sonet-payload-pointer-ptrdec-count {
                 type string;
                 description
                   "Number of times the value of the SONET/SDH payload 
                   pointer had negative justification";
               }
               leaf sonet-payload-pointer-newptr-ndf-count {
                 type string;
                 description
                   "Number of times a new payload pointer was created with 
                   the New Data Found flag set";
               }
             }
             container sonet-vt-information {
               list media-alarm {
                 leaf media-alarm-name {
                   type string;
                 }
                 leaf media-alarm-seconds {
                   type int32;
                 }
                 leaf media-alarm-count {
                   type int32;
                 }
                 leaf media-alarm-state {
                   type string;
                 }
               }
             }
             list optics-diagnostics {
               description
                 "Optics diagnostics";
               leaf optic-diagnostics-not-available {
                 type string;
                 description
                   "Optical diagnostics not supported by this transceiver";
               }
               leaf laser-bias-current-not-available {
                 type string;
                 description
                   "Laser bias current measurement not available";
               }
               leaf soa-bias-current-not-available {
                 type string;
                 description
                   "SOA bias current measurement not available";
               }
               leaf laser-tx-power-not-available {
                 type string;
                 description
                   "Laser output power measurement not available";
               }
               leaf module-temperature-not-available {
                 type string;
                 description
                   "Module temperature measurement not available";
               }
               leaf tx-module-temperature-not-available {
                 type string;
                 description
                   "Tx module temperature measurement not available";
               }
               leaf rx-module-temperature-not-available {
                 type string;
                 description
                   "Rx module temperature measurement not available";
               }
               leaf laser-rx-power-not-available {
                 type string;
                 description
                   "Laser receiver optical power measurement not available";
               }
               leaf laser-tx-power-high-alarm-threshold-not-available {
                 type string;
                 description
                   "Laser output power high alarm threshold not available";
               }
               leaf laser-tx-power-low-alarm-threshold-not-available {
                 type string;
                 description
                   "Laser output power low alarm threshold not available";
               }
               leaf laser-tx-power-high-warning-threshold-not-available {
                 type string;
                 description
                   "Laser output power high warning threshold not available";
               }
               leaf laser-tx-power-low-warning-threshold-not-available {
                 type string;
                 description
                   "Laser output power low warning threshold not available";
               }
               leaf laser-bias-current {
                 type string;
                 description
                   "Laser bias current (milliamperes)";
               }
               leaf soa-bias-current {
                 type string;
                 description
                   "SOA bias current (milliamperes)";
               }
               leaf laser-output-power {
                 type string;
                 description
                   "Laser output power (milliwatts)";
               }
               leaf laser-output-power-dbm {
                 type string;
                 description
                   "Laser output power (dBm)";
               }
               leaf module-temperature {
                 type string;
                 description
                   "Module temperature";
               }
               leaf tx-module-temperature {
                 type string;
                 description
                   "Tx module temperature";
               }
               leaf rx-module-temperature {
                 type string;
                 description
                   "Rx module temperature";
               }
               leaf module-voltage {
                 type string;
                 description
                   "Module voltage";
               }
               leaf corrected-error-ratio {
                 type string;
                 description
                   "Corrected error ratio";
               }
               leaf uncorrected-words-ratio {
                 type string;
                 description
                   "Uncorrected words ratio";
               }
               leaf tx-module-voltage {
                 type string;
                 description
                   "Tx module voltage";
               }
               leaf rx-module-voltage {
                 type string;
                 description
                   "Rx module voltage";
               }
               leaf rx-signal-avg-optical-power {
                 type string;
                 description
                   "Receiver signal average power (milliwatts)";
               }
               leaf rx-signal-avg-optical-power-dbm {
                 type string;
                 description
                   "Receiver signal average power (dBm)";
               }
               leaf laser-rx-optical-power {
                 type string;
                 description
                   "Laser receiver optical power (milliwatts)";
               }
               leaf laser-rx-optical-power-dbm {
                 type string;
                 description
                   "Laser receiver optical power (dBm)";
               }
               leaf wavelength-channel {
                 type string;
                 description
                   "Wavelength channel number set";
               }
               leaf wavelength-setpoint {
                 type string;
                 description
                   "Wavelength point set";
               }
               leaf tx-dither {
                 type string;
                 description
                   "Tx dither status";
               }
               leaf frequency-error {
                 type string;
                 description
                   "Frequency error value";
               }
               leaf wavelength-error {
                 type string;
                 description
                   "Wavelength error value";
               }
               leaf laser-bias-current-high-alarm {
                 type string;
                 description
                   "Laser bias current high alarm";
               }
               leaf laser-bias-current-low-alarm {
                 type string;
                 description
                   "Laser bias current low alarm";
               }
               leaf laser-bias-current-high-warn {
                 type string;
                 description
                   "Laser bias current high warning";
               }
               leaf laser-bias-current-low-warn {
                 type string;
                 description
                   "Laser bias current low warning";
               }
               leaf soa-bias-current-high-alarm {
                 type string;
                 description
                   "SOA bias current high alarm";
               }
               leaf soa-bias-current-low-alarm {
                 type string;
                 description
                   "SOA bias current low alarm";
               }
               leaf soa-bias-current-high-warn {
                 type string;
                 description
                   "SOA bias current high warning";
               }
               leaf soa-bias-current-low-warn {
                 type string;
                 description
                   "SOA bias current low warning";
               }
               leaf laser-tx-power-high-alarm {
                 type string;
                 description
                   "Laser output power high alarm";
               }
               leaf laser-tx-power-low-alarm {
                 type string;
                 description
                   "Laser output power low alarm";
               }
               leaf laser-tx-power-high-warn {
                 type string;
                 description
                   "Laser output power high warning";
               }
               leaf laser-tx-power-low-warn {
                 type string;
                 description
                   "Laser output power low warning";
               }
               leaf tx-power-high-alarm {
                 type string;
                 description
                   "Tx power high alarm";
               }
               leaf tx-power-low-alarm {
                 type string;
                 description
                   "Tx power low alarm";
               }
               leaf tx-power-high-warn {
                 type string;
                 description
                   "Tx power high warning";
               }
               leaf tx-power-low-warn {
                 type string;
                 description
                   "Tx power low warning";
               }
               leaf module-temperature-high-alarm {
                 type string;
                 description
                   "Module temperature high alarm";
               }
               leaf module-temperature-low-alarm {
                 type string;
                 description
                   "Module temperature low alarm";
               }
               leaf module-temperature-high-warn {
                 type string;
                 description
                   "Module temperature high warning";
               }
               leaf module-temperature-low-warn {
                 type string;
                 description
                   "Module temperature low warning";
               }
               leaf tx-module-temperature-high-alarm {
                 type string;
                 description
                   "Tx module temperature high alarm";
               }
               leaf tx-module-temperature-low-alarm {
                 type string;
                 description
                   "Tx module temperature low alarm";
               }
               leaf rx-module-temperature-high-alarm {
                 type string;
                 description
                   "Rx module temperature high alarm";
               }
               leaf rx-module-temperature-low-alarm {
                 type string;
                 description
                   "Rx module temperature low alarm";
               }
               leaf module-voltage-high-alarm {
                 type string;
                 description
                   "Module voltage high alarm";
               }
               leaf module-voltage-low-alarm {
                 type string;
                 description
                   "Module voltage low alarm";
               }
               leaf module-voltage-high-warn {
                 type string;
                 description
                   "Module voltage high warning";
               }
               leaf module-voltage-low-warn {
                 type string;
                 description
                   "Module voltage low warning";
               }
               leaf tx-module-voltage-high-alarm {
                 type string;
                 description
                   "Tx module voltage high alarm";
               }
               leaf tx-module-voltage-low-alarm {
                 type string;
                 description
                   "Tx module voltage low alarm";
               }
               leaf rx-module-voltage-high-alarm {
                 type string;
                 description
                   "Rx module voltage high alarm";
               }
               leaf rx-module-voltage-low-alarm {
                 type string;
                 description
                   "Rx module voltage low alarm";
               }
               leaf laser-rx-power-high-alarm {
                 type string;
                 description
                   "Laser receiver power high alarm";
               }
               leaf laser-rx-power-low-alarm {
                 type string;
                 description
                   "Laser receiver power low alarm";
               }
               leaf laser-rx-power-high-warn {
                 type string;
                 description
                   "Laser receiver power high warning";
               }
               leaf laser-rx-power-low-warn {
                 type string;
                 description
                   "Laser receiver power low warning";
               }
               leaf rx-power-high-alarm {
                 type string;
                 description
                   "Receiver power high alarm";
               }
               leaf rx-power-low-alarm {
                 type string;
                 description
                   "Receiver power low alarm";
               }
               leaf rx-power-high-warn {
                 type string;
                 description
                   "Receiver power high warning";
               }
               leaf rx-power-low-warn {
                 type string;
                 description
                   "Receiver power low warning";
               }
               leaf laser-end-of-life-alarm {
                 type string;
                 description
                   "Laser end-of-life alarm";
               }
               leaf laser-wavelength-alarm {
                 type string;
                 description
                   "Laser wavelength alarm";
               }
               leaf laser-bias-current-alarm {
                 type string;
                 description
                   "Laser bias current alarm";
               }
               leaf module-temperature-alarm {
                 type string;
                 description
                   "Module temperature alarm";
               }
               leaf laser-power-alarm {
                 type string;
                 description
                   "Laser power alarm";
               }
               leaf modulator-temperature-alarm {
                 type string;
                 description
                   "Modulator temperature alarm";
               }
               leaf modulator-bias-alarm {
                 type string;
                 description
                   "Modulator bias alarm";
               }
               leaf module-not-ready-alarm {
                 type string;
                 description
                   "Module not ready alarm";
               }
               leaf module-power-down-alarm {
                 type string;
                 description
                   "Module power down alarm";
               }
               leaf module-not-init-done-alarm {
                 type string;
                 description
                   "Module initialization not done alarm";
               }
               leaf module-not-high-power-on-alarm {
                 type string;
                 description
                   "Module not high powered on alarm";
               }
               leaf module-fault-alarm {
                 type string;
                 description
                   "Module in fault state alarm";
               }
               leaf pld-flash-init-fault-alarm {
                 type string;
                 description
                   "PLD or Flash initialization fault alarm";
               }
               leaf power-supply-fault-alarm {
                 type string;
                 description
                   "Power supply fault alarm";
               }
               leaf checksum-fault-alarm {
                 type string;
                 description
                   "Checksum fault alarm";
               }
               leaf apd-supply-fault-alarm {
                 type string;
                 description
                   "APD supply fault alarm";
               }
               leaf tec-fault-alarm {
                 type string;
                 description
                   "TEC fault alarm";
               }
               leaf wavelength-unlocked-alarm {
                 type string;
                 description
                   "Wavelength unlocked alarm";
               }
               leaf tx-tune-alarm {
                 type string;
                 description
                   "Tx tune alarm";
               }
               leaf tx-mux-fifo-error-alarm {
                 type string;
                 description
                   "Tx multiplexer fifo error alarm";
               }
               leaf tx-loss-of-pll-alarm {
                 type string;
                 description
                   "Tx loss of PLL alarm";
               }
               leaf tx-data-not-ready-alarm {
                 type string;
                 description
                   "Tx data not ready alarm";
               }
               leaf tx-not-ready-alarm {
                 type string;
                 description
                   "Tx not ready alarm";
               }
               leaf tx-laser-fault-alarm {
                 type string;
                 description
                   "Tx laser fault alarm";
               }
               leaf tx-laser-disabled-alarm {
                 type string;
                 description
                   "Tx laser disabled alarm";
               }
               leaf tx-loss-of-signal-functionality-alarm {
                 type string;
                 description
                   "Tx loss of signal functionality alarm";
               }
               leaf tx-cdr-loss-of-lock-alarm {
                 type string;
                 description
                   "Tx CDR loss of lock alarm";
               }
               leaf rx-loss-avg-opt-power-alarm {
                 type string;
                 description
                   "Receiver loss of average optical power alarm";
               }
               leaf rx-loss-ac-power-alarm {
                 type string;
                 description
                   "Receiver loss of AC power alarm";
               }
               leaf rx-loss-of-pll-alarm {
                 type string;
                 description
                   "Receiver loss of PLL alarm";
               }
               leaf rx-not-ready-alarm {
                 type string;
                 description
                   "Receiver not ready alarm";
               }
               leaf rx-loss-of-signal-alarm {
                 type string;
                 description
                   "Receiver loss of signal alarm";
               }
               leaf rx-cdr-loss-of-lock-alarm {
                 type string;
                 description
                   "Receiver CDR loss of lock alarm";
               }
               leaf laser-bias-current-high-alarm-threshold {
                 type string;
                 description
                   "Laser bias current high alarm threshold (milliamperes)";
               }
               leaf laser-bias-current-low-alarm-threshold {
                 type string;
                 description
                   "Laser bias current low alarm threshold (milliamperes)";
               }
               leaf laser-bias-current-high-warn-threshold {
                 type string;
                 description
                   "Laser bias current high warning threshold (milliamperes)";
               }
               leaf laser-bias-current-low-warn-threshold {
                 type string;
                 description
                   "Laser bias current low warning threshold (milliamperes)";
               }
               leaf soa-bias-current-high-alarm-threshold {
                 type string;
                 description
                   "SOA bias current high alarm threshold (milliamperes)";
               }
               leaf soa-bias-current-low-alarm-threshold {
                 type string;
                 description
                   "SOA bias current low alarm threshold (milliamperes)";
               }
               leaf soa-bias-current-high-warn-threshold {
                 type string;
                 description
                   "SOA bias current high warning threshold (milliamperes)";
               }
               leaf soa-bias-current-low-warn-threshold {
                 type string;
                 description
                   "SOA bias current low warning threshold (milliamperes)";
               }
               leaf laser-tx-power-high-alarm-threshold {
                 type string;
                 description
                   "Laser transmitter power high alarm threshold 
                   (milliwatts)";
               }
               leaf laser-tx-power-high-alarm-threshold-dbm {
                 type string;
                 description
                   "Laser transmitter power high alarm threshold (dBm)";
               }
               leaf laser-tx-power-low-alarm-threshold {
                 type string;
                 description
                   "Laser transmitter power low alarm threshold (milliwatts)";
               }
               leaf laser-tx-power-low-alarm-threshold-dbm {
                 type string;
                 description
                   "Laser transmitter power low alarm threshold (dBm)";
               }
               leaf laser-tx-power-high-warn-threshold {
                 type string;
                 description
                   "Laser transmitter power high warning threshold 
                   (milliwatts)";
               }
               leaf laser-tx-power-high-warn-threshold-dbm {
                 type string;
                 description
                   "Laser transmitter power high warning threshold (dBm)";
               }
               leaf laser-tx-power-low-warn-threshold {
                 type string;
                 description
                   "Laser transmitter power low warning threshold 
                   (milliwatts)";
               }
               leaf laser-tx-power-low-warn-threshold-dbm {
                 type string;
                 description
                   "Laser transmitter power low warning threshold (dBm)";
               }
               leaf module-temperature-high-alarm-threshold {
                 type string;
                 description
                   "Module temperature high alarm threshold";
               }
               leaf module-temperature-low-alarm-threshold {
                 type string;
                 description
                   "Module temperature low alarm threshold";
               }
               leaf module-temperature-high-warn-threshold {
                 type string;
                 description
                   "Module temperature high warning threshold";
               }
               leaf module-temperature-low-warn-threshold {
                 type string;
                 description
                   "Module temperature low warning threshold";
               }
               leaf laser-temperature-high-alarm-threshold {
                 type string;
                 description
                   "Laser temperature high alarm threshold";
               }
               leaf laser-temperature-low-alarm-threshold {
                 type string;
                 description
                   "Laser temperature low alarm threshold";
               }
               leaf laser-temperature-high-warn-threshold {
                 type string;
                 description
                   "Laser temperature high warning threshold";
               }
               leaf laser-temperature-low-warn-threshold {
                 type string;
                 description
                   "Laser temperature low warning threshold";
               }
               leaf module-voltage-high-alarm-threshold {
                 type string;
                 description
                   "Module voltage high alarm threshold (volts)";
               }
               leaf module-voltage-low-alarm-threshold {
                 type string;
                 description
                   "Module voltage low alarm threshold (volts)";
               }
               leaf module-voltage-high-warn-threshold {
                 type string;
                 description
                   "Module voltage high warning threshold (volts)";
               }
               leaf module-voltage-low-warn-threshold {
                 type string;
                 description
                   "Module voltage low warning threshold (volts)";
               }
               leaf laser-rx-power-high-alarm-threshold {
                 type string;
                 description
                   "Laser receiver power high alarm (milliwatts)";
               }
               leaf laser-rx-power-high-alarm-threshold-dbm {
                 type string;
                 description
                   "Laser receiver power high alarm (dBm)";
               }
               leaf laser-rx-power-low-alarm-threshold {
                 type string;
                 description
                   "Laser receiver power low alarm (milliwatts)";
               }
               leaf laser-rx-power-low-alarm-threshold-dbm {
                 type string;
                 description
                   "Laser receiver power low alarm (dBm)";
               }
               leaf laser-rx-power-high-warn-threshold {
                 type string;
                 description
                   "Laser receiver power high warning (milliwatts)";
               }
               leaf laser-rx-power-high-warn-threshold-dbm {
                 type string;
                 description
                   "Laser receiver power high warning (dBm)";
               }
               leaf laser-rx-power-low-warn-threshold {
                 type string;
                 description
                   "Laser receiver power low warning (milliwatts)";
               }
               leaf laser-rx-power-low-warn-threshold-dbm {
                 type string;
                 description
                   "Laser receiver power low warning (dBm)";
               }
               leaf rx-power-high-alarm-threshold {
                 type string;
                 description
                   "Receiver power high alarm (milliwatts)";
               }
               leaf rx-power-high-alarm-threshold-dbm {
                 type string;
                 description
                   "Receiver power high alarm (dBm)";
               }
               leaf rx-power-low-alarm-threshold {
                 type string;
                 description
                   "Receiver power low alarm (milliwatts)";
               }
               leaf rx-power-low-alarm-threshold-dbm {
                 type string;
                 description
                   "Receiver power low alarm (dBm)";
               }
               leaf rx-power-high-warning-threshold {
                 type string;
                 description
                   "Receiver power high warning (milliwatts)";
               }
               leaf rx-power-high-warning-threshold-dbm {
                 type string;
                 description
                   "Receiver power high warning (dBm)";
               }
               leaf rx-power-low-warning-threshold {
                 type string;
                 description
                   "Receiver power low warning (milliwatts)";
               }
               leaf rx-power-low-warning-threshold-dbm {
                 type string;
                 description
                   "Receiver power low warning (dBm)";
               }
               leaf los-alarm-threshold {
                 type string;
                 description
                   "LOS alarm threshold (milliwatts)";
               }
               leaf los-alarm-threshold-dbm {
                 type string;
                 description
                   "LOS alarm threshold (dBm)";
               }
               leaf los-warning-threshold {
                 type string;
                 description
                   "LOS warning threshold (milliwatts)";
               }
               leaf los-warning-threshold-dbm {
                 type string;
                 description
                   "LOS warning threshold (dBm)";
               }
               leaf dsp-module-state {
                 type string;
                 description
                   "DSP module state";
               }
               leaf output-power {
                 type string;
                 description
                   "Output power (milliwatts)";
               }
               leaf output-power-dbm {
                 type string;
                 description
                   "Output power (dBm)";
               }
               leaf input-power {
                 type string;
                 description
                   "Input power (milliwatts)";
               }
               leaf input-power-dbm {
                 type string;
                 description
                   "Input power (dBm)";
               }
               leaf per-wave-rx-optical-power {
                 type string;
                 description
                   "Per-wavelength receiver optical power (milliwatts)";
               }
               leaf per-wave-rx-optical-power-dbm {
                 type string;
                 description
                   "Per-wavelength receiver optical power (dBm)";
               }
               leaf lane-laser-frequency-error {
                 type string;
                 description
                   "Lane laser frequency error (MHz)";
               }
               leaf tec-current {
                 type string;
                 description
                   "Tec current";
               }
               leaf residual-isi {
                 type string;
                 description
                   "Residual ISI";
               }
               container optics-diagnostics-ot {
                 description
                   "OT interface optics diagnostics";
                 leaf module-temp-fault {
                   type string;
                   description
                     "Module temperature fault";
                 }
                 leaf specific-hw-fault {
                   type string;
                   description
                     "Specific HW fault";
                 }
                 leaf internal-power-fault {
                   type string;
                   description
                     "Internal power fault";
                 }
                 leaf post-therm-fault {
                   type string;
                   description
                     "Power thermal fault";
                 }
                 leaf post-fault {
                   type string;
                   description
                     "Post fault";
                 }
                 leaf command-error {
                   type string;
                   description
                     "Command error";
                 }
                 leaf rx-pll-lock {
                   type string;
                   description
                     "RX PLL lock";
                 }
                 leaf network-lane-los {
                   type string;
                   description
                     "Network Lane LOS";
                 }
                 leaf network-lane-lof {
                   type string;
                   description
                     "Network Lane LOF";
                 }
                 leaf network-lane-oof {
                   type string;
                   description
                     "Network Lane OOF";
                 }
                 leaf network-lane-lom {
                   type string;
                   description
                     "Network Lane LOM";
                 }
                 leaf network-lane-oom {
                   type string;
                   description
                     "Network Lane OOM";
                 }
                 leaf network-lane-otu-bdi {
                   type string;
                   description
                     "Network Lane OTU BDI";
                 }
                 leaf lane-rx-fifo-error {
                   type string;
                   description
                     "Lane RX FIFO error";
                 }
                 leaf tx-reference-clock-fault {
                   type string;
                   description
                     "TX reference clock fault";
                 }
                 leaf rx-modem-sync-fault {
                   type string;
                   description
                     "Rx modem sync fault";
                 }
                 leaf rx-modem-loss-of-lock {
                   type string;
                   description
                     "RX modem loss of lock";
                 }
                 leaf rx-loss-of-alignment {
                   type string;
                   description
                     "RX loss of alignment";
                 }
                 leaf rx-out-of-alignment {
                   type string;
                   description
                     "RX out of alignment";
                 }
                 leaf rx-timing-fault {
                   type string;
                   description
                     "Rx timing fault";
                 }
                 leaf link-msg-data-available {
                   type string;
                   description
                     "Link msg data available";
                 }
                 leaf modulator-bias-control-loop-fail {
                   type string;
                   description
                     "Modulator Bias Control Loop Fail";
                 }
                 leaf itla-fault {
                   type string;
                   description
                     "ITLA fault";
                 }
                 leaf dac-calib-fault {
                   type string;
                   description
                     "DAC calib fault";
                 }
                 leaf adc-calib-fault {
                   type string;
                   description
                     "ADC calib fault";
                 }
                 leaf prom-fault {
                   type string;
                   description
                     "PROM fault";
                 }
                 leaf tx-mod-bias-voa-ctrl-loop-high-alarm {
                   type string;
                   description
                     "TX mod bias VOA ctrl loop high alarm";
                 }
                 leaf tx-mod-bias-voa-ctrl-loop-low-alarm {
                   type string;
                   description
                     "TX mod bias VOA ctrl loop low alarm";
                 }
                 leaf rx-phase-control-loop-high-alarm {
                   type string;
                   description
                     "RX phase control loop high alarm";
                 }
                 leaf rx-phase-control-loop-low-alarm {
                   type string;
                   description
                     "RX phase control loop low alarm";
                 }
                 leaf rx-phase-control-loop-high-warning {
                   type string;
                   description
                     "RX phase control loop high warning";
                 }
                 leaf rx-phase-control-loop-low-warning {
                   type string;
                   description
                     "RX phase control loop low warning";
                 }
                 leaf oa-pump-bias-current-high-alarm {
                   type string;
                   description
                     "OA pump bias current high alarm";
                 }
                 leaf oa-pump-bias-current-low-alarm {
                   type string;
                   description
                     "OA pump bias current low alarm";
                 }
                 leaf oa-pump-bias-current-high-warning {
                   type string;
                   description
                     "OA pump bias current high warning";
                 }
                 leaf oa-pump-bias-current-low-warning {
                   type string;
                   description
                     "OA pump bias current low warning";
                 }
                 leaf tx-jitter-pll-lol-input-nw-lane {
                   type string;
                   description
                     "Tx jitter PLL LOL i/p nw lane";
                 }
                 leaf tx-out-of-alignment {
                   type string;
                   description
                     "TX out of alignment";
                 }
                 leaf tx-cmu-lock-fault {
                   type string;
                   description
                     "Tx CMU lock fault";
                 }
                 leaf adc-signal-below-threshold {
                   type string;
                   description
                     "ADC signal below threshold";
                 }
                 leaf tx-output-power-adjustment-fault {
                   type string;
                   description
                     "Tx output power adjustment fault";
                 }
                 leaf tx-output-mod-converge-fault {
                   type string;
                   description
                     "TX output mod converge fault";
                 }
                 leaf tx-laser-ready-fault {
                   type string;
                   description
                     "Tx laser ready fault";
                 }
                 leaf tx-laser-ready-off-fault {
                   type string;
                   description
                     "Tx laser ready off fault";
                 }
                 leaf tx-asic-ready-fault {
                   type string;
                   description
                     "Tx asic ready fault";
                 }
                 leaf tx-initialization-fault {
                   type string;
                   description
                     "Tx initialization fault";
                 }
                 leaf rx-demodulator-lock-fault {
                   type string;
                   description
                     "Rx demodulator lock fault";
                 }
                 leaf rx-dispersion-lock-fault {
                   type string;
                   description
                     "Rx dispersion lock fault";
                 }
                 leaf rx-adc-output-fault {
                   type string;
                   description
                     "Rx ADC output fault";
                 }
                 leaf rx-optical-input-fault {
                   type string;
                   description
                     "Rx optical input fault";
                 }
                 leaf rx-asic-ready-fault {
                   type string;
                   description
                     "Rx asic ready fault";
                 }
                 leaf rx-initialization-fault {
                   type string;
                   description
                     "Rx initialization fault";
                 }
                 leaf tx-mod-bias-high-alarm {
                   type string;
                   description
                     "TX modulator bias high alarm";
                 }
                 leaf tx-mod-bias-low-alarm {
                   type string;
                   description
                     "TX modulator bias low alarm";
                 }
                 leaf tx-mod-bias-high-warning {
                   type string;
                   description
                     "TX modulator bias high warning";
                 }
                 leaf tx-mod-bias-low-warning {
                   type string;
                   description
                     "TX modulator bias low warning";
                 }
                 leaf rx-pwr-high-alarm {
                   type string;
                   description
                     "RX power high alarm";
                 }
                 leaf rx-pwr-low-alarm {
                   type string;
                   description
                     "RX power low alarm";
                 }
                 leaf rx-pwr-high-warn {
                   type string;
                   description
                     "RX power high warning";
                 }
                 leaf rx-pwr-low-warn {
                   type string;
                   description
                     "RX power low warning";
                 }
                 leaf tx-laser-power-high-alarm {
                   type string;
                   description
                     "TX laser power high alarm";
                 }
                 leaf tx-laser-power-low-alarm {
                   type string;
                   description
                     "TX laser power low alarm";
                 }
                 leaf tx-laser-power-high-warn {
                   type string;
                   description
                     "TX laser power high warning";
                 }
                 leaf tx-laser-power-low-warn {
                   type string;
                   description
                     "TX laser power low warning";
                 }
                 leaf tx-bias-high-alarm {
                   type string;
                   description
                     "TX laser current high alarm";
                 }
                 leaf tx-bias-low-alarm {
                   type string;
                   description
                     "TX laser current low alarm";
                 }
                 leaf tx-bias-high-warn {
                   type string;
                   description
                     "TX laser current high warning";
                 }
                 leaf tx-bias-low-warn {
                   type string;
                   description
                     "TX laser current low warning";
                 }
                 leaf tx-laser-temp-high-alarm {
                   type string;
                   description
                     "TX laser temperature high alarm";
                 }
                 leaf tx-laser-temp-low-alarm {
                   type string;
                   description
                     "TX laser temperature low alarm";
                 }
                 leaf tx-laser-temp-high-warn {
                   type string;
                   description
                     "TX laser temperature high warning";
                 }
                 leaf tx-laser-temp-low-warn {
                   type string;
                   description
                     "TX laser temperature low warning";
                 }
               }
             }
             list optics-diagnostics-vendor-extension {
               description
                 "Optics diagnostics vendor extension";
               leaf optics-vendor-part-number {
                 type string;
                 description
                   "Optics component vendor part number";
               }
               leaf optics-vendor-material-number {
                 type string;
                 description
                   "Optic component vendor material number";
               }
             }
           }
         }
         container src-information {
           leaf src-chassis-name {
             type string;
             description
               "Source chassis name";
           }
           leaf src-fpc {
             type int32;
             description
               "Source FPC";
           }
           leaf-list src-pfe-id {
             type int32;
             description
               "Source PFE id";
           }
         }
         container peer-configuration-status {
           description
             "Nonmatching DCE end DLCIs";
           leaf peer-nonmatching-dlci {
             type int32;
             description
               "DCE end DLCIs that does not match the DTE";
           }
         }
         container lmi-statistics {
           description
             "LMI statistics for an interface";
           leaf lmi-statistics-dte-descriptor {
             type string;
             description
               "DTE interface statistics";
           }
           leaf lmi-enquiries-sent {
             type int32;
             description
               "Number of enquiry packets sent";
           }
           leaf lmi-full-enquiries-sent {
             type int32;
             description
               "Number of full enquiry packets sent";
           }
           leaf lmi-enquiry-responses-received {
             type int32;
             description
               "Number of enquiry response packets received";
           }
           leaf lmi-full-enquiry-responses-received {
             type int32;
             description
               "Number of full enquiry packets received";
           }
           leaf lmi-statistics-dce-descriptor {
             type string;
             description
               "DCE interface statistics";
           }
           leaf lmi-enquiries-received {
             type int32;
             description
               "Number of enquiry packets received";
           }
           leaf lmi-full-enquiries-received {
             type int32;
             description
               "Number of full enquiry packets received";
           }
           leaf lmi-enquiry-responses-sent {
             type int32;
             description
               "Number of enquiry response packets sent";
           }
           leaf lmi-full-enquiry-responses-sent {
             type int32;
             description
               "Number of full enquiry response packets sent";
           }
           leaf lmi-statistics-common-descriptor {
             type string;
             description
               "Statistics common to DTE and DCE";
           }
           leaf lmi-unknown-messages-received {
             type int32;
             description
               "Number of packets received that do not contain valid 
               messages";
           }
           leaf lmi-asynchronous-updates-received {
             type int32;
             description
               "Number of ifstate change updates received";
           }
           leaf lmi-out-of-sequence {
             type int32;
             description
               "Number of packets received in unexpected sequence";
           }
           leaf lmi-keepalive-responses-timeout {
             type int32;
             description
               "Number of times, the timer for keepalive packets expired";
           }
         }
         container lsi-traffic-statistics {
           leaf input-bytes {
             type int32;
           }
           leaf input-bps {
             type int32;
           }
           leaf input-packets {
             type int32;
           }
           leaf input-pps {
             type int32;
           }
         }
         container stp-traffic-statistics {
           leaf stp-input-bytes-dropped {
             type int32;
             description
               "Drop statistics due to stp state at ingress in bytes";
           }
           leaf stp-output-bytes-dropped {
             type int32;
             description
               "Drop statistics due to stp state at egress in bytes";
           }
           leaf stp-input-packets-dropped {
             type int32;
             description
               "Drop statistics due to stp state at ingress in packets";
           }
           leaf stp-output-packets-dropped {
             type int32;
             description
               "Drop statistics due to stp state at egress in packets";
           }
         }
         container af-info {
           leaf af-bw {
             type string;
           }
           leaf af-gnf-id {
             type string;
           }
           leaf af-collapsed-fwd-mode {
             type string;
           }
         }
         container af-fe-info {
           list fe-info {
             leaf fe-num {
               type string;
             }
             leaf fe-bw {
               type string;
             }
             leaf fe-state {
               type string;
             }
             leaf fe-tx-packets {
               type uint64;
             }
             leaf fe-tx-bytes {
               type uint64;
             }
           }
         }
         list af-fe-res-info {
           leaf fe-res-tx-packets {
             type uint64;
           }
           leaf fe-res-tx-bytes {
             type uint64;
           }
         }
         container af-fe-q-pkts {
           list fe-q-pkts-info {
             leaf fe-number {
               type string;
             }
             leaf fe-high-tx-packets {
               type uint64;
             }
             leaf fe-low-tx-packets {
               type uint64;
             }
           }
         }
         container af-fe-q-bytes {
           list fe-q-bytes-info {
             leaf fe-number {
               type string;
             }
             leaf fe-high-tx-bytes {
               type uint64;
             }
             leaf fe-low-tx-bytes {
               type uint64;
             }
           }
         }
         list af-fe-q-res-pkts {
           leaf fe-res-high-tx-packets {
             type uint64;
           }
           leaf fe-res-low-tx-packets {
             type uint64;
           }
         }
         list af-fe-q-res-bytes {
           leaf fe-res-high-tx-bytes {
             type uint64;
           }
           leaf fe-res-low-tx-bytes {
             type uint64;
           }
         }
         list af-collapsed-fwd-stats-mode-disp {
           leaf af-collapsed-fwd-mode-disp {
             type string;
           }
         }
         list af-collapsed-fwd-stats-pkts {
           leaf af-optimal-packets {
             type uint64;
           }
           leaf af-non-optimal-packets {
             type uint64;
           }
         }
         list af-collapsed-fwd-stats-bytes {
           leaf af-optimal-bytes {
             type uint64;
           }
           leaf af-non-optimal-bytes {
             type uint64;
           }
         }
         container queue-num-forwarding-class-name-map {
           leaf queue-number {
             type int32;
             description
               "Queue number";
           }
           leaf forwarding-class-name {
             type string;
             description
               "Forwarding class name associated with queue";
           }
         }
         container chassis-queue-counters {
           description
             "Chassis queue counter statistics";
           container interface-chassis-cos-summary {
             description
               "Packet Forwarding Engine chassis forwarding class and queue 
               information for an interface";
             leaf intf-cos-chassis-num-queues-supported {
               type int32;
               description
                 "Number of Packet Forwarding Engine chassis queues the 
                 interface supports";
             }
             leaf intf-cos-chassis-num-queues-in-use {
               type int32;
               description
                 "Number of Packet Forwarding Engine chassis queues in use 
                 on the interface";
             }
           }
           list queue {
             description
               "Counters for a single queue";
             leaf queue-number {
               type int32;
               description
                 "Queue number";
             }
             leaf forwarding-class-name {
               type string;
               description
                 "Forwarding class name associated with queue";
             }
             leaf queue-counters-queued-packets {
               type uint64;
               description
                 "Queued packet count";
             }
             leaf queue-counters-queued-packets-rate {
               type uint64;
               description
                 "Rate at which packets are queued";
             }
             leaf queue-counters-queued-bytes {
               type uint64;
               description
                 "Queued bytes count";
             }
             leaf queue-counters-queued-bytes-rate {
               type uint64;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets {
               type uint64;
               description
                 "Total number of transmitted packets";
             }
             leaf queue-counters-trans-packets-rate {
               type uint64;
               description
                 "Rate at which packets are transmitted";
             }
             leaf queue-counters-trans-bytes {
               type uint64;
               description
                 "Total number of transmitted bytes";
             }
             leaf queue-counters-trans-bytes-rate {
               type uint64;
               description
                 "Rate at which bytes are transmitted";
             }
             leaf queue-counters-tail-drop-packets-na {
               type string;
               description
                 "Number of packets dropped due to tail drop not available";
             }
             leaf queue-counters-tail-drop-packets {
               type uint64;
               description
                 "Number of packets dropped at the tail of the queue";
             }
             leaf queue-counters-tail-drop-packets-rate {
               type uint64;
               description
                 "Rate at which packets are dropped at tail of queue";
             }
             leaf queue-counters-tail-drop-bytes {
               type uint64;
               description
                 "Number of packets dropped at tail drop of the queue";
             }
             leaf queue-counters-tail-drop-bytes-rate {
               type uint64;
               description
                 "Number of packets dropped at tail drop of the queue";
             }
             leaf queue-counters-rate-limit-drop-packets-na {
               type string;
               description
                 "Number of packets dropped due to rate-limit drop not 
                 available";
             }
             leaf queue-counters-rate-limit-drop-packets {
               type uint64;
               description
                 "Number of packets dropped by rate-limit for the queue";
             }
             leaf queue-counters-rate-limit-drop-packets-rate {
               type uint64;
               description
                 "Rate at which packets are dropped by rate-limit for the 
                 queue";
             }
             leaf queue-counters-rate-limit-drop-bytes-na {
               type string;
               description
                 "Number of bytes dropped due to tail drop not available";
             }
             leaf queue-counters-rate-limit-drop-bytes {
               type uint64;
               description
                 "Number of bytes dropped at the tail of the queue";
             }
             leaf queue-counters-rate-limit-drop-bytes-rate {
               type uint64;
               description
                 "Rate at which bytes are dropped at the tail of the queue";
             }
             leaf queue-counters-red-packets-na {
               type string;
               description
                 "Number of packets dropped due to RED not available";
             }
             leaf queue-counters-red-packets {
               type uint64;
               description
                 "Number of packets dropped due to RED";
             }
             leaf queue-counters-red-packets-rate {
               type uint64;
               description
                 "Rate at which packets are dropped due to RED";
             }
             leaf queue-counters-red-packets-ln {
               type uint64;
               description
                 "Number of RED dropped low-loss, non-TCP packets";
             }
             leaf queue-counters-red-packets-rate-ln {
               type uint64;
               description
                 "RED drop rate for low-loss, non-TCP packets";
             }
             leaf queue-counters-red-packets-lt {
               type uint64;
               description
                 "Number of RED dropped of low-loss, TCP packets";
             }
             leaf queue-counters-red-packets-rate-lt {
               type uint64;
               description
                 "RED drop rate for low-loss, TCP packets";
             }
             leaf queue-counters-red-packets-hn {
               type uint64;
               description
                 "Number of RED dropped high-loss, non-TCP packets";
             }
             leaf queue-counters-red-packets-rate-hn {
               type uint64;
               description
                 "RED drop rate for high-loss, non-TCP packets";
             }
             leaf queue-counters-red-packets-ht {
               type uint64;
               description
                 "Number of RED dropped high-loss, TCP packets";
             }
             leaf queue-counters-red-packets-rate-ht {
               type uint64;
               description
                 "RED drop rate for high-loss, TCP packets";
             }
             leaf queue-counters-red-packets-low {
               type uint64;
               description
                 "Number of RED dropped low-loss packets";
             }
             leaf queue-counters-red-packets-rate-low {
               type uint64;
               description
                 "RED drop rate for low-loss packets";
             }
             leaf queue-counters-red-packets-medium-low {
               type uint64;
               description
                 "Number of RED dropped medium-low-loss packets";
             }
             leaf queue-counters-red-packets-rate-medium-low {
               type uint64;
               description
                 "RED drop rate for medium-low-loss packets";
             }
             leaf queue-counters-red-packets-medium-high {
               type uint64;
               description
                 "Number of RED dropped medium-high-loss packets";
             }
             leaf queue-counters-red-packets-rate-medium-high {
               type uint64;
               description
                 "RED drop rate for medium-high-loss packets";
             }
             leaf queue-counters-red-packets-medium {
               type uint64;
               description
                 "Number of RED dropped medium-loss packets";
             }
             leaf queue-counters-red-packets-rate-medium {
               type uint64;
               description
                 "RED drop rate for medium-loss packets";
             }
             leaf queue-counters-red-packets-high {
               type uint64;
               description
                 "Number of RED dropped high-loss packets";
             }
             leaf queue-counters-red-packets-rate-high {
               type uint64;
               description
                 "RED drop rate for high-loss packets";
             }
             leaf queue-counters-red-bytes-na {
               type string;
               description
                 "Number of bytes dropped due to RED not available";
             }
             leaf queue-counters-red-bytes {
               type uint64;
               description
                 "Number of bytes dropped due to RED";
             }
             leaf queue-counters-red-bytes-rate {
               type uint64;
               description
                 "Rate at which bytes are dropped due to RED";
             }
             leaf queue-counters-red-bytes-ln {
               type uint64;
               description
                 "Number of RED dropped low-loss, non-TCP bytes";
             }
             leaf queue-counters-red-bytes-rate-ln {
               type uint64;
               description
                 "RED drop rate for low-loss, non-TCP bytes";
             }
             leaf queue-counters-red-bytes-lt {
               type uint64;
               description
                 "Number of RED dropped low-loss, TCP bytes";
             }
             leaf queue-counters-red-bytes-rate-lt {
               type uint64;
               description
                 "RED drop rate for low-loss, TCP bytes";
             }
             leaf queue-counters-red-bytes-hn {
               type uint64;
               description
                 "Number of RED dropped high-loss, non-TCP bytes";
             }
             leaf queue-counters-red-bytes-rate-hn {
               type uint64;
               description
                 "RED drop rate for high-loss, non-TCP bytes";
             }
             leaf queue-counters-red-bytes-ht {
               type uint64;
               description
                 "Number of RED dropped high-loss, TCP bytes";
             }
             leaf queue-counters-red-bytes-rate-ht {
               type uint64;
               description
                 "RED drop rate for high-loss, TCP bytes";
             }
             leaf queue-counters-red-bytes-low {
               type uint64;
               description
                 "Number of RED dropped low-loss bytes";
             }
             leaf queue-counters-red-bytes-rate-low {
               type uint64;
               description
                 "RED drop rate for low-loss bytes";
             }
             leaf queue-counters-red-bytes-medium-low {
               type uint64;
               description
                 "Number of RED dropped medium-low-loss bytes";
             }
             leaf queue-counters-red-bytes-rate-medium-low {
               type uint64;
               description
                 "RED drop rate for medium-low-loss bytes";
             }
             leaf queue-counters-red-bytes-medium-high {
               type uint64;
               description
                 "Number of RED dropped medium-high-loss bytes";
             }
             leaf queue-counters-red-bytes-rate-medium-high {
               type uint64;
               description
                 "RED drop rate for medium-high-loss bytes";
             }
             leaf queue-counters-red-bytes-medium {
               type uint64;
               description
                 "Number of RED dropped medium-loss bytes";
             }
             leaf queue-counters-red-bytes-rate-medium {
               type uint64;
               description
                 "RED drop rate for medium-loss bytes";
             }
             leaf queue-counters-red-bytes-high {
               type uint64;
               description
                 "Number of RED dropped high-loss bytes";
             }
             leaf queue-counters-red-bytes-rate-high {
               type uint64;
               description
                 "RED drop rate for high-loss bytes";
             }
             leaf queue-counters-timestamp {
               type uint64;
               description
                 "Last packet enqueued timestamp";
             }
             leaf queue-counters-total-drop-packets {
               type uint64;
               description
                 "Number of total packets dropped at the queue";
             }
             leaf queue-counters-total-drop-packets-rate {
               type uint64;
               description
                 "Number of total packets dropped at the queue";
             }
             leaf queue-counters-total-drop-bytes {
               type uint64;
               description
                 "Number of total packets dropped at the queue";
             }
             leaf queue-counters-total-drop-bytes-rate {
               type uint64;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
         }
         container ingress-queue-counters {
           description
             "Ingress queue counter statistics";
           list queue {
             description
               "Counters for a single queue";
             leaf queue-number {
               type int32;
               description
                 "Queue number";
             }
             leaf forwarding-class-name {
               type string;
               description
                 "Forwarding class name associated with queue";
             }
             leaf queue-counters-queued-packets {
               type uint64;
               description
                 "Queued packet count";
             }
             leaf queue-counters-queued-packets-rate {
               type uint64;
               description
                 "Rate at which packets are queued";
             }
             leaf queue-counters-queued-bytes {
               type uint64;
               description
                 "Queued bytes count";
             }
             leaf queue-counters-queued-bytes-rate {
               type uint64;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets {
               type uint64;
               description
                 "Total number of transmitted packets";
             }
             leaf queue-counters-trans-packets-rate {
               type uint64;
               description
                 "Rate at which packets are transmitted";
             }
             leaf queue-counters-trans-bytes {
               type uint64;
               description
                 "Total number of transmitted bytes";
             }
             leaf queue-counters-trans-bytes-rate {
               type uint64;
               description
                 "Rate at which bytes are transmitted";
             }
             leaf queue-counters-tail-drop-packets-na {
               type string;
               description
                 "Number of packets dropped due to tail drop not available";
             }
             leaf queue-counters-tail-drop-packets {
               type uint64;
               description
                 "Number of packets dropped at the tail of the queue";
             }
             leaf queue-counters-tail-drop-packets-rate {
               type uint64;
               description
                 "Rate at which packets are dropped at tail of queue";
             }
             leaf queue-counters-tail-drop-bytes {
               type uint64;
               description
                 "Number of packets dropped at tail drop of the queue";
             }
             leaf queue-counters-tail-drop-bytes-rate {
               type uint64;
               description
                 "Number of packets dropped at tail drop of the queue";
             }
             leaf queue-counters-rate-limit-drop-packets-na {
               type string;
               description
                 "Number of packets dropped due to rate-limit drop not 
                 available";
             }
             leaf queue-counters-rate-limit-drop-packets {
               type uint64;
               description
                 "Number of packets dropped by rate-limit for the queue";
             }
             leaf queue-counters-rate-limit-drop-packets-rate {
               type uint64;
               description
                 "Rate at which packets are dropped by rate-limit for the 
                 queue";
             }
             leaf queue-counters-rate-limit-drop-bytes-na {
               type string;
               description
                 "Number of bytes dropped due to tail drop not available";
             }
             leaf queue-counters-rate-limit-drop-bytes {
               type uint64;
               description
                 "Number of bytes dropped at the tail of the queue";
             }
             leaf queue-counters-rate-limit-drop-bytes-rate {
               type uint64;
               description
                 "Rate at which bytes are dropped at the tail of the queue";
             }
             leaf queue-counters-red-packets-na {
               type string;
               description
                 "Number of packets dropped due to RED not available";
             }
             leaf queue-counters-red-packets {
               type uint64;
               description
                 "Number of packets dropped due to RED";
             }
             leaf queue-counters-red-packets-rate {
               type uint64;
               description
                 "Rate at which packets are dropped due to RED";
             }
             leaf queue-counters-red-packets-ln {
               type uint64;
               description
                 "Number of RED dropped low-loss, non-TCP packets";
             }
             leaf queue-counters-red-packets-rate-ln {
               type uint64;
               description
                 "RED drop rate for low-loss, non-TCP packets";
             }
             leaf queue-counters-red-packets-lt {
               type uint64;
               description
                 "Number of RED dropped of low-loss, TCP packets";
             }
             leaf queue-counters-red-packets-rate-lt {
               type uint64;
               description
                 "RED drop rate for low-loss, TCP packets";
             }
             leaf queue-counters-red-packets-hn {
               type uint64;
               description
                 "Number of RED dropped high-loss, non-TCP packets";
             }
             leaf queue-counters-red-packets-rate-hn {
               type uint64;
               description
                 "RED drop rate for high-loss, non-TCP packets";
             }
             leaf queue-counters-red-packets-ht {
               type uint64;
               description
                 "Number of RED dropped high-loss, TCP packets";
             }
             leaf queue-counters-red-packets-rate-ht {
               type uint64;
               description
                 "RED drop rate for high-loss, TCP packets";
             }
             leaf queue-counters-red-packets-low {
               type uint64;
               description
                 "Number of RED dropped low-loss packets";
             }
             leaf queue-counters-red-packets-rate-low {
               type uint64;
               description
                 "RED drop rate for low-loss packets";
             }
             leaf queue-counters-red-packets-medium-low {
               type uint64;
               description
                 "Number of RED dropped medium-low-loss packets";
             }
             leaf queue-counters-red-packets-rate-medium-low {
               type uint64;
               description
                 "RED drop rate for medium-low-loss packets";
             }
             leaf queue-counters-red-packets-medium-high {
               type uint64;
               description
                 "Number of RED dropped medium-high-loss packets";
             }
             leaf queue-counters-red-packets-rate-medium-high {
               type uint64;
               description
                 "RED drop rate for medium-high-loss packets";
             }
             leaf queue-counters-red-packets-medium {
               type uint64;
               description
                 "Number of RED dropped medium-loss packets";
             }
             leaf queue-counters-red-packets-rate-medium {
               type uint64;
               description
                 "RED drop rate for medium-loss packets";
             }
             leaf queue-counters-red-packets-high {
               type uint64;
               description
                 "Number of RED dropped high-loss packets";
             }
             leaf queue-counters-red-packets-rate-high {
               type uint64;
               description
                 "RED drop rate for high-loss packets";
             }
             leaf queue-counters-red-bytes-na {
               type string;
               description
                 "Number of bytes dropped due to RED not available";
             }
             leaf queue-counters-red-bytes {
               type uint64;
               description
                 "Number of bytes dropped due to RED";
             }
             leaf queue-counters-red-bytes-rate {
               type uint64;
               description
                 "Rate at which bytes are dropped due to RED";
             }
             leaf queue-counters-red-bytes-ln {
               type uint64;
               description
                 "Number of RED dropped low-loss, non-TCP bytes";
             }
             leaf queue-counters-red-bytes-rate-ln {
               type uint64;
               description
                 "RED drop rate for low-loss, non-TCP bytes";
             }
             leaf queue-counters-red-bytes-lt {
               type uint64;
               description
                 "Number of RED dropped low-loss, TCP bytes";
             }
             leaf queue-counters-red-bytes-rate-lt {
               type uint64;
               description
                 "RED drop rate for low-loss, TCP bytes";
             }
             leaf queue-counters-red-bytes-hn {
               type uint64;
               description
                 "Number of RED dropped high-loss, non-TCP bytes";
             }
             leaf queue-counters-red-bytes-rate-hn {
               type uint64;
               description
                 "RED drop rate for high-loss, non-TCP bytes";
             }
             leaf queue-counters-red-bytes-ht {
               type uint64;
               description
                 "Number of RED dropped high-loss, TCP bytes";
             }
             leaf queue-counters-red-bytes-rate-ht {
               type uint64;
               description
                 "RED drop rate for high-loss, TCP bytes";
             }
             leaf queue-counters-red-bytes-low {
               type uint64;
               description
                 "Number of RED dropped low-loss bytes";
             }
             leaf queue-counters-red-bytes-rate-low {
               type uint64;
               description
                 "RED drop rate for low-loss bytes";
             }
             leaf queue-counters-red-bytes-medium-low {
               type uint64;
               description
                 "Number of RED dropped medium-low-loss bytes";
             }
             leaf queue-counters-red-bytes-rate-medium-low {
               type uint64;
               description
                 "RED drop rate for medium-low-loss bytes";
             }
             leaf queue-counters-red-bytes-medium-high {
               type uint64;
               description
                 "Number of RED dropped medium-high-loss bytes";
             }
             leaf queue-counters-red-bytes-rate-medium-high {
               type uint64;
               description
                 "RED drop rate for medium-high-loss bytes";
             }
             leaf queue-counters-red-bytes-medium {
               type uint64;
               description
                 "Number of RED dropped medium-loss bytes";
             }
             leaf queue-counters-red-bytes-rate-medium {
               type uint64;
               description
                 "RED drop rate for medium-loss bytes";
             }
             leaf queue-counters-red-bytes-high {
               type uint64;
               description
                 "Number of RED dropped high-loss bytes";
             }
             leaf queue-counters-red-bytes-rate-high {
               type uint64;
               description
                 "RED drop rate for high-loss bytes";
             }
             leaf queue-counters-timestamp {
               type uint64;
               description
                 "Last packet enqueued timestamp";
             }
             leaf queue-counters-total-drop-packets {
               type uint64;
               description
                 "Number of total packets dropped at the queue";
             }
             leaf queue-counters-total-drop-packets-rate {
               type uint64;
               description
                 "Number of total packets dropped at the queue";
             }
             leaf queue-counters-total-drop-bytes {
               type uint64;
               description
                 "Number of total packets dropped at the queue";
             }
             leaf queue-counters-total-drop-bytes-rate {
               type uint64;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
           container interface-cos-short-summary {
             description
               "Summary of queue information on an interface";
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           container queue-num-forwarding-class-name-map {
             leaf queue-number {
               type int32;
               description
                 "Queue number";
             }
             leaf forwarding-class-name {
               type string;
               description
                 "Forwarding class name associated with queue";
             }
           }
         }
         container otn-oc-information {
           list media-alarm {
             leaf media-alarm-name {
               type string;
             }
             leaf media-alarm-seconds {
               type int32;
             }
             leaf media-alarm-count {
               type int32;
             }
             leaf media-alarm-state {
               type string;
             }
           }
         }
         container otn-otu-information {
           list media-alarm {
             leaf media-alarm-name {
               type string;
             }
             leaf media-alarm-seconds {
               type int32;
             }
             leaf media-alarm-count {
               type int32;
             }
             leaf media-alarm-state {
               type string;
             }
           }
         }
         container otn-odu-information {
           list media-alarm {
             leaf media-alarm-name {
               type string;
             }
             leaf media-alarm-seconds {
               type int32;
             }
             leaf media-alarm-count {
               type int32;
             }
             leaf media-alarm-state {
               type string;
             }
           }
         }
         container otn-ot-module-information {
           list media-alarm {
             leaf media-alarm-name {
               type string;
             }
             leaf media-alarm-seconds {
               type int32;
             }
             leaf media-alarm-count {
               type int32;
             }
             leaf media-alarm-state {
               type string;
             }
           }
         }
         list otn-odu-tcm-information {
           list media-alarm {
             leaf media-alarm-name {
               type string;
             }
             leaf media-alarm-seconds {
               type int32;
             }
             leaf media-alarm-count {
               type int32;
             }
             leaf media-alarm-state {
               type string;
             }
           }
         }
         container ima-state {
           leaf media-type {
             type string;
             description
               "Type of media this information is for";
           }
           leaf ima-state-line {
             type string;
             description
               "Line state of IMA link";
           }
           leaf ima-state-near-end {
             type string;
             description
               "Near-end states of IMA group/link";
           }
           leaf ima-state-far-end {
             type string;
             description
               "Far-end states of IMA group/link";
           }
         }
         container ima-group-information {
           description
             "IMA group alarms";
           list media-alarm {
             leaf media-alarm-name {
               type string;
             }
             leaf media-alarm-seconds {
               type int32;
             }
             leaf media-alarm-count {
               type int32;
             }
             leaf media-alarm-state {
               type string;
             }
           }
         }
         container ima-link-information {
           description
             "IMA link alarms";
           list media-alarm {
             leaf media-alarm-name {
               type string;
             }
             leaf media-alarm-seconds {
               type int32;
             }
             leaf media-alarm-count {
               type int32;
             }
             leaf media-alarm-state {
               type string;
             }
           }
         }
         container ethernet-mac-pfc-statistics {
           description
             "Ethernet MAC Priority Flow control Statistics";
           leaf mac-pfc-dot1p {
             type int32;
           }
           leaf input-mac-pfc-frames {
             type int32;
           }
           leaf output-mac-pfc-frames {
             type int32;
           }
         }
         container satop-information {
           leaf ce-payload-size {
             type int32;
           }
           leaf ce-idle-pattern {
             type string;
           }
           leaf ce-octet-aligned {
             type string;
           }
           leaf ce-jitter-buffer-packets {
             type int32;
           }
           leaf ce-jitter-buffer-latency {
             type int32;
           }
           leaf ce-jitter-buffer-auto-adjust {
             type string;
           }
           leaf ce-excessive-packet-loss-rate-sample-period {
             type int32;
           }
           leaf ce-excessive-packet-loss-rate-threshold {
             type int32;
           }
         }
         container cesopsn-information {
           leaf ce-packetization-latency {
             type int32;
           }
           leaf ce-idle-pattern {
             type string;
           }
           leaf ce-jitter-buffer-packets {
             type int32;
           }
           leaf ce-jitter-buffer-latency {
             type int32;
           }
           leaf ce-jitter-buffer-auto-adjust {
             type string;
           }
           leaf ce-excessive-packet-loss-rate-sample-period {
             type int32;
           }
           leaf ce-excessive-packet-loss-rate-threshold {
             type int32;
           }
         }
         container ima-group-properties {
           leaf ima-version {
             type string;
             description
               "IMA specification version";
           }
           leaf ima-frame-length {
             type int32;
             description
               "IMA frame length";
           }
           leaf ima-differential-delay {
             type int32;
             description
               "IMA differential delay in milliseconds";
           }
           leaf ima-symmetry {
             type string;
             description
               "IMA operation symmetry mode";
           }
           leaf ima-transmit-clock {
             type string;
             description
               "IMA transmit clock mode";
           }
           leaf ima-tx-minimum-links {
             type int32;
             description
               "IMA transmit minimum links";
           }
           leaf ima-rx-minimum-links {
             type int32;
             description
               "IMA receive minimum links";
           }
           leaf ima-frame-sync-alpha {
             type int32;
             description
               "Consecutive invalid ICP cells for IMA frame synchronization";
           }
           leaf ima-frame-sync-beta {
             type int32;
             description
               "Consecutive errored ICP cells for IMA frame synchronization";
           }
           leaf ima-frame-sync-gamma {
             type int32;
             description
               "Consecutive valid ICP cells for IMA frame synchronization";
           }
           leaf ima-group-link-enumerator {
             type int32;
             description
               "Enumerator for link in this IMA group";
           }
           leaf ima-group-link-information {
             type string;
             description
               "Information for link in this IMA group";
           }
           leaf ima-test-period {
             type int32;
             description
               "IMA Test period";
           }
           leaf ima-test-elapsed {
             type int32;
             description
               "IMA Test elapsed time";
           }
           leaf ima-test-status {
             type string;
             description
               "IMA test procedure status";
           }
           leaf ima-test-pattern {
             type int32;
             description
               "IMA test tx pattern";
           }
           leaf ima-test-link {
             type string;
             description
               "IMA test procedure link";
           }
           leaf ima-test-result-pattern {
             type int32;
             description
               "IMA test rx pattern";
           }
           leaf ima-test-result-status {
             type string;
             description
               "IMA test result";
           }
           leaf ima-test-result-miscon {
             type int32;
             description
               "IMA test misconnected seconds";
           }
           leaf ima-test-result-mispat {
             type int32;
             description
               "IMA test mismatched pattern seconds";
           }
         }
         container ima-link-properties {
           leaf ima-group-id {
             type int32;
             description
               "IMA group ID";
           }
           leaf ima-link-direction {
             type string;
             description
               "IMA link direction";
           }
         }
         container cos-information {
           description
             "Information about class-of-service configuration";
           list cos-stream-information {
             key "cos-direction";
             description
               "Information about the traffic stream";
             leaf cos-direction {
               type string;
               description
                 "Direction of the traffic stream";
             }
             list cos-queue-configuration {
               key "cos-queue-number";
               leaf cos-queue-number {
                 type int32;
                 description
                   "Queue number";
               }
               leaf cos-queue-forwarding-class {
                 type string;
               }
               leaf cos-queue-bandwidth-remainder {
                 type string;
               }
               leaf cos-queue-bandwidth {
                 type int32;
               }
               leaf cos-queue-bandwidth-bps-remainder {
                 type string;
               }
               leaf cos-queue-bandwidth-bps {
                 type uint64;
               }
               leaf cos-queue-buffer-remainder {
                 type string;
               }
               leaf cos-queue-buffer {
                 type int32;
               }
               leaf cos-queue-buffer-bytes {
                 type int32;
               }
               leaf cos-queue-priority {
                 type string;
               }
               leaf cos-queue-limit {
                 type string;
               }
             }
           }
           container cos-forwarding-class-information {
             container fc-map {
               description
                 "Class-of-service forwarding class to queue mapping";
               list fc-map-item {
                 leaf fc-name {
                   type string;
                   description
                     "Class-of-service forwarding class name";
                 }
                 leaf fc-number {
                   type uint32;
                   description
                     "Identifier for Class-of-service forwarding class";
                 }
                 leaf fc-queue-number {
                   type uint32;
                   description
                     "Class-of-service forwarding class queue number";
                 }
                 leaf fc-rqueue-number {
                   type uint32;
                   description
                     "Class-of-service forwarding class restricted queue 
                     number";
                 }
                 leaf fc-priority {
                   type string;
                   description
                     "Class-of-service forwarding class queue priority";
                 }
                 leaf fc-policing-priority {
                   type string;
                   description
                     "Class-of-service forwarding class policing priority";
                 }
                 leaf fc-spu-priority {
                   type string;
                   description
                     "Class-of-service forwarding class spu priority";
                 }
                 leaf fc-no-loss {
                   type string;
                   description
                     "Class-of-service forwarding class no-loss";
                 }
                 leaf fc-pfc-priority {
                   type string;
                   description
                     "Class-of-service forwarding class pfc-priority";
                 }
                 leaf fc-multicast {
                   type string;
                   description
                     "Class-of-service forwarding class multicast";
                 }
                 leaf fc-latency-ecn {
                   type string;
                   description
                     "Class-of-service forwarding class latency ECN";
                 }
               }
             }
           }
           container cos-forwarding-class-map-information {
             container fc-map {
               description
                 "Class-of-service forwarding class to queue mapping";
               list fc-map-item {
                 leaf fc-name {
                   type string;
                   description
                     "Class-of-service forwarding class name";
                 }
                 leaf fc-number {
                   type uint32;
                   description
                     "Identifier for Class-of-service forwarding class";
                 }
                 leaf fc-queue-number {
                   type uint32;
                   description
                     "Class-of-service forwarding class queue number";
                 }
                 leaf fc-rqueue-number {
                   type uint32;
                   description
                     "Class-of-service forwarding class restricted queue 
                     number";
                 }
                 leaf fc-priority {
                   type string;
                   description
                     "Class-of-service forwarding class queue priority";
                 }
                 leaf fc-policing-priority {
                   type string;
                   description
                     "Class-of-service forwarding class policing priority";
                 }
                 leaf fc-spu-priority {
                   type string;
                   description
                     "Class-of-service forwarding class spu priority";
                 }
                 leaf fc-no-loss {
                   type string;
                   description
                     "Class-of-service forwarding class no-loss";
                 }
                 leaf fc-pfc-priority {
                   type string;
                   description
                     "Class-of-service forwarding class pfc-priority";
                 }
                 leaf fc-multicast {
                   type string;
                   description
                     "Class-of-service forwarding class multicast";
                 }
                 leaf fc-latency-ecn {
                   type string;
                   description
                     "Class-of-service forwarding class latency ECN";
                 }
               }
             }
           }
           container cos-classifier-information {
             list classifier {
               description
                 "Class-of-service code point classifier";
               leaf classifier-name {
                 type string;
                 description
                   "Class-of-service classifier name";
               }
               leaf code-point-type {
                 type string;
                 description
                   "Class-of-service code point type";
               }
               leaf table-index {
                 type uint32;
                 description
                   "Table index";
               }
               container classifier-map {
                 list classifier-map-item {
                   leaf code-point {
                     type string;
                     description
                       "Class-of-service code point alias name or bits";
                   }
                   leaf fc-name {
                     type string;
                     description
                       "Class-of-service forwarding class name";
                   }
                   leaf loss-priority {
                     type string;
                     description
                       "Class-of-service loss priority";
                   }
                   leaf cntag-present {
                     type string;
                     description
                       "Class-of-service cntag present";
                   }
                 }
               }
             }
           }
           container cos-loss-priority-map-information {
             list loss-priority-map {
               description
                 "Class-of-service code point loss priority map";
               leaf loss-priority-map-name {
                 type string;
                 description
                   "Name of class-of-service loss priority map";
               }
               leaf code-point-type {
                 type string;
                 description
                   "Class-of-service code point type";
               }
               leaf table-index {
                 type uint32;
                 description
                   "Table index";
               }
               list loss-priority-map-table {
                 list loss-priority-map-item {
                   leaf code-point {
                     type string;
                     description
                       "Class-of-service code point alias name or bits";
                   }
                   leaf loss-priority {
                     type string;
                     description
                       "Class-of-service loss priority";
                   }
                 }
                 list loss-priority-map-table-entry {
                   leaf table-index {
                     type uint32;
                     description
                       "Table index";
                   }
                   leaf code-point {
                     type string;
                     description
                       "Class-of-service code point alias name or bits";
                   }
                   leaf loss-priority {
                     type string;
                     description
                       "Class-of-service loss priority";
                   }
                 }
               }
             }
           }
           container cos-drop-profile-information {
             list drop-profile {
               description
                 "Class-of-service drop profile";
               leaf profile-name {
                 type string;
                 description
                   "Class-of-service drop profile name";
               }
               leaf profile-type {
                 type string;
                 description
                   "Class-of-service drop profile type";
               }
               leaf table-index {
                 type uint32;
                 description
                   "Table index";
               }
               container profile-map {
                 list profile-map-item {
                   leaf fill-level {
                     type uint32;
                     description
                       "Class-of-service drop profile fill level value";
                   }
                   leaf probability {
                     type uint32;
                     description
                       "Class-of-service drop profile probability value";
                   }
                 }
               }
             }
           }
           container cos-mpls-ecn-map-information {
             list cos-mpls-ecn-map-info {
               description
                 "Class-of-service mpls-ecn-map information";
               leaf ecn-capable-exp {
                 type int32;
                 description
                   "ECN capable exp";
               }
               leaf congestion-experienced-exp {
                 type int32;
                 description
                   "Congestion Expereienced exp";
               }
             }
           }
           container cos-monitoring-profile-information {
             list monitoring-profile {
               description
                 "Class-of-service monitoring profile";
               leaf monitoring-profile-name {
                 type string;
                 description
                   "Class-of-service monitoring profile name";
               }
               container export-filters {
                 container export-filter {
                   leaf filter-name {
                     type string;
                     description
                       "Class-of-service monitoring profile filter name";
                   }
                   leaf monitoring-queue-number {
                     type uint32;
                     description
                       "Class-of-service monitoring profile filter queue 
                       value";
                   }
                   leaf peak-queue-length-value {
                     type uint32;
                     description
                       "Class-of-service monitoring profile peak queue 
                       length value";
                   }
                 }
               }
             }
           }
           container cos-rewrite-information {
             list rewrite {
               description
                 "Class-of-service drop profile";
               leaf rewrite-name {
                 type string;
                 description
                   "Class-of-service rewrite rule name";
               }
               leaf code-point-type {
                 type string;
                 description
                   "Class-of-service code point type";
               }
               leaf table-index {
                 type uint32;
                 description
                   "Table index";
               }
               container rewrite-map {
                 list rewrite-map-item {
                   leaf fc-name {
                     type string;
                     description
                       "Class-of-service forwarding class name";
                   }
                   leaf loss-priority {
                     type string;
                     description
                       "Class-of-service loss priority";
                   }
                   leaf code-point {
                     type string;
                     description
                       "Class-of-service code point alias name or bits";
                   }
                 }
               }
             }
           }
           container cos-loss-priority-rewrite-information {
             list loss-priority-rewrite {
               description
                 "Class-of-service loss priority to code point rewrite";
               leaf loss-priority-rewrite-name {
                 type string;
                 description
                   "Name of class-of-service loss priority rewrite";
               }
               leaf code-point-type {
                 type string;
                 description
                   "Class-of-service code point type";
               }
               leaf table-index {
                 type uint32;
                 description
                   "Table index";
               }
               list loss-priority-rewrite-table {
                 list loss-priority-rewrite-item {
                   leaf loss-priority {
                     type string;
                     description
                       "Class-of-service loss priority";
                   }
                   leaf code-point {
                     type string;
                     description
                       "Class-of-service code point alias name or bits";
                   }
                 }
                 list loss-priority-rewrite-table-entry {
                   leaf table-index {
                     type uint32;
                     description
                       "Table index";
                   }
                   leaf loss-priority {
                     type string;
                     description
                       "Class-of-service loss priority";
                   }
                   leaf code-point {
                     type string;
                     description
                       "Class-of-service code point alias name or bits";
                   }
                 }
               }
             }
           }
           container cos-code-point-map-information {
             list code-point-map {
               description
                 "Class-of-service code point alias map";
               leaf code-point-type {
                 type string;
                 description
                   "Class-of-service code point type";
               }
               container alias-map {
                 list alias-map-item {
                   leaf code-point-alias {
                     type string;
                     description
                       "Class-of-service code point alias name";
                   }
                   leaf code-point-bits {
                     type string;
                     description
                       "Class-of-service code point bit sequence";
                   }
                 }
               }
             }
           }
           container cos-fragmentation-map-information {
             list fragmentation-map {
               description
                 "Class-of-service fragmentation map";
               leaf fragmentation-map-name {
                 type string;
                 description
                   "Class-of-service fragmentation map name";
               }
               leaf fragmentation-map-index {
                 type uint32;
                 description
                   "Index number for Class-of-service fragmentation map";
               }
               list fragment-map {
                 leaf fc-name {
                   type string;
                   description
                     "Class-of-service forwarding class name";
                 }
                 leaf no-fragmentation {
                   type empty;
                   description
                     "Do not fragment packets of this class";
                 }
                 leaf fragment-threshold {
                   type string;
                   description
                     "Fragmentation threshold";
                 }
                 leaf fragment-multilink-class {
                   type int32;
                   description
                     "Identifier for multilink class";
                 }
               }
             }
           }
           container cos-translation-table-map-information {
             list translation-table {
               description
                 "Class-of-service code point translation table";
               leaf translation-table-name {
                 type string;
                 description
                   "Class-of-service translation table name";
               }
               leaf translation-table-type {
                 type string;
                 description
                   "Class-of-service translation table type";
               }
               leaf table-index {
                 type uint32;
                 description
                   "Table index";
               }
               container translation-table-map {
                 container translation-table-map-item {
                   leaf from-code-point {
                     type string;
                     description
                       "Class-of-service code point alias name or bits";
                   }
                   leaf to-code-point {
                     type string;
                     description
                       "Class-of-service code point alias name or bits";
                   }
                 }
               }
               list translation-table-entry {
                 leaf table-index {
                   type uint32;
                   description
                     "Table index";
                 }
                 leaf from-code-point {
                   type string;
                   description
                     "Class-of-service code point alias name or bits";
                 }
                 leaf to-code-point {
                   type string;
                   description
                     "Class-of-service code point alias name or bits";
                 }
               }
             }
           }
           container cos-multi-destination-information {
             container sm-md-map {
               leaf scheduler-map-name {
                 type string;
                 description
                   "Class-of-service scheduler map name";
               }
               leaf scheduler-map-index {
                 type uint64;
                 description
                   "Class-of-service scheduler map index";
               }
             }
             container fc-md-map {
               leaf fc-name {
                 type string;
                 description
                   "Class-of-service forwarding class name";
               }
               leaf fc-queue-number {
                 type uint32;
                 description
                   "Class-of-service forwarding class queue number";
               }
             }
             container cls-md-map {
               leaf multidest-classifier-name {
                 type string;
                 description
                   "Multi destination classifier name";
               }
               leaf multidest-classifier-type {
                 type string;
                 description
                   "Multi destination classifier type";
               }
               leaf multidest-classifier-index {
                 type uint32;
                 description
                   "Multi destination classifier id";
               }
             }
           }
           container cos-forwarding-class-set-information {
             list forwarding-class-set {
               description
                 "Class-of-service forwarding class set information";
               list forwarding-class-set-entry {
                 leaf forwarding-class-set-name {
                   type string;
                   description
                     "Class-of-service forwarding class set name";
                 }
                 leaf forwarding-class-set-type {
                   type string;
                   description
                     "Identifier for Class-of-service forwarding class set 
                     type";
                 }
                 leaf forwarding-class-set-index {
                   type uint32;
                   description
                     "Identifier for Class-of-service forwarding class set";
                 }
                 container fc-map {
                   description
                     "Class-of-service forwarding class to queue mapping";
                   list fc-map-item {
                     leaf fc-name {
                       type string;
                       description
                         "Class-of-service forwarding class name";
                     }
                     leaf fc-number {
                       type uint32;
                       description
                         "Identifier for Class-of-service forwarding class";
                     }
                     leaf fc-queue-number {
                       type uint32;
                       description
                         "Class-of-service forwarding class queue number";
                     }
                     leaf fc-rqueue-number {
                       type uint32;
                       description
                         "Class-of-service forwarding class restricted queue
                         number";
                     }
                     leaf fc-priority {
                       type string;
                       description
                         "Class-of-service forwarding class queue priority";
                     }
                     leaf fc-policing-priority {
                       type string;
                       description
                         "Class-of-service forwarding class policing 
                         priority";
                     }
                     leaf fc-spu-priority {
                       type string;
                       description
                         "Class-of-service forwarding class spu priority";
                     }
                     leaf fc-no-loss {
                       type string;
                       description
                         "Class-of-service forwarding class no-loss";
                     }
                     leaf fc-pfc-priority {
                       type string;
                       description
                         "Class-of-service forwarding class pfc-priority";
                     }
                     leaf fc-multicast {
                       type string;
                       description
                         "Class-of-service forwarding class multicast";
                     }
                     leaf fc-latency-ecn {
                       type string;
                       description
                         "Class-of-service forwarding class latency ECN";
                     }
                   }
                 }
               }
             }
           }
           container cos-policy-map-information {
             list policy-map {
               description
                 "Class-of-service Policy-map";
               leaf policy-map-name {
                 type string;
                 description
                   "Class-of-service Policy-map name";
               }
               leaf table-index {
                 type uint32;
                 description
                   "Table index";
               }
               leaf policy-map-user-attribute {
                 type uint32;
                 description
                   "User-defined attribute";
               }
               container policy-map-cp-entries {
                 leaf code-point-type {
                   type string;
                   description
                     "Class-of-service code point type";
                 }
                 leaf code-point {
                   type string;
                   description
                     "Class-of-service code point alias name or bits";
                 }
                 leaf code-point-option {
                   type string;
                   description
                     "Class-of-service code point option flag";
                 }
               }
             }
           }
           container cos-client-info {
             list cos-client {
               description
                 "Class-of-service Junos client information";
               leaf cos-client-info-internal-id {
                 type uint32;
                 description
                   "Junos client internal identifier";
               }
               leaf cos-client-info-requests {
                 type uint32;
                 description
                   "Number of requests from Junos client";
               }
               leaf cos-client-info-responses {
                 type uint32;
                 description
                   "Number of responses to Junos client";
               }
               leaf cos-client-info-failures {
                 type uint32;
                 description
                   "Number of failures while handling Junos client requests";
               }
               leaf cos-client-info-identifier {
                 type string;
                 description
                   "Junos client identifier";
               }
               leaf cos-client-name {
                 type string;
                 description
                   "Junos client name";
               }
               leaf cos-client-state {
                 type string;
                 description
                   "Junos client state information";
               }
               leaf cos-client-internal-name {
                 type string;
                 description
                   "Junos client internal name";
               }
               leaf cos-client-stats {
                 type string;
                 description
                   "Junos client statistics";
               }
               leaf cos-client-failure-stats {
                 type string;
                 description
                   "Junos client failure/error statistics";
               }
               leaf cos-client-validate-failures {
                 type uint32;
                 description
                   "Junos client request validation failures";
               }
               leaf cos-client-ownership-failures {
                 type uint32;
                 description
                   "Junos client ownership validation failures";
               }
               leaf cos-client-info-name {
                 type string;
                 description
                   "CoS client name";
               }
               leaf cos-client-internal-id {
                 type uint32;
                 description
                   "Junos client internal identifier";
               }
               leaf cos-client-requests {
                 type uint64;
                 description
                   "Number of requests from Junos client";
               }
               leaf cos-client-responses {
                 type uint64;
                 description
                   "Number of responses to Junos client";
               }
               leaf cos-client-failures {
                 type uint64;
                 description
                   "Number of failures while handling Junos client requests";
               }
               leaf cos-client-identifier {
                 type string;
                 description
                   "Junos client identifier";
               }
               leaf cos-client-status {
                 type string;
                 description
                   "Junos client status";
               }
               leaf cos-client-connected-time {
                 type string;
                 description
                   "Junos client time of connect";
               }
               leaf cos-client-reconnected-time {
                 type string;
                 description
                   "Junos client time of reconnect";
               }
               leaf cos-client-disconnected-time {
                 type string;
                 description
                   "Junos client time of disconnect";
               }
               leaf cos-client-message-type {
                 type string;
                 description
                   "Junos client message type";
               }
               leaf cos-client-operation-type {
                 type string;
                 description
                   "Junos client operation type";
               }
               leaf-list cos-bind-point-type {
                 type string;
                 description
                   "Class-of-service bind point type";
               }
               leaf-list cos-bind-point-owner-type {
                 type string;
                 description
                   "Class-of-service bind point owner type";
               }
               leaf-list cos-bind-point-owner-internal-id {
                 type uint32;
                 description
                   "Junos client internal identifier";
               }
               leaf-list cos-bind-point-name {
                 type string;
                 description
                   "Class-of-service bind point name";
               }
               leaf cos-bind-point-feature {
                 type string;
                 description
                   "Class-of-service bind point feature name";
               }
               leaf cos-bind-point-feature-object-name {
                 type string;
                 description
                   "Class-of-service bind point feature object name";
               }
             }
           }
           container cos-host-outbound-info {
             list cos-host-outbound-traffic-info {
               description
                 "Class-of-service host-outbound-traffic information";
               leaf cos-host-outbound-traffic-protocol-name {
                 type string;
                 description
                   "CoS host outbound traffic protocol name";
               }
               leaf cos-host-outbound-traffic-dscp {
                 type string;
                 description
                   "CoS host outbound traffic dscp";
               }
               leaf cos-host-outbound-traffic-dot1p {
                 type string;
                 description
                   "CoS host outbound traffic ieee 802.1p";
               }
               leaf cos-host-outbound-traffic-fc-id {
                 type string;
                 description
                   "CoS host outbound traffic forwarding class id";
               }
               leaf cos-host-outbound-traffic-queue-id {
                 type string;
                 description
                   "CoS host outbound traffic queue id";
               }
               leaf cos-host-outbound-traffic-restrict-queue-id {
                 type string;
                 description
                   "CoS host outbound traffic restrict queue id";
               }
               leaf cos-host-outbound-traffic-override-firewall {
                 type string;
                 description
                   "CoS host outbound traffic override firwall action";
               }
               leaf cos-host-outbound-traffic-rw-dot1p {
                 type string;
                 description
                   "CoS host outbound traffic - use ieee 802.1p rewrite 
                   rules";
               }
             }
           }
           container cos-drop-congestion-notification-information {
             list cos-drop-congestion-notification-info {
               description
                 "Class-of-service drop-congestion-notification information";
               leaf cos-dcn-fc-name {
                 type string;
                 description
                   "Cos DCN forwarding class";
               }
               leaf cos-dcn-udp-port {
                 type int32;
                 description
                   "Cos DCN udp port number";
               }
             }
             container cos-drop-congestion-notification-dscp-map {
               list cos-drop-congestion-notification-dscp-map-item {
                 leaf trimmable-dscp {
                   type uint32;
                   description
                     "Trimmable DSCP code-point";
                 }
                 leaf trimmed-dscp {
                   type uint32;
                   description
                     "Trimmed DSCP code-point";
                 }
               }
             }
           }
           container cos-dedicated-buffer-profile-information {
             list dedicated-buffer-profile {
               description
                 "Class-of-service dedicated buffer profile";
               leaf dedicated-buffer-profile-name {
                 type string;
                 description
                   "Class-of-service dedicated buffer profile name";
               }
               leaf dedicated-buffer-profile-index {
                 type int32;
                 description
                   "Class-of-service dedicated buffer profile index";
               }
               leaf ingress-buffer-size {
                 type string;
                 description
                   "Ingress per port dedicated buffer in cells";
               }
               leaf egress-buffer-size {
                 type string;
                 description
                   "Egress per port dedicated buffer in cells";
               }
             }
           }
           container cos-dynamic-threshold-profile-information {
             list dynamic-threshold-profile {
               key "dynamic-threshold-profile-name";
               description
                 "Class-of-service dynamic threshold profile";
               leaf dynamic-threshold-profile-name {
                 type string;
                 description
                   "Class-of-service dynamic threshold profile name";
               }
               leaf dynamic-threshold-profile-index {
                 type uint64;
                 description
                   "Class-of-service dynamic threshold profile index";
               }
               list dynamic-threshold-profile-entry {
                 key "dynamic-threshold-profile-priority-group";
                 description
                   "Class-of-service dynamic threshold profile entry";
                 leaf dynamic-threshold-profile-priority-group {
                   type string;
                   description
                     "Class-of-service dynamic threshold profile priority 
                     group";
                 }
                 leaf dynamic-threshold-profile-threshold-value {
                   type uint32;
                   description
                     "Class-of-service dynamic threshold profile threshold 
                     value";
                 }
               }
             }
           }
           container cos-decn-profile-information {
             list decn-profile {
               description
                 "Class-of-service decn profile";
               leaf decn-profile-name {
                 type string;
                 description
                   "Class-of-service decn profile name";
               }
               leaf decn-profile-index {
                 type uint64;
                 description
                   "Class-of-service decn profile index";
               }
               list decn-profile-queue {
                 description
                   "Class-of-service decn profile queue";
                 leaf dynamic-explicit-congestion-notification-queue {
                   type uint32;
                   description
                     "Class-of-service DECN queue";
                 }
                 leaf dynamic-explicit-congestion-notification-offset {
                   type uint32;
                   description
                     "Class-of-service DECN offset";
                 }
                 leaf dynamic-explicit-congestion-notification-floor {
                   type uint32;
                   description
                     "Class-of-service DECN floor";
                 }
               }
             }
           }
           container cos-scheduler-map-information {
             list scheduler-map {
               description
                 "Class-of-service scheduler map";
               leaf scheduler-map-name {
                 type string;
                 description
                   "Class-of-service scheduler map name";
               }
               leaf scheduler-map-index {
                 type uint64;
                 description
                   "Class-of-service scheduler map index";
               }
               leaf user-plane-name {
                 type string;
                 description
                   "Class-of-service user-plane name for XDA";
               }
               list scheduler {
                 leaf scheduler-name {
                   type string;
                   description
                     "Class-of-service scheduler name";
                 }
                 leaf fc-name {
                   type string;
                   description
                     "Class-of-service forwarding class name";
                 }
                 leaf scheduler-index {
                   type uint64;
                   description
                     "Class of service scheduler index";
                 }
                 leaf scheduler-tx-rate {
                   type string;
                   description
                     "Class-of-service scheduler transmit rate";
                 }
                 leaf scheduler-tx-limit {
                   type string;
                   description
                     "Class-of-service scheduler transmit limit";
                 }
                 leaf scheduler-buffer-size {
                   type string;
                   description
                     "Class-of-service scheduler buffer size";
                 }
                 leaf scheduler-buffer-multicast-share {
                   type uint32;
                   description
                     "Class-of-service scheduler multicast buffer share";
                 }
                 leaf scheduler-buffer-limit {
                   type string;
                   description
                     "Class-of-service scheduler buffer limit";
                 }
                 leaf scheduler-buffer-rate {
                   type string;
                   description
                     "Class-of-service scheduler buffer rate";
                 }
                 leaf scheduler-shared-buffer-maximum-percentage {
                   type uint32;
                   description
                     "Shared Buffer maximum percentage";
                 }
                 leaf scheduler-shared-buffer-multicast-maximum-percentage {
                   type uint32;
                   description
                     "Shared Buffer multicast maximum percentage";
                 }
                 leaf scheduler-buffer-dynamic-threshold {
                   type uint32;
                   description
                     "Queue shared-buffer dynamic threshold";
                 }
                 leaf scheduler-priority {
                   type string;
                   description
                     "Class-of-service scheduler priority";
                 }
                 leaf scheduler-shaping-rate {
                   type string;
                   description
                     "Class-of-service scheduler shaping rate";
                 }
                 leaf scheduler-shaping-rate-burst {
                   type string;
                   description
                     "Class-of-service scheduler shaping rate burst";
                 }
                 leaf scheduler-adjust-minimum {
                   type int32;
                   description
                     "Class-of-service scheduler adjustment minimum rate";
                 }
                 leaf scheduler-adjust-percent {
                   type int32;
                   description
                     "Class-of-service scheduler percent adjustment for a 
                     queue";
                 }
                 leaf scheduler-excess-priority {
                   type string;
                   description
                     "Class-of-service scheduler excess priority";
                 }
                 leaf scheduler-excess-rate {
                   type string;
                   description
                     "Class-of-service scheduler excess rate";
                 }
                 leaf scheduler-explicit-congestion-notification {
                   type string;
                   description
                     "Class-of-service ECN status of queue";
                 }
                 leaf scheduler-ecn-rtlog-rate-limit {
                   type uint32;
                   description
                     "Class-of-service ECN Security Log Rate Limit";
                 }
                 leaf scheduler-ecn-no-pfc-assist {
                   type string;
                   description
                     "Class-of-service ECN no pfc assist";
                 }
                 leaf scheduler-latency-ecn {
                   type string;
                   description
                     "Latency based ECN";
                 }
                 leaf scheduler-latency-ecn-threshold {
                   type uint32;
                   description
                     "Latency threshold";
                 }
                 leaf scheduler-queue-monitoring {
                   type string;
                   description
                     "Class-of-service queue depth monitoring of queue";
                 }
                 leaf scheduler-drop-profile-ln-index {
                   type uint32;
                   description
                     "Class-of-service scheduler drop profile index low, 
                     non-TCP";
                 }
                 leaf scheduler-drop-profile-ln {
                   type string;
                   description
                     "Class-of-service scheduler drop profile low, non-TCP";
                 }
                 leaf scheduler-drop-profile-lt-index {
                   type uint32;
                   description
                     "Class-of-service scheduler drop profile index low, TCP";
                 }
                 leaf scheduler-drop-profile-lt {
                   type string;
                   description
                     "Class-of-service scheduler drop profile low, TCP";
                 }
                 leaf scheduler-drop-profile-hn-index {
                   type uint32;
                   description
                     "Class-of-service scheduler drop profile index high, 
                     non-TCP";
                 }
                 leaf scheduler-drop-profile-hn {
                   type string;
                   description
                     "Class-of-service scheduler drop profile high, non-TCP";
                 }
                 leaf scheduler-drop-profile-ht-index {
                   type uint32;
                   description
                     "Class-of-service scheduler drop profile index high, 
                     TCP";
                 }
                 leaf scheduler-drop-profile-ht {
                   type string;
                   description
                     "Class-of-service scheduler drop profile high, TCP";
                 }
                 leaf scheduler-drop-profile-la-index {
                   type uint32;
                   description
                     "Class-of-service scheduler drop profile index low";
                 }
                 leaf scheduler-drop-profile-la {
                   type string;
                   description
                     "Class-of-service scheduler drop profile low";
                 }
                 leaf scheduler-drop-profile-ma-index {
                   type uint32;
                   description
                     "Class-of-service scheduler drop profile index medium";
                 }
                 leaf scheduler-drop-profile-ma {
                   type string;
                   description
                     "Class-of-service scheduler drop profile medium";
                 }
                 leaf scheduler-drop-profile-mla-index {
                   type uint32;
                   description
                     "Class-of-service scheduler drop profile index 
                     medium-low";
                 }
                 leaf scheduler-drop-profile-mla {
                   type string;
                   description
                     "Class-of-service scheduler drop profile medium-low";
                 }
                 leaf scheduler-drop-profile-mha-index {
                   type uint32;
                   description
                     "Class-of-service scheduler drop profile index 
                     medium-high";
                 }
                 leaf scheduler-drop-profile-mha {
                   type string;
                   description
                     "Class-of-service scheduler drop profile medium-high";
                 }
                 leaf scheduler-drop-profile-ha-index {
                   type uint32;
                   description
                     "Class-of-service scheduler drop profile index high";
                 }
                 leaf scheduler-drop-profile-ha {
                   type string;
                   description
                     "Class-of-service scheduler drop profile high";
                 }
               }
             }
           }
           container cos-traffic-control-profile-information {
             list traffic-control-profile {
               description
                 "Information about one or more traffic control profiles";
               leaf traffic-control-profile-name {
                 type string;
                 description
                   "Class-of-service traffic control profile name";
               }
               leaf traffic-control-profile-index {
                 type uint64;
                 description
                   "Index number for Class-of-service traffic control 
                   profile";
               }
               leaf user-plane-name {
                 type string;
                 description
                   "Class-of-service user-plane name for XDA";
               }
               leaf scheduler-map-name {
                 type string;
                 description
                   "Class-of-service scheduler map name";
               }
               leaf atm-service {
                 type string;
                 description
                   "Class-of-service traffic control profile atm service";
               }
               leaf shaping-rate {
                 type uint64;
                 description
                   "Class-of-service shaping rate";
               }
               leaf shaping-rate-burst {
                 type uint32;
                 description
                   "Class-of-service shaping rate burst, in bytes";
               }
               leaf low-granularity {
                 type uint32;
                 description
                   "Class-of-service low-granularity mode support";
               }
               leaf queue-mode-4q {
                 type uint32;
                 description
                   "Class-of-service tcp-voq-mode(4Q) mode support";
               }
               leaf shaping-rate-priority-strict-high {
                 type uint64;
                 description
                   "Class-of-service shaping rate for priority strict high";
               }
               leaf shaping-rate-priority-strict-high-burst {
                 type uint32;
                 description
                   "Class-of-service shaping rate burst for priority 
                   strict-high";
               }
               leaf shaping-rate-priority-high {
                 type uint64;
                 description
                   "Class-of-service shaping rate for priority high";
               }
               leaf shaping-rate-priority-high-burst {
                 type uint32;
                 description
                   "Class-of-service shaping rate for priority high burst";
               }
               leaf shaping-rate-priority-medium {
                 type uint64;
                 description
                   "Class-of-service shaping rate for priority medium";
               }
               leaf shaping-rate-priority-medium-burst {
                 type uint32;
                 description
                   "Class-of-service shaping rate for priority medium burst";
               }
               leaf shaping-rate-priority-medium-low {
                 type uint64;
                 description
                   "Class-of-service shaping rate for priority medium-low";
               }
               leaf shaping-rate-priority-medium-low-burst {
                 type uint32;
                 description
                   "Class-of-service shaping rate burst for priority 
                   medium-low";
               }
               leaf shaping-rate-priority-low {
                 type uint64;
                 description
                   "Class-of-service shaping rate for priority low";
               }
               leaf shaping-rate-priority-low-burst {
                 type uint32;
                 description
                   "Class-of-service shaping rate for priority low burst";
               }
               leaf shaping-rate-excess-high {
                 type uint64;
                 description
                   "Class-of-service shaping rate for excess high";
               }
               leaf shaping-rate-excess-high-burst {
                 type uint32;
                 description
                   "Class-of-service shaping rate for excess high burst";
               }
               leaf shaping-rate-excess-medium-high {
                 type uint64;
                 description
                   "Class-of-service shaping rate for excess medium-high";
               }
               leaf shaping-rate-excess-medium-high-burst {
                 type uint32;
                 description
                   "Class-of-service shaping rate burst for excess 
                   medium-high";
               }
               leaf shaping-rate-excess-medium-low {
                 type uint64;
                 description
                   "Class-of-service shaping rate for excess medium-low";
               }
               leaf shaping-rate-excess-medium-low-burst {
                 type uint32;
                 description
                   "Class-of-service shaping rate burst for excess 
                   medium-low";
               }
               leaf shaping-rate-excess-low {
                 type uint64;
                 description
                   "Class-of-service shaping rate for excess low";
               }
               leaf shaping-rate-excess-low-burst {
                 type uint32;
                 description
                   "Class-of-service shaping rate for excess low burst";
               }
               leaf guaranteed-rate {
                 type uint64;
                 description
                   "Class-of-service guaranteed rate";
               }
               leaf guaranteed-rate-burst {
                 type uint32;
                 description
                   "Class-of-service guaranteed rate burst, in bytes";
               }
               leaf delay-buffer-rate {
                 type uint64;
                 description
                   "Class-of-service delay buffer rate";
               }
               leaf excess-rate {
                 type uint32;
                 description
                   "Class-of-service excess rate";
               }
               leaf excess-rate-high {
                 type uint32;
                 description
                   "Class-of-service excess rate for excess-high priority 
                   traffic";
               }
               leaf excess-rate-medium-high {
                 type uint32;
                 description
                   "Class-of-service excess rate for excess-medium-high 
                   priority traffic";
               }
               leaf excess-rate-medium-low {
                 type uint32;
                 description
                   "Class-of-service excess rate for excess-medium-low 
                   priority traffic";
               }
               leaf excess-rate-low {
                 type uint32;
                 description
                   "Class-of-service excess rate for excess-low priority 
                   traffic";
               }
               leaf adjust-minimum {
                 type uint64;
                 description
                   "Class-of-service adjustment minimum rate";
               }
               leaf overhead-bytes {
                 type int32;
                 description
                   "Class-of-service Overhead bytes";
               }
               leaf frame-mode-bytes {
                 type int32;
                 description
                   "Class-of-service overhead bytes when in frame-mode";
               }
               leaf cell-mode-bytes {
                 type int32;
                 description
                   "Class-of-service overhead bytes when in cell-mode";
               }
               leaf overhead-accounting-mode {
                 type string;
                 description
                   "Class-of-service Overhead Accounting Mode";
               }
               list traffic-control-profile-instance {
                 description
                   "Class-of-service traffic control profile instance";
                 leaf traffic-control-profile-instance-name {
                   type string;
                   description
                     "Class-of-service traffic control profile instance";
                 }
                 leaf traffic-control-profile-instance-index {
                   type uint32;
                   description
                     "Index number for Class-of-service traffic control 
                     profile instance";
                 }
                 leaf instance-reference-count {
                   type uint32;
                   description
                     "Instance reference count";
                 }
               }
             }
           }
           container cos-routing-instance-information {
             list routing-instance-map {
               description
                 "Mapping between class-of-service objects and routing 
                 instances";
               leaf routing-instance-name {
                 type string;
                 description
                   "Name of class-of-service routing instance";
               }
               list i-logical-map {
                 leaf i-logical-name {
                   type string;
                   description
                     "Class-of-service logical interface name";
                 }
                 leaf i-logical-index {
                   type uint32;
                   description
                     "Class-of-service logical interface index";
                 }
                 leaf monitoring-profile-map-name {
                   type string;
                   description
                     "Monitoring Profile Name";
                 }
                 list cos-objects {
                   description
                     "Class-of-service object  mappings";
                   leaf cos-object-type {
                     type string;
                     description
                       "Class-of-service object type";
                   }
                   leaf cos-object-name {
                     type string;
                     description
                       "Class-of-service object name";
                   }
                   leaf cos-object-subtype {
                     type string;
                     description
                       "Class-of-service object subtype";
                   }
                   leaf cos-object-index {
                     type uint64;
                     description
                       "Class-of-service object index";
                   }
                 }
               }
             }
           }
           container cos-fabric-scheduler-map-information {
             container fabric-scheduler-map {
               list fabric-scheduler {
                 leaf fabric-scheduler-name {
                   type string;
                   description
                     "Class-of-service scheduler name";
                 }
                 leaf fabric-scheduler-index {
                   type uint32;
                   description
                     "Class of service scheduler index";
                 }
                 leaf fabric-scheduler-drop-profile-ln-index {
                   type uint32;
                   description
                     "Class-of-service scheduler drop profile index low, 
                     non-TCP";
                 }
                 leaf fabric-scheduler-drop-profile-ln {
                   type string;
                   description
                     "Class-of-service scheduler drop profile low, non-TCP";
                 }
                 leaf fabric-scheduler-drop-profile-lt-index {
                   type uint32;
                   description
                     "Class-of-service scheduler drop profile index low, TCP";
                 }
                 leaf fabric-scheduler-drop-profile-lt {
                   type string;
                   description
                     "Class-of-service scheduler drop profile low, TCP";
                 }
                 leaf fabric-scheduler-drop-profile-hn-index {
                   type uint32;
                   description
                     "Class-of-service scheduler drop profile index high, 
                     non-TCP";
                 }
                 leaf fabric-scheduler-drop-profile-hn {
                   type string;
                   description
                     "Class-of-service scheduler drop profile high, non-TCP";
                 }
                 leaf fabric-scheduler-drop-profile-ht-index {
                   type uint32;
                   description
                     "Class-of-service scheduler drop profile index high, 
                     TCP";
                 }
                 leaf fabric-scheduler-drop-profile-ht {
                   type string;
                   description
                     "Class-of-service scheduler drop profile high, TCP";
                 }
                 leaf fabric-scheduler-priority {
                   type string;
                 }
               }
             }
           }
           container cos-tcm-information {
             list tcm {
               description
                 "Class-of-service traffic-class-map";
               leaf tcm-name {
                 type string;
                 description
                   "Class-of-service traffic-class-map name";
               }
               leaf tcm-type {
                 type string;
                 description
                   "Class-of-service traffic-class-map type";
               }
               leaf table-index {
                 type uint32;
                 description
                   "Table index";
               }
               container tcm-map {
                 list tcm-map-item {
                   leaf code-point {
                     type string;
                     description
                       "Class-of-service code point alias name or bits";
                   }
                   leaf tc-name {
                     type string;
                     description
                       "Class-of-service traffic-class-map traffic-class 
                       name";
                   }
                 }
               }
             }
           }
           container cos-lecn-profile-information {
             list lecn-profile {
               description
                 "Class-of-service lecn profile";
               leaf lecn-profile-name {
                 type string;
                 description
                   "Class-of-service lecn profile name";
               }
               leaf lecn-profile-index {
                 type uint64;
                 description
                   "Class-of-service lecn profile index";
               }
               list lecn-profile-queue {
                 description
                   "Class-of-service lecn profile queue";
                 leaf latency-explicit-congestion-notification-queue {
                   type uint32;
                   description
                     "Class-of-service LECN queue";
                 }
                 leaf latency-explicit-congestion-notification-latency {
                   type uint32;
                   description
                     "Class-of-service LECN latency";
                 }
               }
             }
           }
         }
         container physical-interface-cos-information {
           description
             "Physical interface class-of-service parameters";
           leaf physical-interface-cos-hw-max-queues {
             type int32;
             description
               "Maximum number of class-of-service queues supported by the 
               hardware";
           }
           leaf physical-interface-cos-use-max-queues {
             type int32;
             description
               "Maximum number of usable class-of-service queues";
           }
           leaf physical-interface-schedulers {
             type int32;
             description
               "Schedulers allocated to this interface";
           }
           leaf physical-interface-bypass-queueing-chip {
             type string;
             description
               "Bypass queueing chip enabled on this interface";
           }
           container physical-interface-red-buffer-occupancy {
             description
               "Type of buffer occupancy information used for performing 
               random early drop on the interface";
             leaf instant-usage-weight-exponent {
               type int32;
               description
                 "Weight used for instant buffer usage information for 
                 computing buffer occupancy expressed as a negative 
                 exponent of 2";
             }
           }
         }
         container precl-statistics {
           description
             "Preclassifier Statistics ";
           container precl-information {
             description
               "Preclassifier Statistics";
             container precl-per-class-statistics {
               leaf precl-traffic-class {
                 type string;
                 description
                   "Traffic class";
               }
               leaf precl-rx-packets {
                 type int32;
                 description
                   "Packets received by the preclassifier";
               }
               leaf precl-tx-packets {
                 type int32;
                 description
                   "Packets transmitted by the preclassifier";
               }
               leaf precl-dropped-packets {
                 type int32;
                 description
                   "Packets dropped by the preclassifier";
               }
             }
           }
         }
         container mlfr-uni-nni-traffic-statistics {
           container bundle {
             container multilink-frames {
               description
                 "Link-pic bound frame statistics for multilink bundles and 
                 classes";
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
             container network-frames {
               description
                 "Internet/RE bound frame statistics for multilink bundles 
                 and classes";
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
           }
           container mlfr-uni-nni-link-information {
             leaf active-bundle-links {
               type int32;
               description
                 "Number of active bundle links in this multilink Frame 
                 Relay UNI NNI bundle instance";
             }
             leaf removed-bundle-links {
               type int32;
               description
                 "Number of bundle links that are removed from service in 
                 this multilink Frame Relay UNI NNI bundle instance";
             }
             leaf disabled-bundle-links {
               type int32;
               description
                 "Number of bundle links that are not allowed to transmit in
                 this multilink Frame Relay UNI NNI bundle instance";
             }
           }
           list mlfr-uni-nni-link {
             key "name";
             leaf name {
               type string;
               description
                 "Name of this item";
             }
             leaf down {
               type empty;
               description
                 "Link is down";
             }
             leaf link-uptime {
               type string;
               description
                 "Total uptime for the member link";
             }
             leaf input-frames {
               type int32;
             }
             leaf input-fps {
               type int32;
             }
             leaf input-bytes {
               type int32;
             }
             leaf input-bps {
               type int32;
             }
             leaf output-frames {
               type int32;
             }
             leaf output-fps {
               type int32;
             }
             leaf output-bytes {
               type int32;
             }
             leaf output-bps {
               type int32;
             }
             leaf current-differential-delay {
               type int32;
               description
                 "Current differential delay of this bundle link";
             }
             leaf recent-high-differential-delay {
               type int32;
               description
                 "Recent highest differential delay of this bundle link (in 
                 every 256 measurements)";
             }
             leaf over-red-differential {
               type int32;
               description
                 "Number of times over red differential delay";
             }
             leaf over-yellow-differential {
               type int32;
               description
                 "Number of times over yellow differential delay";
             }
             leaf lip-header-string {
               type string;
               description
                 "Header string of the LIP display";
             }
             leaf rcv-lip-addlink {
               type int32;
               description
                 "Number of LIP ADD_LINKs received";
             }
             leaf rcv-lip-link-ack {
               type int32;
               description
                 "Number of LIP ADD_LINK_ACKs received";
             }
             leaf rcv-lip-link-rej {
               type int32;
               description
                 "Number of LIP ADD_LINK_REJs received";
             }
             leaf rcv-lip-hello {
               type int32;
               description
                 "Number of LIP HELLOs received";
             }
             leaf rcv-lip-hello-ack {
               type int32;
               description
                 "Number of LIP HELLO_ACKs received";
             }
             leaf rcv-lip-link-rem {
               type int32;
               description
                 "Number of LIP LINK_REMOVEs received";
             }
             leaf rcv-lip-rem-ack {
               type int32;
               description
                 "Number of LIP LINK_REMOVE_ACKs received";
             }
             leaf xmt-lip-addlink {
               type int32;
               description
                 "Number of LIP ADD_LINKs transmitted";
             }
             leaf xmt-lip-link-ack {
               type int32;
               description
                 "Number of LIP LINK_ACKs transmitted";
             }
             leaf xmt-lip-link-rej {
               type int32;
               description
                 "Number of LIP LINK_REJs transmitted";
             }
             leaf xmt-lip-hello {
               type int32;
               description
                 "Number of LIP HELLOs transmitted";
             }
             leaf xmt-lip-hello-ack {
               type int32;
               description
                 "Number of LIP HELLO_ACKs transmitted";
             }
             leaf xmt-lip-link-rem {
               type int32;
               description
                 "Number of LIP LINK_REMOVEs transmitted";
             }
             leaf xmt-lip-rem-ack {
               type int32;
               description
                 "Number of LIP LINK_REMOVE_ACKs transmitted";
             }
           }
         }
       }
       list logical-interface {
         key "name";
         description
           "Information about a single logical interface";
         leaf name {
           type string;
           description
             "Name of this item";
         }
         leaf local-index {
           type int32;
           description
             "Local kernel index for this interface";
         }
         leaf snmp-index {
           type int32;
           description
             "SNMP ifIndex for this interface";
         }
         leaf hardware-token {
           type int32;
           description
             "Hardware token for layer 3 ifl";
         }
         leaf generation {
           type int32;
           description
             "Generation number used to distinguish between successive 
             instances of this interface";
         }
         leaf description {
           type string;
           description
             "Description of this interface";
         }
         leaf multilink-flapped {
           type string;
           description
             "Time when the interface last flapped";
         }
         leaf logical-interface-bandwidth {
           type string;
           description
             "Bandwidth of this logical interface";
         }
         leaf link-address {
           type string;
           description
             "Link address on this logical interface";
         }
         leaf encapsulation {
           type string;
           description
             "Encapsulation on the logical interface";
         }
         leaf esi-value {
           type string;
           description
             "Ethernet segment identifier for this interface";
         }
         leaf esi-mode {
           type string;
           description
             "Ethernet segment mode for this interface";
         }
         leaf evpn-multihomed-status {
           type string;
         }
         leaf virtual-gateway-esi-value {
           type string;
           description
             "Ethernet segment identifier for this interface";
         }
         leaf virtual-gateway-esi-mode {
           type string;
           description
             "Ethernet segment mode for this interface";
         }
         leaf interface-set-name {
           type string;
           description
             "Class-of-service interface-set name";
         }
         leaf copy-tos-to-outer-ip-header {
           type string;
           description
             "Flag that enables copying of the value in the ToS field of the
             IP packet's payload header to the delivery header in the 
             generic routingencapsulation packet";
         }
         leaf copy-tos-to-outer-ip-header-transit {
           type string;
           description
             "Flag that enables copying of the value in the ToS field of the
             IP packet's payload header to the delivery header in the 
             generic routing encapsulation transit packet";
         }
         leaf gre-keepalive-configured {
           type string;
           description
             "Gre Keepalives enabled on the logical interface";
         }
         leaf gre-keepalive-adj-state {
           type string;
           description
             "Gre Keepalives enabled on the logical interface";
         }
         leaf demux-table-type {
           type string;
           description
             "Demux table enabled on the logical interface";
         }
         leaf redundant-logical-interface-name {
           type string;
           description
             "Name of the redundant logical interface";
         }
         leaf tenant-name {
           type string;
           description
             "Tenant name assigned to logical interface";
         }
         leaf lcp-state {
           type string;
           description
             "State of the Line Control Protocol";
         }
         leaf chap-state {
           type string;
           description
             "State of the Challenge Handshake Authentication Protocol";
         }
         leaf pap-state {
           type string;
           description
             "State of the Password Authentication Protocol";
         }
         leaf logical-interface-mac {
           type string;
           description
             "MAC on the logical interface";
         }
         leaf logical-interface-vgw-v4-mac {
           type string;
           description
             "MAC on the logical interface";
         }
         leaf logical-interface-vgw-v6-mac {
           type string;
           description
             "MAC on the logical interface";
         }
         leaf vrfname {
           type string;
           description
             "Routing instance name";
         }
         leaf zonename {
           type string;
           description
             "Zone name";
         }
         leaf subunit {
           type int32;
           description
             "Subunit for this interface";
         }
         leaf dialer-time-to-disconnect {
           type string;
           description
             "Time for dialer to disconnect due to idle timeout";
         }
         container if-config-flags {
           leaf iff-none {
             type empty;
           }
           leaf iff-hardware-down {
             type empty;
           }
           leaf iff-down {
             type empty;
           }
           leaf iff-up {
             type empty;
           }
           leaf iff-admin-down {
             type empty;
           }
           leaf iff-admin-up {
             type empty;
           }
           leaf iff-link-down {
             type empty;
           }
           leaf iff-device-down {
             type empty;
           }
           leaf iff-point-to-point {
             type empty;
           }
           leaf iff-point-to-multipoint {
             type empty;
           }
           leaf plp-to-clp {
             type empty;
           }
           leaf iff-multiaccess {
             type empty;
           }
           leaf iff-change {
             type empty;
           }
           leaf iff-inverse-arp {
             type empty;
           }
           leaf iff-no-multicast {
             type empty;
           }
           leaf iff-multicast {
             type empty;
           }
           leaf iff-promiscuous {
             type empty;
           }
           leaf iff-all-multicast {
             type empty;
           }
           leaf iff-snmp-traps {
             type empty;
           }
           leaf iff-rx-passive {
             type empty;
           }
           leaf iff-tx-passive {
             type empty;
           }
           leaf iff-ccc-down {
             type empty;
           }
           leaf iff-clear-df {
             type empty;
           }
           leaf iff-tunnel-reassembly {
             type empty;
           }
           leaf iff-acfc {
             type empty;
           }
           leaf iff-pfc {
             type empty;
           }
           leaf iff-rdd {
             type empty;
           }
           leaf iff-looped {
             type empty;
           }
           leaf iff-framing-conflict {
             type empty;
           }
           leaf internal-flags {
             type int32;
             description
               "Hexadecimal value of internal flag bits";
           }
         }
         container layer2-input-policer-information {
           description
             "Information about Layer 2 input policer for interface";
           leaf layer2-input-policer {
             type string;
             description
               "Name of the Layer 2 input policer";
           }
         }
         container layer2-output-policer-information {
           description
             "Information about Layer 2 output policer for interface";
           leaf layer2-output-policer {
             type string;
             description
               "Name of the Layer 2 output policer";
           }
         }
         container atm-input-policer-information {
           description
             "Information about atm input policer for interface";
           leaf atm-input-policer {
             type string;
             description
               "Name of the atm input policer";
           }
         }
         container pppoe-information {
           description
             "PPPoE information";
           list pppoe-interface {
             leaf state {
               type string;
               description
                 "State";
             }
             leaf session-id {
               type string;
               description
                 "Session ID";
             }
             leaf ac-name-session {
               type string;
               description
                 "Session AC name";
             }
             leaf remote-mac {
               type string;
               description
                 "Remote MAC address";
             }
             leaf ac-name-config {
               type string;
               description
                 "Configured AC name";
             }
             leaf service-name {
               type string;
               description
                 "Service name";
             }
             leaf auto-reconnect {
               type string;
               description
                 "Autoreconnect timeout";
             }
             leaf idle-timeout {
               type string;
               description
                 "Idle timeout";
             }
             leaf underlying-interface-name {
               type string;
               description
                 "Underlying interface name";
             }
             leaf underlying-interface-index {
               type string;
               description
                 "Underlying interface index";
             }
             leaf padg-credits {
               type int32;
               description
                 "PADG transmit credits";
             }
             leaf pppoe-credit-scale-factor {
               type string;
               description
                 "Scaling factor";
             }
             leaf ignore-eol-tag {
               type string;
               description
                 "Ignore End-of-List TAG";
             }
             leaf ppp-max-payload-tag {
               type int32;
               description
                 "PPP-Max-Payload TAG";
             }
             leaf interface-name {
               type string;
               description
                 "Class-of-service interface name";
             }
             leaf interface-index {
               type uint32;
               description
                 "Class-of-service interface index";
             }
             leaf aci-iflset-name {
               type string;
               description
                 "ACI Interface Set name";
             }
             leaf aci-iflset-index {
               type string;
               description
                 "ACI Interface Set index";
             }
             leaf ifl-type {
               type string;
               description
                 "Type";
             }
             leaf session-uptime {
               type string;
               description
                 "Duration for which the session has been up";
             }
             leaf dynamic-profile {
               type string;
               description
                 "Dynamic Profile name";
             }
             leaf pppoe-credits {
               type string;
               description
                 "Forwarding credit balances";
             }
             leaf dynamic-interface-bandwidth {
               type string;
               description
                 "Dynamic interface bandwidth";
             }
             leaf agent-circuit-id {
               type string;
               description
                 "Agent Circuit ID";
             }
             leaf agent-remote-id {
               type string;
               description
                 "Agent Remote ID";
             }
             leaf padm-motm {
               type string;
               description
                 "PADM Message of the Moment tag";
             }
             leaf padm-hurl {
               type string;
               description
                 "PADM HTTP URL tag";
             }
           }
         }
         container pppoe-underlying-information {
           description
             "PPPoE Underlying information";
           list pppoe-underlying-interface {
             leaf dynamic-profile {
               type string;
               description
                 "Dynamic Profile name";
             }
             leaf service-name-table {
               type string;
               description
                 "Name of Service Name Table";
             }
             leaf max-sessions {
               type int32;
               description
                 "Maximum number of PPPoE sessions";
             }
             leaf max-sessions-vsa-ignore {
               type string;
               description
                 "Ignore max-sessions VSA";
             }
             leaf duplicate-protection {
               type string;
               description
                 "Duplicate protection mode";
             }
             leaf short-cycle-protection {
               type string;
               description
                 "Short cycle protection mode";
             }
             leaf direct-connect {
               type string;
               description
                 "Direct connect mode";
             }
             leaf ac-name {
               type string;
               description
                 "Access Concentrator name";
             }
             leaf underlying-interface-name {
               type string;
               description
                 "Underlying interface name";
             }
             leaf underlying-interface-index {
               type string;
               description
                 "Underlying interface index";
             }
             leaf encapsulation-type-identifier {
               type string;
               description
                 "Encapsulation type identifier";
             }
             leaf state {
               type string;
               description
                 "State";
             }
             leaf active-sessions {
               type int32;
               description
                 "Number of active PPPoE sessions";
             }
             leaf aci-autosensing {
               type string;
               description
                 "ACI VLAN Autosensing mode";
             }
             leaf line-identity-autosensing {
               type string;
               description
                 "Line Identity Autosensing mode";
             }
           }
         }
         container aci-vlan-information {
           leaf dynamic-profile {
             type string;
             description
               "Dynamic Profile name";
           }
         }
         container line-identity-information {
           leaf dynamic-profile {
             type string;
             description
               "Dynamic Profile name";
           }
           leaf circuit-id {
             type string;
             description
               "Aci vlan attribute";
           }
           leaf remote-id {
             type string;
             description
               "Aci vlan attribute";
           }
           leaf accept-no-ids {
             type string;
             description
               "Aci vlan attribute";
           }
         }
         container demux-information {
           description
             "Demux information";
           container demux-interface {
             leaf demux-underlying-interface-name {
               type string;
               description
                 "Underlying interface name";
             }
             leaf demux-underlying-interface-index {
               type string;
               description
                 "Underlying interface index";
             }
             leaf demux-inet-prefix-type {
               type string;
               description
                 "Prefix type";
             }
             leaf demux-inet-prefix-count {
               type string;
               description
                 "IPv4 Prefix count";
             }
             leaf demux-inet-prefix {
               type string;
               description
                 "IPv4 Prefix";
             }
             leaf demux-inet6-prefix-type {
               type string;
               description
                 "Prefix type";
             }
             leaf demux-inet6-prefix-count {
               type string;
               description
                 "IPv6 Prefix count";
             }
             leaf demux-inet6-prefix {
               type string;
               description
                 "IPv6 Prefix";
             }
           }
         }
         container dual-ad-icl-color-information {
           container dual-ad-icl-color-info {
             description
               "Dual-AD ICL Color Information";
             leaf dual-ad-icl-color-type {
               type uint32;
               description
                 "Dual-AD ICL Color Type";
             }
             leaf dual-ad-icl-color {
               type uint32;
               description
                 "Dual-AD ICL Color";
             }
           }
         }
         container dialer-information {
           description
             "Dialer information";
           leaf dialer-time-to-disconnect {
             type string;
             description
               "Time for dialer to disconnect due to idle timeout";
           }
           container dialer-interface {
             leaf dialer-interface-name {
               type string;
               description
                 "Interface name";
             }
             leaf dialer-interface-state {
               type string;
               description
                 "Dialer interface state";
             }
             leaf pool-id {
               type string;
               description
                 "Pool identifier";
             }
             leaf primary-interface {
               type string;
               description
                 "Primary interface";
             }
             leaf activation-delay {
               type string;
               description
                 "Activation delay";
             }
             leaf deactivation-delay {
               type string;
               description
                 "Deactivation delay";
             }
             leaf activation-delay-elapsed {
               type string;
               description
                 "Activation delay elapsed";
             }
             leaf deactivation-delay-elapsed {
               type string;
               description
                 "Deactivation delay elapsed";
             }
             leaf call-idle-timeout {
               type string;
               description
                 "Call idle timeout";
             }
             leaf initial-route-check {
               type string;
               description
                 "Initial route check delay";
             }
             leaf redial-delay {
               type string;
               description
                 "Delay before dialer dials out again (seconds)";
             }
             leaf callback-wait-period {
               type string;
               description
                 "Delay before dialer attempts callback (seconds)";
             }
             leaf callback-wait-period-elapsed {
               type string;
               description
                 "Number of seconds in callback wait period that have 
                 elapsed";
             }
             leaf load-threshold {
               type string;
               description
                 "Load threshold that determines when interfaces are added 
                 to bundle";
             }
             leaf load-interval {
               type string;
               description
                 "Interval over which average load is calculated";
             }
             container dialer-interface-flags {
               description
                 "Flags indicating interface configuration";
               leaf backup {
                 type empty;
                 description
                   "Dialer backup";
               }
               leaf multilink {
                 type empty;
                 description
                   "Dialer multilink";
               }
               leaf watchlist {
                 type empty;
                 description
                   "Dialer watchlist";
               }
               leaf interesting-detected {
                 type empty;
                 description
                   "Interesting packet detected";
               }
             }
           }
         }
         container shared-interface-information {
           description
             "Shared interface information";
           container shared-interface-logical-interface {
             description
               "Shared interface logical interface";
             leaf peer-interface-name {
               type string;
               description
                 "Peer interface name";
             }
             leaf interface-shared-with {
               type string;
               description
                 "Logical interface owner";
             }
             leaf rx-fe {
               type string;
               description
                 "Rx tunnel token forwarding element";
             }
             leaf rx-nhid {
               type string;
               description
                 "Rx tunnel token next hop index";
             }
             leaf tx-fe {
               type string;
               description
                 "Tx tunnel token forwarding element";
             }
             leaf tx-nhid {
               type string;
               description
                 "Tx tunnel token next hop index";
             }
           }
         }
         container mac-database {
           list mac-record {
             leaf mac-address {
               type jt:mac-addr;
             }
             leaf receive-frames {
               type int32;
             }
             leaf receive-bytes {
               type int32;
             }
             leaf transmit-frames {
               type int32;
             }
             leaf transmit-bytes {
               type int32;
             }
           }
         }
         container policer-overhead {
           description
             "Policer overhead information";
           leaf ingress-policer-overhead {
             type int32;
             description
               "Ingress policer overhead information";
           }
           leaf egress-policer-overhead {
             type int32;
             description
               "Egress policer overhead information";
           }
         }
         container queue-counters {
           description
             "Queue counter statistics";
           leaf queue-counters-error-message {
             type string;
             description
               "Queue statistics not available for this interface";
           }
           list queue {
             description
               "Counters for a single queue";
             leaf queue-number {
               type int32;
               description
                 "Queue number";
             }
             leaf queue-counters-queued-packets {
               type uint64;
               description
                 "Queued packet count";
             }
             leaf queue-counters-trans-packets {
               type uint64;
               description
                 "Total number of transmitted packets";
             }
             leaf queue-counters-total-drop-packets {
               type uint64;
               description
                 "Number of total packets dropped at the queue";
             }
             leaf forwarding-class-name {
               type string;
               description
                 "Forwarding class name associated with queue";
             }
             leaf queue-counters-queued-packets-rate {
               type uint64;
               description
                 "Rate at which packets are queued";
             }
             leaf queue-counters-queued-bytes {
               type uint64;
               description
                 "Queued bytes count";
             }
             leaf queue-counters-queued-bytes-rate {
               type uint64;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets-rate {
               type uint64;
               description
                 "Rate at which packets are transmitted";
             }
             leaf queue-counters-trans-bytes {
               type uint64;
               description
                 "Total number of transmitted bytes";
             }
             leaf queue-counters-trans-bytes-rate {
               type uint64;
               description
                 "Rate at which bytes are transmitted";
             }
             leaf queue-counters-tail-drop-packets-na {
               type string;
               description
                 "Number of packets dropped due to tail drop not available";
             }
             leaf queue-counters-tail-drop-packets {
               type uint64;
               description
                 "Number of packets dropped at the tail of the queue";
             }
             leaf queue-counters-tail-drop-packets-rate {
               type uint64;
               description
                 "Rate at which packets are dropped at tail of queue";
             }
             leaf queue-counters-tail-drop-bytes {
               type uint64;
               description
                 "Number of packets dropped at tail drop of the queue";
             }
             leaf queue-counters-tail-drop-bytes-rate {
               type uint64;
               description
                 "Number of packets dropped at tail drop of the queue";
             }
             leaf queue-counters-rate-limit-drop-packets-na {
               type string;
               description
                 "Number of packets dropped due to rate-limit drop not 
                 available";
             }
             leaf queue-counters-rate-limit-drop-packets {
               type uint64;
               description
                 "Number of packets dropped by rate-limit for the queue";
             }
             leaf queue-counters-rate-limit-drop-packets-rate {
               type uint64;
               description
                 "Rate at which packets are dropped by rate-limit for the 
                 queue";
             }
             leaf queue-counters-rate-limit-drop-bytes-na {
               type string;
               description
                 "Number of bytes dropped due to tail drop not available";
             }
             leaf queue-counters-rate-limit-drop-bytes {
               type uint64;
               description
                 "Number of bytes dropped at the tail of the queue";
             }
             leaf queue-counters-rate-limit-drop-bytes-rate {
               type uint64;
               description
                 "Rate at which bytes are dropped at the tail of the queue";
             }
             leaf queue-counters-red-packets-na {
               type string;
               description
                 "Number of packets dropped due to RED not available";
             }
             leaf queue-counters-red-packets {
               type uint64;
               description
                 "Number of packets dropped due to RED";
             }
             leaf queue-counters-red-packets-rate {
               type uint64;
               description
                 "Rate at which packets are dropped due to RED";
             }
             leaf queue-counters-red-packets-ln {
               type uint64;
               description
                 "Number of RED dropped low-loss, non-TCP packets";
             }
             leaf queue-counters-red-packets-rate-ln {
               type uint64;
               description
                 "RED drop rate for low-loss, non-TCP packets";
             }
             leaf queue-counters-red-packets-lt {
               type uint64;
               description
                 "Number of RED dropped of low-loss, TCP packets";
             }
             leaf queue-counters-red-packets-rate-lt {
               type uint64;
               description
                 "RED drop rate for low-loss, TCP packets";
             }
             leaf queue-counters-red-packets-hn {
               type uint64;
               description
                 "Number of RED dropped high-loss, non-TCP packets";
             }
             leaf queue-counters-red-packets-rate-hn {
               type uint64;
               description
                 "RED drop rate for high-loss, non-TCP packets";
             }
             leaf queue-counters-red-packets-ht {
               type uint64;
               description
                 "Number of RED dropped high-loss, TCP packets";
             }
             leaf queue-counters-red-packets-rate-ht {
               type uint64;
               description
                 "RED drop rate for high-loss, TCP packets";
             }
             leaf queue-counters-red-packets-low {
               type uint64;
               description
                 "Number of RED dropped low-loss packets";
             }
             leaf queue-counters-red-packets-rate-low {
               type uint64;
               description
                 "RED drop rate for low-loss packets";
             }
             leaf queue-counters-red-packets-medium-low {
               type uint64;
               description
                 "Number of RED dropped medium-low-loss packets";
             }
             leaf queue-counters-red-packets-rate-medium-low {
               type uint64;
               description
                 "RED drop rate for medium-low-loss packets";
             }
             leaf queue-counters-red-packets-medium-high {
               type uint64;
               description
                 "Number of RED dropped medium-high-loss packets";
             }
             leaf queue-counters-red-packets-rate-medium-high {
               type uint64;
               description
                 "RED drop rate for medium-high-loss packets";
             }
             leaf queue-counters-red-packets-medium {
               type uint64;
               description
                 "Number of RED dropped medium-loss packets";
             }
             leaf queue-counters-red-packets-rate-medium {
               type uint64;
               description
                 "RED drop rate for medium-loss packets";
             }
             leaf queue-counters-red-packets-high {
               type uint64;
               description
                 "Number of RED dropped high-loss packets";
             }
             leaf queue-counters-red-packets-rate-high {
               type uint64;
               description
                 "RED drop rate for high-loss packets";
             }
             leaf queue-counters-red-bytes-na {
               type string;
               description
                 "Number of bytes dropped due to RED not available";
             }
             leaf queue-counters-red-bytes {
               type uint64;
               description
                 "Number of bytes dropped due to RED";
             }
             leaf queue-counters-red-bytes-rate {
               type uint64;
               description
                 "Rate at which bytes are dropped due to RED";
             }
             leaf queue-counters-red-bytes-ln {
               type uint64;
               description
                 "Number of RED dropped low-loss, non-TCP bytes";
             }
             leaf queue-counters-red-bytes-rate-ln {
               type uint64;
               description
                 "RED drop rate for low-loss, non-TCP bytes";
             }
             leaf queue-counters-red-bytes-lt {
               type uint64;
               description
                 "Number of RED dropped low-loss, TCP bytes";
             }
             leaf queue-counters-red-bytes-rate-lt {
               type uint64;
               description
                 "RED drop rate for low-loss, TCP bytes";
             }
             leaf queue-counters-red-bytes-hn {
               type uint64;
               description
                 "Number of RED dropped high-loss, non-TCP bytes";
             }
             leaf queue-counters-red-bytes-rate-hn {
               type uint64;
               description
                 "RED drop rate for high-loss, non-TCP bytes";
             }
             leaf queue-counters-red-bytes-ht {
               type uint64;
               description
                 "Number of RED dropped high-loss, TCP bytes";
             }
             leaf queue-counters-red-bytes-rate-ht {
               type uint64;
               description
                 "RED drop rate for high-loss, TCP bytes";
             }
             leaf queue-counters-red-bytes-low {
               type uint64;
               description
                 "Number of RED dropped low-loss bytes";
             }
             leaf queue-counters-red-bytes-rate-low {
               type uint64;
               description
                 "RED drop rate for low-loss bytes";
             }
             leaf queue-counters-red-bytes-medium-low {
               type uint64;
               description
                 "Number of RED dropped medium-low-loss bytes";
             }
             leaf queue-counters-red-bytes-rate-medium-low {
               type uint64;
               description
                 "RED drop rate for medium-low-loss bytes";
             }
             leaf queue-counters-red-bytes-medium-high {
               type uint64;
               description
                 "Number of RED dropped medium-high-loss bytes";
             }
             leaf queue-counters-red-bytes-rate-medium-high {
               type uint64;
               description
                 "RED drop rate for medium-high-loss bytes";
             }
             leaf queue-counters-red-bytes-medium {
               type uint64;
               description
                 "Number of RED dropped medium-loss bytes";
             }
             leaf queue-counters-red-bytes-rate-medium {
               type uint64;
               description
                 "RED drop rate for medium-loss bytes";
             }
             leaf queue-counters-red-bytes-high {
               type uint64;
               description
                 "Number of RED dropped high-loss bytes";
             }
             leaf queue-counters-red-bytes-rate-high {
               type uint64;
               description
                 "RED drop rate for high-loss bytes";
             }
             leaf queue-counters-timestamp {
               type uint64;
               description
                 "Last packet enqueued timestamp";
             }
             leaf queue-counters-total-drop-packets-rate {
               type uint64;
               description
                 "Number of total packets dropped at the queue";
             }
             leaf queue-counters-total-drop-bytes {
               type uint64;
               description
                 "Number of total packets dropped at the queue";
             }
             leaf queue-counters-total-drop-bytes-rate {
               type uint64;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-short-summary {
             description
               "Summary of queue information on an interface";
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
         }
         container ingress-queue-counters {
           description
             "Ingress queue counter statistics";
           list queue {
             description
               "Counters for a single queue";
             leaf queue-number {
               type int32;
               description
                 "Queue number";
             }
             leaf forwarding-class-name {
               type string;
               description
                 "Forwarding class name associated with queue";
             }
             leaf queue-counters-queued-packets {
               type uint64;
               description
                 "Queued packet count";
             }
             leaf queue-counters-queued-packets-rate {
               type uint64;
               description
                 "Rate at which packets are queued";
             }
             leaf queue-counters-queued-bytes {
               type uint64;
               description
                 "Queued bytes count";
             }
             leaf queue-counters-queued-bytes-rate {
               type uint64;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets {
               type uint64;
               description
                 "Total number of transmitted packets";
             }
             leaf queue-counters-trans-packets-rate {
               type uint64;
               description
                 "Rate at which packets are transmitted";
             }
             leaf queue-counters-trans-bytes {
               type uint64;
               description
                 "Total number of transmitted bytes";
             }
             leaf queue-counters-trans-bytes-rate {
               type uint64;
               description
                 "Rate at which bytes are transmitted";
             }
             leaf queue-counters-tail-drop-packets-na {
               type string;
               description
                 "Number of packets dropped due to tail drop not available";
             }
             leaf queue-counters-tail-drop-packets {
               type uint64;
               description
                 "Number of packets dropped at the tail of the queue";
             }
             leaf queue-counters-tail-drop-packets-rate {
               type uint64;
               description
                 "Rate at which packets are dropped at tail of queue";
             }
             leaf queue-counters-tail-drop-bytes {
               type uint64;
               description
                 "Number of packets dropped at tail drop of the queue";
             }
             leaf queue-counters-tail-drop-bytes-rate {
               type uint64;
               description
                 "Number of packets dropped at tail drop of the queue";
             }
             leaf queue-counters-rate-limit-drop-packets-na {
               type string;
               description
                 "Number of packets dropped due to rate-limit drop not 
                 available";
             }
             leaf queue-counters-rate-limit-drop-packets {
               type uint64;
               description
                 "Number of packets dropped by rate-limit for the queue";
             }
             leaf queue-counters-rate-limit-drop-packets-rate {
               type uint64;
               description
                 "Rate at which packets are dropped by rate-limit for the 
                 queue";
             }
             leaf queue-counters-rate-limit-drop-bytes-na {
               type string;
               description
                 "Number of bytes dropped due to tail drop not available";
             }
             leaf queue-counters-rate-limit-drop-bytes {
               type uint64;
               description
                 "Number of bytes dropped at the tail of the queue";
             }
             leaf queue-counters-rate-limit-drop-bytes-rate {
               type uint64;
               description
                 "Rate at which bytes are dropped at the tail of the queue";
             }
             leaf queue-counters-red-packets-na {
               type string;
               description
                 "Number of packets dropped due to RED not available";
             }
             leaf queue-counters-red-packets {
               type uint64;
               description
                 "Number of packets dropped due to RED";
             }
             leaf queue-counters-red-packets-rate {
               type uint64;
               description
                 "Rate at which packets are dropped due to RED";
             }
             leaf queue-counters-red-packets-ln {
               type uint64;
               description
                 "Number of RED dropped low-loss, non-TCP packets";
             }
             leaf queue-counters-red-packets-rate-ln {
               type uint64;
               description
                 "RED drop rate for low-loss, non-TCP packets";
             }
             leaf queue-counters-red-packets-lt {
               type uint64;
               description
                 "Number of RED dropped of low-loss, TCP packets";
             }
             leaf queue-counters-red-packets-rate-lt {
               type uint64;
               description
                 "RED drop rate for low-loss, TCP packets";
             }
             leaf queue-counters-red-packets-hn {
               type uint64;
               description
                 "Number of RED dropped high-loss, non-TCP packets";
             }
             leaf queue-counters-red-packets-rate-hn {
               type uint64;
               description
                 "RED drop rate for high-loss, non-TCP packets";
             }
             leaf queue-counters-red-packets-ht {
               type uint64;
               description
                 "Number of RED dropped high-loss, TCP packets";
             }
             leaf queue-counters-red-packets-rate-ht {
               type uint64;
               description
                 "RED drop rate for high-loss, TCP packets";
             }
             leaf queue-counters-red-packets-low {
               type uint64;
               description
                 "Number of RED dropped low-loss packets";
             }
             leaf queue-counters-red-packets-rate-low {
               type uint64;
               description
                 "RED drop rate for low-loss packets";
             }
             leaf queue-counters-red-packets-medium-low {
               type uint64;
               description
                 "Number of RED dropped medium-low-loss packets";
             }
             leaf queue-counters-red-packets-rate-medium-low {
               type uint64;
               description
                 "RED drop rate for medium-low-loss packets";
             }
             leaf queue-counters-red-packets-medium-high {
               type uint64;
               description
                 "Number of RED dropped medium-high-loss packets";
             }
             leaf queue-counters-red-packets-rate-medium-high {
               type uint64;
               description
                 "RED drop rate for medium-high-loss packets";
             }
             leaf queue-counters-red-packets-medium {
               type uint64;
               description
                 "Number of RED dropped medium-loss packets";
             }
             leaf queue-counters-red-packets-rate-medium {
               type uint64;
               description
                 "RED drop rate for medium-loss packets";
             }
             leaf queue-counters-red-packets-high {
               type uint64;
               description
                 "Number of RED dropped high-loss packets";
             }
             leaf queue-counters-red-packets-rate-high {
               type uint64;
               description
                 "RED drop rate for high-loss packets";
             }
             leaf queue-counters-red-bytes-na {
               type string;
               description
                 "Number of bytes dropped due to RED not available";
             }
             leaf queue-counters-red-bytes {
               type uint64;
               description
                 "Number of bytes dropped due to RED";
             }
             leaf queue-counters-red-bytes-rate {
               type uint64;
               description
                 "Rate at which bytes are dropped due to RED";
             }
             leaf queue-counters-red-bytes-ln {
               type uint64;
               description
                 "Number of RED dropped low-loss, non-TCP bytes";
             }
             leaf queue-counters-red-bytes-rate-ln {
               type uint64;
               description
                 "RED drop rate for low-loss, non-TCP bytes";
             }
             leaf queue-counters-red-bytes-lt {
               type uint64;
               description
                 "Number of RED dropped low-loss, TCP bytes";
             }
             leaf queue-counters-red-bytes-rate-lt {
               type uint64;
               description
                 "RED drop rate for low-loss, TCP bytes";
             }
             leaf queue-counters-red-bytes-hn {
               type uint64;
               description
                 "Number of RED dropped high-loss, non-TCP bytes";
             }
             leaf queue-counters-red-bytes-rate-hn {
               type uint64;
               description
                 "RED drop rate for high-loss, non-TCP bytes";
             }
             leaf queue-counters-red-bytes-ht {
               type uint64;
               description
                 "Number of RED dropped high-loss, TCP bytes";
             }
             leaf queue-counters-red-bytes-rate-ht {
               type uint64;
               description
                 "RED drop rate for high-loss, TCP bytes";
             }
             leaf queue-counters-red-bytes-low {
               type uint64;
               description
                 "Number of RED dropped low-loss bytes";
             }
             leaf queue-counters-red-bytes-rate-low {
               type uint64;
               description
                 "RED drop rate for low-loss bytes";
             }
             leaf queue-counters-red-bytes-medium-low {
               type uint64;
               description
                 "Number of RED dropped medium-low-loss bytes";
             }
             leaf queue-counters-red-bytes-rate-medium-low {
               type uint64;
               description
                 "RED drop rate for medium-low-loss bytes";
             }
             leaf queue-counters-red-bytes-medium-high {
               type uint64;
               description
                 "Number of RED dropped medium-high-loss bytes";
             }
             leaf queue-counters-red-bytes-rate-medium-high {
               type uint64;
               description
                 "RED drop rate for medium-high-loss bytes";
             }
             leaf queue-counters-red-bytes-medium {
               type uint64;
               description
                 "Number of RED dropped medium-loss bytes";
             }
             leaf queue-counters-red-bytes-rate-medium {
               type uint64;
               description
                 "RED drop rate for medium-loss bytes";
             }
             leaf queue-counters-red-bytes-high {
               type uint64;
               description
                 "Number of RED dropped high-loss bytes";
             }
             leaf queue-counters-red-bytes-rate-high {
               type uint64;
               description
                 "RED drop rate for high-loss bytes";
             }
             leaf queue-counters-timestamp {
               type uint64;
               description
                 "Last packet enqueued timestamp";
             }
             leaf queue-counters-total-drop-packets {
               type uint64;
               description
                 "Number of total packets dropped at the queue";
             }
             leaf queue-counters-total-drop-packets-rate {
               type uint64;
               description
                 "Number of total packets dropped at the queue";
             }
             leaf queue-counters-total-drop-bytes {
               type uint64;
               description
                 "Number of total packets dropped at the queue";
             }
             leaf queue-counters-total-drop-bytes-rate {
               type uint64;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
           container interface-cos-short-summary {
             description
               "Summary of queue information on an interface";
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           container queue-num-forwarding-class-name-map {
             leaf queue-number {
               type int32;
               description
                 "Queue number";
             }
             leaf forwarding-class-name {
               type string;
               description
                 "Forwarding class name associated with queue";
             }
           }
         }
         container forwarding-class-counters {
           description
             "Forwarding-class counter statistics";
           leaf forwarding-class-counters-error-message {
             type string;
             description
               "Forwarding-class statistics not available for this interface";
           }
           container ipv4-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container ipv6-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container mpls-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container layer2-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container other-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container protocol-aggregate-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container forwarding-class-statistics {
             container protocol-aggregate-forwarding-class-counters {
             }
             container ipv4-forwarding-class-counters {
             }
             container ipv6-forwarding-class-counters {
             }
             container mpls-forwarding-class-counters {
             }
             container layer2-forwarding-class-counters {
             }
             container other-forwarding-class-counters {
             }
           }
           container forwarding-class-accounting-parameters {
             leaf forwarding-class-accounting-for-protocol {
               type string;
             }
             leaf forwarding-class-accounting-for-traffic-direction {
               type string;
             }
             leaf forwarding-class-accounting-for-traffic-type {
               type string;
             }
             leaf forwarding-class-accounting-overhead-bytes {
               type uint32;
             }
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container multilink-bundle-link-information {
           leaf multilink-active-bundle-links {
             type int32;
             description
               "Number of active bundle links in this multilink bundle 
               instance";
           }
           leaf multilink-removed-bundle-links {
             type int32;
             description
               "Number of bundle links that are removed from service in this
               multilink bundle instance";
           }
           leaf multilink-disabled-bundle-links {
             type int32;
             description
               "Number of bundle links that are not allowed to transmit in 
               this multilink bundle instance";
           }
         }
         container multilink-bundle-options {
           leaf mrru {
             type int32;
           }
           leaf remote-mrru {
             type int32;
             description
               "Remote max received reconstructed unit";
           }
           leaf drop-timeout {
             type int32;
           }
           leaf mlppp-inner-ppp-pfc {
             type string;
             description
               "MLPPP inner PPP protocol field compression";
           }
           leaf sequence-number-format {
             type string;
           }
           leaf ml-fragment-threshold {
             type int32;
           }
           leaf minimum-links {
             type int32;
           }
           leaf interleave-fragments {
             type string;
           }
           leaf multilink-classes {
             type int32;
             description
               "Number of multilink classes";
           }
           leaf link-layer-overhead {
             type string;
             description
               "Link layer overhead";
           }
           leaf filler-packet-interval {
             type int32;
           }
         }
         container multilink-bundle-errors {
           description
             "Multilink bundle errors";
           leaf packet-drops {
             type int32;
             description
               "Number of packets dropped";
           }
           leaf packet-drop-bytes {
             type int32;
             description
               "Number of bytes in dropped packets";
           }
           leaf fragment-drops {
             type int32;
             description
               "Number of fragments dropped";
           }
           leaf fragment-drop-bytes {
             type int32;
             description
               "Number of bytes in dropped fragments";
           }
           leaf mrru-exceeded {
             type int32;
             description
               "Number of assembled packets that exceeded MRRU";
           }
           leaf processing-errors {
             type int32;
             description
               "Number of errors encountered in assembling packets";
           }
         }
         container multilink-traffic-statistics {
           container bundle {
             container multilink-frames {
               description
                 "Link-pic bound frame statistics for multilink bundles and 
                 classes";
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
             container network-frames {
               description
                 "Internet/RE bound frame statistics for multilink bundles 
                 and classes";
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
             container network-v6-frames {
               description
                 "Transit IPV6 statistics for multilink bundles";
               leaf inputv6-packets {
                 type int32;
               }
               leaf inputv6-bytes {
                 type int32;
               }
               leaf outputv6-packets {
                 type int32;
               }
               leaf outputv6-bytes {
                 type int32;
               }
             }
           }
           container class {
             description
               "Multilink class traffic statistics";
             container class-info {
               description
                 "Multilink class information";
               leaf multilink-class-id {
                 type int32;
                 description
                   "Multilink class ID";
               }
             }
             container multilink-frames {
               description
                 "Link-pic bound frame statistics for multilink bundles and 
                 classes";
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
             container network-frames {
               description
                 "Internet/RE bound frame statistics for multilink bundles 
                 and classes";
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
           }
           list link {
             key "name";
             leaf name {
               type string;
               description
                 "Name of this item";
             }
             leaf down {
               type empty;
               description
                 "Link is down";
             }
             leaf link-uptime {
               type string;
               description
                 "Total uptime for the member link";
             }
             leaf input-frames {
               type int32;
             }
             leaf input-fps {
               type int32;
             }
             leaf input-bytes {
               type int32;
             }
             leaf input-bps {
               type int32;
             }
             leaf output-frames {
               type int32;
             }
             leaf output-fps {
               type int32;
             }
             leaf output-bytes {
               type int32;
             }
             leaf output-bps {
               type int32;
             }
           }
           container multilink-detail-statistics {
             container bundle-detail {
               container fragments {
                 description
                   "Fragment statistics for multilink bundles and classes";
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
               container non-fragments {
                 description
                   "Non-fragment statistics for multilink bundles and 
                   classes";
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
               container lfi {
                 description
                   "LFI frame statistics for multilink bundles and classes";
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
             }
             container class-detail {
               container class-info {
                 description
                   "Multilink class information";
                 leaf multilink-class-id {
                   type int32;
                   description
                     "Multilink class ID";
                 }
               }
               container fragments {
                 description
                   "Fragment statistics for multilink bundles and classes";
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
               container non-fragments {
                 description
                   "Non-fragment statistics for multilink bundles and 
                   classes";
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
             }
           }
           container crtp {
             container crtp-sessions {
               leaf input-frames {
                 type int32;
               }
               leaf output-frames {
                 type int32;
               }
             }
             list crtp-statistics {
               key "name";
               leaf name {
                 type string;
                 description
                   "Name of this item";
               }
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
           }
         }
         container statistics-account-overhead {
           description
             "Statistics account overhead information";
           leaf ingress-account-overhead {
             type int32;
             description
               "Ingress Statistics account overhead information";
           }
           leaf egress-account-overhead {
             type int32;
             description
               "Egress Statistics account overhead information";
           }
         }
         container traffic-statistics {
           leaf input-bps {
             type int32;
           }
           leaf input-pps {
             type int32;
           }
           leaf output-bps {
             type int32;
           }
           leaf output-pps {
             type int32;
           }
           leaf input-packets {
             type int32;
           }
           leaf output-packets {
             type int32;
           }
           leaf input-bytes {
             type int32;
           }
           leaf output-bytes {
             type int32;
           }
           container ipv6-transit-statistics {
             leaf input-bytes {
               type int32;
             }
             leaf output-bytes {
               type int32;
             }
             leaf input-packets {
               type int32;
             }
             leaf output-packets {
               type int32;
             }
           }
           container ipv6-total-statistics {
             leaf input-bytes {
               type int32;
             }
             leaf output-bytes {
               type int32;
             }
             leaf input-packets {
               type int32;
             }
             leaf output-packets {
               type int32;
             }
           }
         }
         container multicast-statistics {
           description
             "Multicast statistics for interface";
           leaf multicast-statistics-header {
             type empty;
           }
           container ipv4-multicast-statistics {
             description
               "IPV4 multicast statistics for interface";
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
           container ipv6-multicast-statistics {
             description
               "IPV6 multicast statistics for interface";
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
         }
         container ingress-traffic-statistics {
           description
             "Traffic statistics at ingress before entering Packet 
             Forwarding Engine";
           leaf input-bps {
             type int32;
           }
           leaf input-pps {
             type int32;
           }
           leaf input-drop-bps {
             type int32;
             description
               "Drop rate at ingress in bits per second ";
           }
           leaf input-drop-pps {
             type int32;
             description
               "Drop rate at ingress in packets per second ";
           }
           leaf input-bytes {
             type int32;
           }
           leaf input-packets {
             type int32;
           }
           leaf input-drop-bytes {
             type int32;
             description
               "Drop statistics at ingress in bytes";
           }
           leaf input-drop-packets {
             type int32;
             description
               "Drop statistics at ingress in packets";
           }
         }
         container local-traffic-statistics {
           description
             "Statistics for locally originated traffic";
           leaf input-bytes {
             type int32;
           }
           leaf input-bps {
             type int32;
           }
           leaf output-bytes {
             type int32;
           }
           leaf output-bps {
             type int32;
           }
           leaf input-packets {
             type int32;
           }
           leaf input-pps {
             type int32;
           }
           leaf output-packets {
             type int32;
           }
           leaf output-pps {
             type int32;
           }
         }
         container transit-traffic-statistics {
           description
             "Statistics for traffic passing through the Packet Forwarding 
             Engine";
           leaf input-bytes {
             type int32;
           }
           leaf input-bps {
             type int32;
           }
           leaf output-bytes {
             type int32;
           }
           leaf output-bps {
             type int32;
           }
           leaf input-packets {
             type int32;
           }
           leaf input-pps {
             type int32;
           }
           leaf output-packets {
             type int32;
           }
           leaf output-pps {
             type int32;
           }
           container ipv6-transit-statistics {
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
           container ipv6-total-statistics {
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
         }
         container keepalive-config {
           description
             "Configured keepalive settings on this interface";
           leaf keepalive-interval {
             type int32;
           }
           leaf keepalive-up-count {
             type int32;
           }
           leaf keepalive-down-count {
             type int32;
           }
         }
         container keepalive-statistics {
           description
             "Keepalive statistics for this interface";
           leaf keepalive-lmi-descriptor {
             type string;
           }
           leaf keepalive-input-count {
             type int32;
           }
           leaf keepalive-input-time {
             type string;
           }
           leaf keepalive-output-count {
             type int32;
           }
           leaf keepalive-output-time {
             type string;
           }
         }
         container ppp-flags {
           leaf iff-ppp-flags-acfc {
             type empty;
           }
           leaf iff-ppp-flags-pfc {
             type empty;
           }
         }
         list ncp-information {
           description
             "Network Control Protocol information";
           leaf ncp-protocol {
             type string;
             description
               "Network protocol for this NCP instance";
           }
           leaf ncp-state {
             type string;
             description
               "State of this NCP instance";
           }
         }
         container virtual-circuit-information {
           description
             "Operational information and statistics for a virtual circuit";
           leaf vpi {
             type int32;
             description
               "Virtual path identifier";
           }
           leaf vci {
             type int32;
             description
               "Virtual circuit identifier";
           }
           leaf psn-tag {
             type string;
             description
               "VPI/VCI swapping configuration";
           }
           leaf psn-vpi {
             type int32;
             description
               "PSN virtual path identifier";
           }
           leaf psn-vci {
             type int32;
             description
               "PSN virtual circuit identifier";
           }
           leaf trunk {
             type int32;
             description
               "ATM trunk identifier";
           }
           leaf dlci {
             type int32;
           }
           leaf swapping {
             type string;
             description
               "VPI/VCI swapping configuration";
           }
           leaf trunk-bandwidth {
             type int32;
             description
               "ATM trunk bandwidth";
           }
           leaf atm-tm-cbr {
             type empty;
             description
               "Constant bit rate";
           }
           leaf atm-tm-vbr {
             type empty;
             description
               "Variable bit rate";
           }
           leaf atm-tm-rtvbr {
             type empty;
             description
               "Real-time variable bit rate";
           }
           leaf peak {
             type int32;
           }
           leaf sustained {
             type int32;
           }
           leaf burst {
             type int32;
           }
           leaf cdvt {
             type int32;
           }
           leaf queue-limit {
             type int32;
           }
           leaf down-time {
             type int32;
             description
               "Total down time for this circuit";
           }
           leaf last-down-time {
             type int32;
             description
               "Time elapsed since circuit last went down";
           }
           leaf ifvc-epd {
             type int32;
             description
               "Early packet discard threshold";
           }
           leaf ifvc-weight {
             type int32;
             description
               "Transmit weight";
           }
           leaf ifvc-epd-plp0 {
             type int32;
             description
               "Early packet discard threshold for PLP 0";
           }
           leaf ifvc-epd-plp1 {
             type int32;
             description
               "Early packet discard threshold for PLP 1";
           }
           container vci-range {
             description
               "ATM VCI range";
             leaf vpi {
               type int32;
               description
                 "Virtual path identifier";
             }
             leaf start-vci {
               type int32;
               description
                 "ATM VCI range's start value";
             }
             leaf end-vci {
               type int32;
               description
                 "ATM VCI range's end value";
             }
           }
           container ifvc-flags {
             leaf ifvc-down {
               type empty;
             }
             leaf ifvc-none {
               type empty;
             }
             leaf ifvc-active {
               type empty;
             }
             leaf ifvc-closed {
               type empty;
             }
             leaf ifvc-inverse-arp {
               type empty;
             }
             leaf ifvc-ilmi {
               type empty;
             }
             leaf ifvc-oam {
               type empty;
             }
             leaf ifvc-shaping {
               type empty;
             }
             leaf ifvc-passiveoam {
               type empty;
             }
             leaf ifvc-multicast {
               type empty;
             }
             leaf ifvc-ccc-down {
               type empty;
             }
             leaf ifvc-configured {
               type empty;
               description
                 "DCE-end is configured";
             }
             leaf ifvc-unconfigured {
               type empty;
               description
                 "DCE-end is unconfigured";
             }
             leaf generic-value {
               type int32;
               description
                 "Hexadecimal value of unknown flag bits";
             }
           }
           container ifvc-multipoint-destination {
             leaf multipoint-address {
               type string;
               description
                 "Protocol address of the remote side of this connection";
             }
           }
           container oam-parameters {
             leaf period {
               type int32;
             }
             leaf up-count {
               type int32;
             }
             leaf down-count {
               type int32;
             }
           }
           container oam-statistics {
             description
               "Container tag for OAM statistics";
             leaf oam-total-received-count {
               type int32;
             }
             leaf oam-total-transmitted-count {
               type int32;
             }
             leaf oam-total-received-count-4 {
               type int32;
             }
             leaf oam-total-transmitted-count-4 {
               type int32;
             }
             leaf oam-loopback-received-count {
               type int32;
             }
             leaf oam-loopback-transmitted-count {
               type int32;
             }
             leaf oam-loopback-received-last {
               type string;
             }
             leaf oam-loopback-transmitted-last {
               type string;
             }
             leaf oam-rdi-received-count {
               type int32;
             }
             leaf oam-rdi-transmitted-count {
               type int32;
             }
             leaf oam-rdi-received-last {
               type string;
             }
             leaf oam-rdi-transmitted-last {
               type string;
             }
             leaf oam-ais-received-count {
               type int32;
             }
             leaf oam-ais-transmitted-count {
               type int32;
             }
             leaf oam-ais-received-last {
               type string;
             }
             leaf oam-ais-transmitted-last {
               type string;
             }
           }
           container traffic-statistics {
             leaf input-bps {
               type int32;
             }
             leaf input-pps {
               type int32;
             }
             leaf output-bps {
               type int32;
             }
             leaf output-pps {
               type int32;
             }
             leaf input-packets {
               type int32;
             }
             leaf output-packets {
               type int32;
             }
             leaf input-bytes {
               type int32;
             }
             leaf output-bytes {
               type int32;
             }
             container ipv6-transit-statistics {
               leaf input-bytes {
                 type int32;
               }
               leaf output-bytes {
                 type int32;
               }
               leaf input-packets {
                 type int32;
               }
               leaf output-packets {
                 type int32;
               }
             }
             container ipv6-total-statistics {
               leaf input-bytes {
                 type int32;
               }
               leaf output-bytes {
                 type int32;
               }
               leaf input-packets {
                 type int32;
               }
               leaf output-packets {
                 type int32;
               }
             }
           }
           container atm-policer-statistics {
             leaf non-conform-clp0-cells {
               type int32;
               description
                 "UPC non-conforming ATM CLP0 cell";
             }
             leaf non-conform-clp1-cells {
               type int32;
               description
                 "UPC non-conforming ATM CLP1 cell";
             }
             leaf tagged-cells {
               type int32;
               description
                 "UPC tagged cell";
             }
           }
           container atm-statistics {
             leaf vc-queue-drops {
               type int32;
             }
           }
           container atm-cos-information {
             leaf vc-cos-mode {
               type string;
               description
                 "Virtual circuit CoS scheduling mode";
             }
             list atm-cos-queue {
               container atm-cos-queue-parameters {
                 leaf cos-forwarding-class-name {
                   type string;
                   description
                     "Forwarding class name associated with queue";
                 }
                 leaf cos-queue-number {
                   type int32;
                   description
                     "Queue number";
                 }
                 leaf scheduling-priority {
                   type string;
                   description
                     "Scheduling priority";
                 }
                 leaf transmit-weight-cells {
                   type int32;
                   description
                     "Weight to apply to scheduling as number of cells";
                 }
                 leaf transmit-weight-percent {
                   type int32;
                   description
                     "Weight to apply to scheduling as fill percentage";
                 }
                 leaf epd-threshold {
                   type int32;
                   description
                     "Early packet drop threshold";
                 }
                 leaf epd-threshold-plp0 {
                   type int32;
                   description
                     "Early packet drop threshold for PLP 0";
                 }
                 leaf epd-threshold-plp1 {
                   type int32;
                   description
                     "Early packet drop threshold for PLP 1";
                 }
                 container linear-red-drop-profile {
                   leaf queue-depth {
                     type uint32;
                     description
                       "Instantaneous queue depth";
                   }
                   leaf low-red {
                     type int32;
                     description
                       "Fill level percentage when linear RED is applied for
                       low PLP";
                   }
                   leaf high-red {
                     type int32;
                     description
                       "Fill level percentage when linear RED is applied for
                       high PLP";
                   }
                   leaf max-low-red {
                     type int32;
                     description
                       "Fill level percentage with 100% packet drop for low 
                       PLP";
                   }
                   leaf max-high-red {
                     type int32;
                     description
                       "Fill level percentage with 100% packet drop for high
                       PLP";
                   }
                 }
               }
               container atm-cos-queue-statistics {
                 leaf atm-output-bytes {
                   type int32;
                 }
                 leaf atm-output-packets {
                   type int32;
                 }
                 leaf atm-packet-drops {
                   type int32;
                 }
               }
               container atm-cos-plp-statistics {
                 leaf atm-plp0-output-bytes {
                   type int32;
                 }
                 leaf atm-plp1-output-bytes {
                   type int32;
                 }
                 leaf atm-plp0-output-packets {
                   type int32;
                 }
                 leaf atm-plp1-output-packets {
                   type int32;
                 }
                 leaf atm-plp0-byte-drops {
                   type int32;
                 }
                 leaf atm-plp1-byte-drops {
                   type int32;
                 }
                 leaf atm-plp0-packet-drops {
                   type int32;
                 }
                 leaf atm-plp1-packet-drops {
                   type int32;
                 }
               }
             }
           }
           container in-arp-statistics {
             description
               "Container tag for ARP statistics";
             leaf received-count {
               type int32;
               description
                 "Number of ARPs received";
             }
             leaf transmitted-count {
               type int32;
               description
                 "Number of ARPs sent";
             }
             leaf denied-count {
               type int32;
               description
                 "Number of ARPs denied";
             }
             leaf operation-not-supported-count {
               type int32;
               description
                 "Number of ARPs with operation not supported";
             }
             leaf bad-packet-length-count {
               type int32;
               description
                 "Number of ARPs with bad packet length";
             }
             leaf bad-protocol-count {
               type int32;
               description
                 "Number of ARPs with bad protocol";
             }
             leaf bad-protocol-length-count {
               type int32;
               description
                 "Number of ARPs with bad protocol length";
             }
             leaf bad-hardware-length-count {
               type int32;
               description
                 "Number of ARPs with bad hardware length";
             }
             leaf dropped-count {
               type int32;
               description
                 "Number of ARPs dropped";
             }
             leaf last-received {
               type string;
               description
                 "Time an ARP was last received";
             }
             leaf last-transmitted {
               type string;
               description
                 "Time an ARP was last sent";
             }
           }
           container dlci-statistics {
             description
               "DLCI statistics for an interface";
             leaf dlci-active {
               type int32;
               description
                 "Number of DLCIs in active state";
             }
             leaf dlci-inactive {
               type int32;
               description
                 "Number of DLCIs in inactive state";
             }
           }
         }
         list filter-information {
           leaf-list filter-input {
             type string;
             description
               "Name of the input filter";
           }
           leaf-list filter-input-precedence {
             type uint32;
             description
               "Precedence of the input filter";
           }
           leaf-list filter-output {
             type string;
             description
               "Name of the output filter";
           }
           leaf-list filter-output-precedence {
             type uint32;
             description
               "Precedence of the output filter";
           }
         }
         list address-family {
           key "address-family-name";
           leaf compression-device-name {
             type string;
             description
               "Name of the link service device";
           }
           leaf address-family-name {
             type string;
           }
           leaf multilink-bundle-name {
             type string;
             description
               "Name of the multilink bundle for this address family";
           }
           leaf as-bundle-name {
             type string;
             description
               "Name of the aggregated SONET bundle for this address family";
           }
           leaf ae-bundle-name {
             type string;
             description
               "Name of the aggregated Ethernet bundle";
           }
           leaf es-sa-name {
             type string;
             description
               "Name of the IPSec security association for this address 
               family";
           }
           leaf mtu {
             type string;
             description
               "MTU size on this interface";
           }
           leaf maximum-labels {
             type uint32;
             description
               "Maximum labels on MPLS iffamily";
           }
           leaf generation {
             type int32;
             description
               "Generation number used to distinguish between successive 
               instances of this interface";
           }
           leaf route-table {
             type int32;
           }
           leaf vpls-mesh-group {
             type string;
           }
           leaf es-sa-fail-count {
             type int32;
             description
               "Number of failures for IPSec security association for this 
               family";
           }
           leaf es-sa-xmt-seq-num {
             type int32;
             description
               "Transmit sequence number of IPSec security association 
               family";
           }
           leaf es-sa-recv-seq-num {
             type int32;
             description
               "Receive sequence number of IPSec security association family";
           }
           leaf evpn-multihomed-status {
             type string;
           }
           leaf evpn-mh-esi-sh-label {
             type string;
           }
           leaf iff-next-hop {
             type int32;
             description
               "Interface family next-hop";
           }
           leaf iff-vpls-status {
             type string;
             description
               "Interface family vpls status";
           }
           leaf max-local-cache {
             type uint32;
             description
               "Max local nh cache size";
           }
           leaf new-hold-limit {
             type uint32;
             description
               "Max limit on new unresolved nh";
           }
           leaf intf-curr-cnt {
             type uint32;
             description
               "Current nh total cache size on this interface";
           }
           leaf intf-unresolved-cnt {
             type uint32;
             description
               "Current new unresolved nh cache size on this interface";
           }
           leaf intf-dropcnt {
             type uint32;
             description
               "Current interface nh drop count";
           }
           leaf mlppp-service-interface {
             type string;
             description
               "Name of the multilink service interface for this address 
               family";
           }
           leaf mlppp-service-dev-pool {
             type string;
             description
               "Name of the multilink service device pool for this address 
               family";
           }
           leaf mlppp-dynamic-profile {
             type string;
             description
               "Name of the multilink dynamic profile for this address 
               family";
           }
           leaf arp-respond-any-local-address {
             type string;
             description
               "Respond to ARP requests for any local address";
           }
           leaf local-bias-information {
             type string;
           }
           leaf ft-iff-dest-port {
             type uint32;
             description
               "Destination UDP port to be used for this family";
           }
           container address-family-flags {
             leaf ifff-none {
               type empty;
             }
             leaf ifff-primary {
               type empty;
             }
             leaf ifff-redirects {
               type empty;
             }
             leaf ifff-no-redirects {
               type empty;
             }
             leaf ifff-no-neighbor-learn {
               type empty;
             }
             leaf ifff-targeted-broadcast {
               type empty;
             }
             leaf ifff-sendbcast-pkt-to-re {
               type empty;
             }
             leaf ifff-hard-down {
               type empty;
             }
             leaf ifff-down {
               type empty;
             }
             leaf ifff-up {
               type empty;
             }
             leaf ifff-func1 {
               type empty;
             }
             leaf ifff-func2 {
               type empty;
             }
             leaf ifff-is-primary {
               type empty;
             }
             leaf ifff-recv-options {
               type empty;
             }
             leaf ifff-recv-ttl-exceeded {
               type empty;
             }
             leaf ifff-dst-class-usage {
               type empty;
             }
             leaf ifff-src-class-input {
               type empty;
             }
             leaf ifff-src-class-output {
               type empty;
             }
             leaf ifff-mtu-user-conf {
               type empty;
             }
             leaf ifff-mac-validate-strict {
               type empty;
             }
             leaf ifff-mac-validate-loose {
               type empty;
             }
             leaf ifff-rpf-check {
               type empty;
             }
             leaf ifff-rpf-loose-mode {
               type empty;
             }
             leaf ifff-sample-input {
               type empty;
             }
             leaf ifff-sample-output {
               type empty;
             }
             leaf ifff-no-asynch-notification {
               type empty;
             }
             leaf ifff-negotiate-address {
               type empty;
             }
             leaf ifff-port-mode-trunk {
               type empty;
             }
             leaf ifff-inter-switch-link {
               type empty;
             }
             leaf ifff-mtu-protocol-adj {
               type empty;
             }
             leaf ifff-unnumbered {
               type empty;
             }
             leaf ifff-tcc-mpls {
               type empty;
             }
             leaf ifff-tcc-inet {
               type empty;
             }
             leaf ifff-tcc-inet6 {
               type empty;
             }
             leaf ifff-tcc-iso {
               type empty;
             }
             leaf ifff-port-mode-isid-trunk {
               type empty;
             }
             leaf generic-value {
               type int32;
               description
                 "Hexadecimal value of unknown flag bits";
             }
           }
           list address-family-unnumbered {
             description
               "Information about an unnumbered address family";
             leaf unnumbered-family-donor-interface-name {
               type string;
               description
                 "Donor interface name";
             }
             leaf unnumbered-family-donor-interface-index {
               type string;
               description
                 "Donor interface index";
             }
             leaf unnumbered-family-preferred-source-address {
               type string;
               description
                 "Unnumbered interface preferred source address";
             }
           }
           container pppoe-underlying-information {
             description
               "PPPoE Underlying information";
             list pppoe-underlying-interface {
               leaf dynamic-profile {
                 type string;
                 description
                   "Dynamic Profile name";
               }
               leaf service-name-table {
                 type string;
                 description
                   "Name of Service Name Table";
               }
               leaf max-sessions {
                 type int32;
                 description
                   "Maximum number of PPPoE sessions";
               }
               leaf max-sessions-vsa-ignore {
                 type string;
                 description
                   "Ignore max-sessions VSA";
               }
               leaf duplicate-protection {
                 type string;
                 description
                   "Duplicate protection mode";
               }
               leaf short-cycle-protection {
                 type string;
                 description
                   "Short cycle protection mode";
               }
               leaf direct-connect {
                 type string;
                 description
                   "Direct connect mode";
               }
               leaf ac-name {
                 type string;
                 description
                   "Access Concentrator name";
               }
               leaf underlying-interface-name {
                 type string;
                 description
                   "Underlying interface name";
               }
               leaf underlying-interface-index {
                 type string;
                 description
                   "Underlying interface index";
               }
               leaf encapsulation-type-identifier {
                 type string;
                 description
                   "Encapsulation type identifier";
               }
               leaf state {
                 type string;
                 description
                   "State";
               }
               leaf active-sessions {
                 type int32;
                 description
                   "Number of active PPPoE sessions";
               }
               leaf aci-autosensing {
                 type string;
                 description
                   "ACI VLAN Autosensing mode";
               }
               leaf line-identity-autosensing {
                 type string;
                 description
                   "Line Identity Autosensing mode";
               }
             }
           }
           list filter-information {
             leaf-list filter-input {
               type string;
               description
                 "Name of the input filter";
             }
             leaf-list filter-input-precedence {
               type uint32;
               description
                 "Precedence of the input filter";
             }
             leaf-list filter-output {
               type string;
               description
                 "Name of the output filter";
             }
             leaf-list filter-output-precedence {
               type uint32;
               description
                 "Precedence of the output filter";
             }
           }
           list policer-information {
             description
               "Interface policer information";
             leaf policer-input {
               type string;
               description
                 "Name of the input policer";
             }
             leaf policer-output {
               type string;
               description
                 "Name of the output policer";
             }
           }
           list interface-address {
             leaf-list interface-address.heading {
               type string;
             }
             leaf ifa-destination {
               type string;
               description
                 "Protocol address of the remote side of this connection";
             }
             leaf ifa-local {
               type string;
               description
                 "Protocol address on this interface";
             }
             leaf ifa-broadcast {
               type string;
               description
                 "Network broadcast address";
             }
             leaf ifa-primary-dns {
               type string;
               description
                 "Primary DNS server address";
             }
             leaf ifa-primary-nbns {
               type string;
               description
                 "Primary Netbios Name server address";
             }
             leaf ifa-secondary-dns {
               type string;
               description
                 "Secondary DNS server address";
             }
             leaf ifa-secondary-nbns {
               type string;
               description
                 "Secondary Netbios Name server address";
             }
             leaf ifa-address-pool {
               type string;
               description
                 "Address pool name";
             }
             leaf generation {
               type int32;
               description
                 "Generation number used to distinguish between successive 
                 instances of this interface";
             }
             container ifa-flags {
               leaf ifaf-none {
                 type empty;
               }
               leaf ifaf-primary {
                 type empty;
               }
               leaf ifaf-preferred {
                 type empty;
               }
               leaf ifaf-master-only {
                 type empty;
               }
               leaf ifaf-down {
                 type empty;
               }
               leaf ifaf-kernel {
                 type empty;
               }
               leaf ifaf-current-default {
                 type empty;
               }
               leaf ifaf-current-preferred {
                 type empty;
               }
               leaf ifaf-current-primary {
                 type empty;
               }
               leaf ifaf-duplicate {
                 type empty;
               }
               leaf ifaf-webauth-http {
                 type empty;
               }
               leaf generic-value {
                 type int32;
                 description
                   "Hexadecimal value of unknown flag bits";
               }
             }
             container in6-addr-flags {
               leaf in6-anycast {
                 type empty;
               }
               leaf in6-tentative {
                 type empty;
               }
               leaf in6-duplicate {
                 type empty;
               }
               leaf in6-detached {
                 type empty;
               }
               leaf in6-deprecated {
                 type empty;
               }
               leaf in6-nodad {
                 type empty;
               }
               leaf in6-temporary {
                 type empty;
               }
               leaf in6-autoconf {
                 type empty;
               }
               leaf in6-nopfxmgmt {
                 type empty;
               }
             }
           }
           container mac-validate-statistics {
             description
               "SRC MAC validate statistics";
             leaf mac-validate-packets {
               type int32;
               description
                 "Number of packets that have failed the mac-validate check";
             }
             leaf mac-validate-bytes {
               type int32;
               description
                 "Number of bytes that have failed the mac-validate check";
             }
           }
           container route-rpf-statistics {
             description
               "Unicast reverse-path forwarding (RPF) statistics";
             leaf route-rpf-packets {
               type int32;
               description
                 "Number of packets that have failed the RPF check";
             }
             leaf route-rpf-bytes {
               type int32;
               description
                 "Number of bytes that have failed the RPF check";
             }
           }
           container destination-class-statistics {
             description
               "Destination class usage (DCU) statistics";
             list destination-class {
               description
                 "DCU statistics for a single class";
               leaf dcu-class-name {
                 type string;
                 description
                   "Name of DCU class";
               }
               leaf dcu-class-packets {
                 type int32;
                 description
                   "Number of packets counted by DCU for this class";
               }
               leaf dcu-class-bytes {
                 type int32;
                 description
                   "Number of bytes counted by DCU for this class";
               }
               leaf dcu-class-pps {
                 type int32;
                 description
                   "Packet-per-seconds counted by DCU for this class";
               }
               leaf dcu-class-bps {
                 type int32;
                 description
                   "Bit-per-seconds counted by DCU for this class";
               }
             }
           }
           container source-class-statistics {
             description
               "Source class usage (SCU) statistics";
             list source-class {
               description
                 "SCU statistics for a single class";
               leaf scu-class-name {
                 type string;
                 description
                   "Name of SCU class";
               }
               leaf scu-class-packets {
                 type int32;
                 description
                   "Number of packets counted by SCU for this class";
               }
               leaf scu-class-bytes {
                 type int32;
                 description
                   "Number of bytes counted by SCU for this class";
               }
               leaf scu-class-pps {
                 type int32;
                 description
                   "Packet-per-seconds counted by SCU for this class";
               }
               leaf scu-class-bps {
                 type int32;
                 description
                   "Bit-per-seconds counted by SCU for this class";
               }
             }
           }
         }
         list bridge-iff-properties {
           description
             "Information about Ethernet-switching address family";
         }
         container l2circuit-info {
           leaf out-of-sequence {
             type int32;
           }
           leaf denied-packets {
             type int32;
           }
           leaf cell-bundle-size {
             type int32;
           }
           leaf cell-bundle-timeout {
             type int32;
           }
           leaf cell-timeout-count {
             type int32;
           }
         }
         container irb-domain {
           leaf irb-routing-instance {
             type string;
             description
               "Name of the Routing Instance";
           }
           leaf irb-bridge {
             type string;
             description
               "Name of the Bridging Domain";
           }
         }
         container media-information {
           description
             "Information about media alarms";
           leaf media-type {
             type string;
             description
               "Type of media this information is for";
           }
           list media-alarm {
             leaf media-alarm-name {
               type string;
             }
             leaf media-alarm-count {
               type int32;
             }
             leaf media-alarm-seconds {
               type int32;
             }
             leaf media-alarm-state {
               type string;
             }
             leaf ce-counter-name {
               type string;
               description
                 "Circuit Emulation counter information";
             }
             leaf ce-counter-packets {
               type int32;
               description
                 "Circuit Emulation number of packets";
             }
             leaf ce-counter-bytes {
               type int32;
               description
                 "Circuit Emulation number of bytes";
             }
             leaf ce-counter-count {
               type int32;
               description
                 "Circuit Emulation number of event occurrences";
             }
           }
           leaf ds1-timeslots {
             type string;
           }
           leaf ds1-line-encoding {
             type string;
           }
           leaf ds1-byte-encoding {
             type string;
           }
           leaf ds1-data-inversion {
             type string;
           }
           leaf idle-cycle-flag {
             type string;
           }
           leaf start-end-flag {
             type string;
           }
           leaf ds0-byte-encoding {
             type string;
           }
           leaf ds0-data-inversion {
             type string;
           }
           leaf e3-data-inversion {
             type string;
           }
           leaf ds1-buildout {
             type string;
             description
               "Number of feet";
           }
         }
         container vtep-info {
           leaf vtep-type {
             type string;
             description
               "Type of VXLAN endpoint";
           }
           leaf vtep-address {
             type string;
             description
               "Protocol address of the connection";
           }
           leaf vtep-l2-routing-instance {
             type string;
             description
               "Name of the layer-2 routing instance";
           }
           leaf vtep-l3-routing-instance {
             type string;
             description
               "Name of the layer-3 routing instance";
           }
         }
         container ft-info {
           leaf ft-encap {
             type string;
             description
               "Type of encap used for FTI";
           }
           leaf ft-dest-port {
             type int32;
             description
               "Destnation UDP port used in encap";
           }
           leaf ft-vnid {
             type int32;
             description
               "VNI value used in encap";
           }
           leaf ft-src-addr {
             type string;
             description
               "Source address used for encap";
           }
           leaf ft-dst-addr {
             type string;
             description
               "Destination address used for encap";
           }
         }
         container rbeb-info {
           leaf rbeb-address {
             type string;
             description
               "Protocol address of the connection";
           }
           leaf rbeb-l2-routing-instance {
             type string;
             description
               "Name of the layer-2 routing instance";
           }
         }
         list macsec-statistics {
           description
             "Information about MAC Security statistics details";
           leaf interface-name {
             type string;
             description
               "Class-of-service interface name";
           }
           leaf encrypted-packets {
             type uint64;
             description
               "Macsec encrypted packets sent";
           }
           leaf encrypted-bytes {
             type uint64;
             description
               "Macsec encrypted bytes sent";
           }
           leaf protected-packets {
             type uint64;
             description
               "Macsec packets sent with only integrity protection";
           }
           leaf protected-bytes {
             type uint64;
             description
               "Macsec bytes sent with only integrity protection";
           }
           leaf ok-packets {
             type uint64;
             description
               "Macsec packets accepted";
           }
           leaf decrypted-bytes {
             type uint64;
             description
               "Macsec received bytes decrypted";
           }
           leaf decrypted-packets {
             type uint64;
             description
               "Macsec received packets decrypted";
           }
           leaf validated-packets {
             type uint64;
             description
               "Macsec received packets validated";
           }
           leaf validated-bytes {
             type uint64;
             description
               "Macsec received bytes validated";
           }
           leaf untagged-packets {
             type uint64;
             description
               "Macsec untagged packets";
           }
           leaf toolong-packets {
             type uint64;
             description
               "Macsec too long packets transmitted on a secure channel";
           }
           leaf control-packets {
             type uint64;
             description
               "Macsec control packets received on a secure channel";
           }
           leaf tagged-miss-packets {
             type uint64;
             description
               "Macsec tagged miss packets received on a secure channel";
           }
           leaf untagged-hit-packets {
             type uint64;
             description
               "Macsec untagged hit packets received on a secure channel";
           }
           leaf notag-packets {
             type uint64;
             description
               "Macsec no tag packets received on a secure channel";
           }
           leaf badtag-packets {
             type uint64;
             description
               "Macsec bad tag packets received on a secure channel";
           }
           leaf unknown-sci-packets {
             type uint64;
             description
               "Macsec unknown sci packets received on a secure channel";
           }
           leaf no-sci-packets {
             type uint64;
             description
               "Macsec no sci packets received on a secure channel";
           }
           leaf control-pass-packets {
             type uint64;
             description
               "Macsec allowed control packets received on a secure channel";
           }
           leaf uncontrol-pass-packets {
             type uint64;
             description
               "Macsec allowed uncontrol packets received on a secure 
               channel";
           }
           leaf control-fail-packets {
             type uint64;
             description
               "Macsec dropped control packets received on a secure channel";
           }
           leaf uncontrol-fail-packets {
             type uint64;
             description
               "Macsec dropped uncontrol packets received on a secure 
               channel";
           }
           leaf hit-dropped-packets {
             type uint64;
             description
               "Macsec hit dropped packets received on a security channel";
           }
           leaf notusing-sa-packets {
             type uint64;
             description
               "Macsec not using sa packets received on a security channel";
           }
           leaf unused-sa-packets {
             type uint64;
             description
               "Macsec unused sa packets received on a security channel";
           }
           leaf late-packets {
             type uint64;
             description
               "Macsec late packets dropped on a security channel";
           }
           leaf delayed-packets {
             type uint64;
             description
               "Macsec delayed packets accepted on a security channel";
           }
           leaf unchecked-packets {
             type uint64;
             description
               "Macsec unchecked packets accepted on a security channel";
           }
           leaf notvalid-packets {
             type uint64;
             description
               "Macsec not valid packets dropped on a security channel";
           }
           leaf invalid-packets {
             type uint64;
             description
               "Macsec invalid packets accepted on a security channel";
           }
           list secure-channel-sent {
             leaf encrypted-packets {
               type uint64;
               description
                 "Macsec encrypted packets sent";
             }
             leaf encrypted-bytes {
               type uint64;
               description
                 "Macsec encrypted bytes sent";
             }
             leaf protected-packets {
               type uint64;
               description
                 "Macsec packets sent with only integrity protection";
             }
             leaf protected-bytes {
               type uint64;
               description
                 "Macsec bytes sent with only integrity protection";
             }
           }
           list secure-association-sent {
             leaf encrypted-packets {
               type uint64;
               description
                 "Macsec encrypted packets sent";
             }
             leaf encrypted-bytes {
               type uint64;
               description
                 "Macsec encrypted bytes sent";
             }
             leaf protected-packets {
               type uint64;
               description
                 "Macsec packets sent with only integrity protection";
             }
             leaf protected-bytes {
               type uint64;
               description
                 "Macsec bytes sent with only integrity protection";
             }
           }
           list secure-channel-received {
             leaf ok-packets {
               type uint64;
               description
                 "Macsec packets accepted";
             }
             leaf decrypted-packets {
               type uint64;
               description
                 "Macsec received packets decrypted";
             }
             leaf decrypted-bytes {
               type uint64;
               description
                 "Macsec received bytes decrypted";
             }
             leaf validated-packets {
               type uint64;
               description
                 "Macsec received packets validated";
             }
             leaf validated-bytes {
               type uint64;
               description
                 "Macsec received bytes validated";
             }
           }
           list secure-association-received {
             leaf ok-packets {
               type uint64;
               description
                 "Macsec packets accepted";
             }
             leaf decrypted-packets {
               type uint64;
               description
                 "Macsec received packets decrypted";
             }
             leaf decrypted-bytes {
               type uint64;
               description
                 "Macsec received bytes decrypted";
             }
             leaf validated-packets {
               type uint64;
               description
                 "Macsec received packets validated";
             }
             leaf validated-bytes {
               type uint64;
               description
                 "Macsec received bytes validated";
             }
           }
           list macsec-error-information {
             list secure-channel-sent-errors {
               leaf untagged-packets {
                 type uint64;
                 description
                   "Macsec untagged packets";
               }
               leaf toolong-packets {
                 type uint64;
                 description
                   "Macsec too long packets transmitted on a secure channel";
               }
             }
             list secure-channel-received-errors {
               leaf control-packets {
                 type uint64;
                 description
                   "Macsec control packets received on a secure channel";
               }
               leaf tagged-miss-packets {
                 type uint64;
                 description
                   "Macsec tagged miss packets received on a secure channel";
               }
               leaf untagged-hit-packets {
                 type uint64;
                 description
                   "Macsec untagged hit packets received on a secure channel";
               }
               leaf untagged-packets {
                 type uint64;
                 description
                   "Macsec untagged packets";
               }
               leaf notag-packets {
                 type uint64;
                 description
                   "Macsec no tag packets received on a secure channel";
               }
               leaf badtag-packets {
                 type uint64;
                 description
                   "Macsec bad tag packets received on a secure channel";
               }
               leaf unknown-sci-packets {
                 type uint64;
                 description
                   "Macsec unknown sci packets received on a secure channel";
               }
               leaf no-sci-packets {
                 type uint64;
                 description
                   "Macsec no sci packets received on a secure channel";
               }
               leaf control-pass-packets {
                 type uint64;
                 description
                   "Macsec allowed control packets received on a secure 
                   channel";
               }
               leaf control-fail-packets {
                 type uint64;
                 description
                   "Macsec dropped control packets received on a secure 
                   channel";
               }
               leaf uncontrol-pass-packets {
                 type uint64;
                 description
                   "Macsec allowed uncontrol packets received on a secure 
                   channel";
               }
               leaf uncontrol-fail-packets {
                 type uint64;
                 description
                   "Macsec dropped uncontrol packets received on a secure 
                   channel";
               }
             }
             list secure-channel-received-extended {
               leaf hit-dropped-packets {
                 type uint64;
                 description
                   "Macsec hit dropped packets received on a security 
                   channel";
               }
               leaf invalid-packets {
                 type uint64;
                 description
                   "Macsec invalid packets accepted on a security channel";
               }
               leaf late-packets {
                 type uint64;
                 description
                   "Macsec late packets dropped on a security channel";
               }
               leaf delayed-packets {
                 type uint64;
                 description
                   "Macsec delayed packets accepted on a security channel";
               }
               leaf unchecked-packets {
                 type uint64;
                 description
                   "Macsec unchecked packets accepted on a security channel";
               }
               leaf notvalid-packets {
                 type uint64;
                 description
                   "Macsec not valid packets dropped on a security channel";
               }
               leaf notusing-sa-packets {
                 type uint64;
                 description
                   "Macsec not using sa packets received on a security 
                   channel";
               }
               leaf unused-sa-packets {
                 type uint64;
                 description
                   "Macsec unused sa packets received on a security channel";
               }
               leaf untagged-hit-packets {
                 type uint64;
                 description
                   "Macsec untagged hit packets received on a secure channel";
               }
             }
           }
         }
         container multilink-bundle-status {
           description
             "Multilink bundle status";
           leaf rx-sequence-number {
             type string;
             description
               "Received sequence number";
           }
           leaf tx-sequence-number {
             type string;
             description
               "Transmitted sequence number";
           }
           leaf packet-drops {
             type int32;
             description
               "Number of packets dropped";
           }
           leaf packet-drop-bytes {
             type int32;
             description
               "Number of bytes in dropped packets";
           }
           leaf fragment-drops {
             type int32;
             description
               "Number of fragments dropped";
           }
           leaf fragment-drop-bytes {
             type int32;
             description
               "Number of bytes in dropped fragments";
           }
           leaf mrru-exceeded {
             type int32;
             description
               "Number of assembled packets that exceeded MRRU";
           }
           leaf processing-errors {
             type int32;
             description
               "Number of errors encountered in assembling packets";
           }
           leaf fragment-timeout {
             type int32;
             description
               "Fragments timed out during assembly";
           }
           leaf sequence-number-missing {
             type int32;
             description
               "Gap detected in sequence numbers";
           }
           leaf out-of-order-sequence-number {
             type int32;
             description
               "Fragments with an out-of-order sequence number";
           }
           leaf out-of-range-sequence-number {
             type int32;
             description
               "Fragments with an out-of-range sequence number";
           }
           leaf packet-buffer-overflow {
             type int32;
             description
               "Number of times the packet data buffer overflowed";
           }
           leaf fragment-buffer-overflow {
             type int32;
             description
               "Number of times the fragment data buffer overflowed";
           }
         }
         container multilink-bundle-class {
           description
             "Multilink class status";
           leaf multilink-class-id {
             type int32;
             description
               "Multilink class ID";
           }
           leaf rx-sequence-number {
             type string;
             description
               "Received sequence number";
           }
           leaf tx-sequence-number {
             type string;
             description
               "Transmitted sequence number";
           }
           leaf packet-drops {
             type int32;
             description
               "Number of packets dropped";
           }
           leaf packet-drop-bytes {
             type int32;
             description
               "Number of bytes in dropped packets";
           }
           leaf fragment-drops {
             type int32;
             description
               "Number of fragments dropped";
           }
           leaf fragment-drop-bytes {
             type int32;
             description
               "Number of bytes in dropped fragments";
           }
           leaf mrru-exceeded {
             type int32;
             description
               "Number of assembled packets that exceeded MRRU";
           }
           leaf processing-errors {
             type int32;
             description
               "Number of errors encountered in assembling packets";
           }
           leaf fragment-timeout {
             type int32;
             description
               "Fragments timed out during assembly";
           }
           leaf sequence-number-missing {
             type int32;
             description
               "Gap detected in sequence numbers";
           }
           leaf out-of-order-sequence-number {
             type int32;
             description
               "Fragments with an out-of-order sequence number";
           }
           leaf out-of-range-sequence-number {
             type int32;
             description
               "Fragments with an out-of-range sequence number";
           }
           leaf packet-buffer-overflow {
             type int32;
             description
               "Number of times the packet data buffer overflowed";
           }
           leaf fragment-buffer-overflow {
             type int32;
             description
               "Number of times the fragment data buffer overflowed";
           }
           leaf multilink-class-drop-timeout {
             type int32;
             description
               "Drop timeout for multilink class (milliseconds)";
           }
         }
         container lag-traffic-statistics {
           container lag-bundle {
             leaf input-packets {
               type int32;
             }
             leaf input-pps {
               type int32;
             }
             leaf input-bytes {
               type int32;
             }
             leaf input-bps {
               type int32;
             }
             leaf output-packets {
               type int32;
             }
             leaf output-pps {
               type int32;
             }
             leaf output-bytes {
               type int32;
             }
             leaf output-bps {
               type int32;
             }
           }
           container lag-adaptive-statistics {
             leaf adaptive-adjusts {
               type int32;
             }
             leaf adaptive-scans {
               type int32;
             }
             leaf adaptive-updates {
               type int32;
             }
           }
           container lag-multicast-statistics {
             leaf lag-multicast-statistics-header {
               type empty;
             }
             container lag-ipv4-multicast-statistics {
               leaf input-packets {
                 type int32;
               }
               leaf input-pps {
                 type int32;
               }
               leaf input-bytes {
                 type int32;
               }
               leaf input-bps {
                 type int32;
               }
               leaf output-packets {
                 type int32;
               }
               leaf output-pps {
                 type int32;
               }
               leaf output-bytes {
                 type int32;
               }
               leaf output-bps {
                 type int32;
               }
             }
             container lag-ipv6-multicast-statistics {
               leaf input-packets {
                 type int32;
               }
               leaf input-pps {
                 type int32;
               }
               leaf input-bytes {
                 type int32;
               }
               leaf input-bps {
                 type int32;
               }
               leaf output-packets {
                 type int32;
               }
               leaf output-pps {
                 type int32;
               }
               leaf output-bytes {
                 type int32;
               }
               leaf output-bps {
                 type int32;
               }
             }
           }
           container aggregate-member-info {
             leaf aggregate-member-count {
               type uint32;
             }
           }
           list lag-link {
             key "name";
             leaf name {
               type string;
               description
                 "Name of this item";
             }
             leaf down {
               type empty;
               description
                 "Link is down";
             }
             leaf input-packets {
               type int32;
             }
             leaf input-pps {
               type int32;
             }
             leaf input-bytes {
               type int32;
             }
             leaf input-bps {
               type int32;
             }
             leaf output-packets {
               type int32;
             }
             leaf output-pps {
               type int32;
             }
             leaf output-bytes {
               type int32;
             }
             leaf output-bps {
               type int32;
             }
           }
           list lag-bfd-view {
             key "name";
             leaf name {
               type string;
               description
                 "Name of this item";
             }
             leaf link-usability {
               type string;
             }
           }
           list lag-targeting-summary {
             leaf targeting-intf-name {
               type string;
             }
             leaf targeting-intf-type {
               type string;
             }
             leaf targeting-intf-link-state {
               type string;
             }
           }
           list lag-marker {
             key "name";
             leaf name {
               type string;
               description
                 "Name of this item";
             }
             leaf marker-rx-packets {
               type string;
             }
             leaf marker-response-tx-packets {
               type string;
             }
             leaf unknown-rx-packets {
               type string;
               description
                 "Number of unknown type packets received";
             }
             leaf illegal-rx-packets {
               type string;
               description
                 "Number of ill formed packets received";
             }
           }
           list lag-lacp-statistics {
             key "name";
             leaf name {
               type string;
               description
                 "Name of this item";
             }
             leaf lacp-rx-packets {
               type string;
               description
                 "Number of LACP packets received";
             }
             leaf lacp-tx-packets {
               type string;
               description
                 "Number of LACP packets transmitted";
             }
             leaf unknown-rx-packets {
               type string;
               description
                 "Number of unknown type packets received";
             }
             leaf illegal-rx-packets {
               type string;
               description
                 "Number of ill formed packets received";
             }
           }
           list if-distribution-list-information {
             leaf list-type {
               type string;
             }
             leaf list-status {
               type string;
             }
             list if-list {
               leaf if-child-name {
                 type string;
               }
               leaf if-status {
                 type string;
               }
             }
           }
           list lag-link-protection-subgrp {
             key "name";
             leaf name {
               type string;
               description
                 "Name of this item";
             }
             leaf lag-link-protection-subgrp-name {
               type string;
             }
             leaf lag-link-protection-subgrp-state {
               type string;
             }
           }
           list lag-lacp-info {
             key "name";
             description
               "LACP information";
             leaf name {
               type string;
               description
                 "Name of this item";
             }
             leaf lacp-role {
               type string;
               description
                 "Whether it is an actor or partner";
             }
             leaf lacp-sys-priority {
               type string;
               description
                 "System priority";
             }
             leaf lacp-system-id {
               type string;
               description
                 "LACP system identifier";
             }
             leaf lacp-port-priority {
               type string;
               description
                 "Priority of the port";
             }
             leaf lacp-port-number {
               type string;
               description
                 "Port number";
             }
             leaf lacp-port-key {
               type string;
               description
                 "Operational key of the port";
             }
           }
           list lag-lacp-state {
             key "name";
             description
               "LACP protocol state information";
             leaf name {
               type string;
               description
                 "Name of this item";
             }
             leaf lacp-role {
               type string;
               description
                 "Whether it is an actor or partner";
             }
             leaf lacp-expired {
               type string;
               description
                 "State of the receive lacp machine is EXPIRED?";
             }
             leaf lacp-defaulted {
               type string;
               description
                 "State of the receive lacp machine is DEFAULTED?";
             }
             leaf lacp-distributing {
               type string;
               description
                 "State of the mux lacp machine is DISTRIBUTING?";
             }
             leaf lacp-collecting {
               type string;
               description
                 "State of the mux lacp machine is COLLECTING?";
             }
             leaf lacp-synchronization {
               type string;
               description
                 "Actor view of partner information is in sync";
             }
             leaf lacp-aggregation {
               type string;
               description
                 "Actor view of partner information is in sync";
             }
             leaf lacp-timeout {
               type string;
               description
                 "Configured as either fast or slow periodic";
             }
             leaf lacp-activity {
               type string;
               description
                 "Configured as either active or passive";
             }
           }
           list lag-lacp-protocol {
             key "name";
             description
               "LACP protocol information";
             leaf name {
               type string;
               description
                 "Name of this item";
             }
             leaf lacp-receive-state {
               type string;
               description
                 "State of the receive lacp machine";
             }
             leaf lacp-transmit-state {
               type string;
               description
                 "State of the transmit lacp machine";
             }
             leaf lacp-mux-state {
               type string;
               description
                 "State of the mux lacp machine";
             }
           }
           list lag-lacp-bfd {
             key "name";
             description
               "BFD protocol information";
             leaf name {
               type string;
               description
                 "Name of this item";
             }
             leaf lacp-bfd-state {
               type string;
               description
                 "State of the BFD session";
             }
           }
           list lacp-hold-up-information {
             key "name";
             description
               "LACP hold-up information";
             leaf name {
               type string;
               description
                 "Name of this item";
             }
             leaf status {
               type string;
             }
             leaf restart-count {
               type int32;
             }
             leaf time-to-expire {
               type int32;
             }
             leaf start-time {
               type string;
             }
           }
         }
         container layer2-input-policer-statistics {
           description
             "Layer 2 input policer statistics for interface";
           leaf policer-low-bytes {
             type int32;
             description
               "Number of loss priority low bytes";
           }
           leaf policer-low-frames {
             type int32;
             description
               "Number of loss priority low frames";
           }
           leaf policer-low-rate {
             type int32;
             description
               "Rate of loss priority low pkts";
           }
           leaf policer-medium-high-bytes {
             type int32;
             description
               "Number of loss priority medium high bytes";
           }
           leaf policer-medium-high-frames {
             type int32;
             description
               "Number of loss priority medium high frames";
           }
           leaf policer-medium-high-rate {
             type int32;
             description
               "Rate of loss priority medium high rate";
           }
           leaf policer-high-bytes {
             type int32;
             description
               "Number of loss priority high bytes";
           }
           leaf policer-high-frames {
             type int32;
             description
               "Number of loss priority high frames";
           }
           leaf policer-high-rate {
             type int32;
             description
               "Rate of loss priority high rate";
           }
           leaf policer-dropped-bytes {
             type int32;
             description
               "Number of dropped bytes";
           }
           leaf policer-dropped-frames {
             type int32;
             description
               "Number of dropped frames";
           }
           leaf policer-dropped-rate {
             type int32;
             description
               "Number of dropped rate";
           }
           leaf policer-medium-low-frames {
             type int32;
             description
               "Number of loss priority medium low frames";
           }
           leaf policer-medium-low-bytes {
             type int32;
             description
               "Number of loss priority medium low bytes";
           }
           leaf policer-medium-low-rate {
             type int32;
             description
               "Rate of loss priority medium low pkts";
           }
         }
         container layer2-output-policer-statistics {
           description
             "Layer 2 output policer statistics for interface";
           leaf policer-low-bytes {
             type int32;
             description
               "Number of loss priority low bytes";
           }
           leaf policer-low-frames {
             type int32;
             description
               "Number of loss priority low frames";
           }
           leaf policer-low-rate {
             type int32;
             description
               "Rate of loss priority low pkts";
           }
           leaf policer-medium-high-bytes {
             type int32;
             description
               "Number of loss priority medium high bytes";
           }
           leaf policer-medium-high-frames {
             type int32;
             description
               "Number of loss priority medium high frames";
           }
           leaf policer-medium-high-rate {
             type int32;
             description
               "Rate of loss priority medium high rate";
           }
           leaf policer-high-bytes {
             type int32;
             description
               "Number of loss priority high bytes";
           }
           leaf policer-high-frames {
             type int32;
             description
               "Number of loss priority high frames";
           }
           leaf policer-high-rate {
             type int32;
             description
               "Rate of loss priority high rate";
           }
           leaf policer-dropped-bytes {
             type int32;
             description
               "Number of dropped bytes";
           }
           leaf policer-dropped-frames {
             type int32;
             description
               "Number of dropped frames";
           }
           leaf policer-dropped-rate {
             type int32;
             description
               "Number of dropped rate";
           }
           leaf policer-medium-low-frames {
             type int32;
             description
               "Number of loss priority medium low frames";
           }
           leaf policer-medium-low-bytes {
             type int32;
             description
               "Number of loss priority medium low bytes";
           }
           leaf policer-medium-low-rate {
             type int32;
             description
               "Rate of loss priority medium low pkts";
           }
         }
         container atm-input-policer-statistics {
           description
             "ATM input Policer Statistics for interface";
           leaf atm-policer-traffic-count-cells {
             type int32;
             description
               "Stats for counted ATM Cells";
           }
           leaf atm-policer-traffic-discard-cells {
             type int32;
             description
               "Stats for discarded ATM Cells";
           }
           leaf atm-policer-traffic-discard-tag-cells {
             type int32;
             description
               "Stats for discard-tag ATM Cells";
           }
         }
         container mac-policer-information {
           leaf mac-address {
             type jt:mac-addr;
           }
           leaf mac-entry-type {
             type string;
           }
           leaf receive-bytes {
             type int32;
           }
           leaf transmit-bytes {
             type int32;
           }
           leaf receive-frames {
             type int32;
           }
           leaf transmit-frames {
             type int32;
           }
           container ether-policer-list {
             list ether-policer-record {
               leaf policer-type {
                 type string;
               }
               leaf out-of-spec-frames {
                 type int32;
               }
               leaf out-of-spec-bytes {
                 type int32;
               }
             }
           }
         }
         container ppp-parameters {
           description
             "PPP parameters";
           leaf lcp-restart-timer {
             type int32;
             description
               "LCP restart timer (milliseconds)";
           }
           leaf ncp-restart-timer {
             type int32;
             description
               "NCP restart timer (milliseconds)";
           }
           leaf termination-requests {
             type string;
             description
               "Whether PPP termination requests are sent";
           }
           leaf loopback-clear-timer {
             type int32;
             description
               "PPP loopback clear timer (seconds)";
           }
         }
       }
       container controller {
         leaf name {
           type string;
           description
             "Name of this item";
         }
         leaf admin-status {
           type string;
           description
             "Desired state of the interface";
         }
         leaf oper-status {
           type string;
           description
             "Current operational state of the interface";
         }
       }
       container interface-set {
         leaf name {
           type string;
           description
             "Name of this item";
         }
         container traffic-statistics {
           leaf input-bps {
             type int32;
           }
           leaf input-pps {
             type int32;
           }
           leaf output-bps {
             type int32;
           }
           leaf output-pps {
             type int32;
           }
           leaf input-packets {
             type int32;
           }
           leaf output-packets {
             type int32;
           }
           leaf input-bytes {
             type int32;
           }
           leaf output-bytes {
             type int32;
           }
           container ipv6-transit-statistics {
             leaf input-bytes {
               type int32;
             }
             leaf output-bytes {
               type int32;
             }
             leaf input-packets {
               type int32;
             }
             leaf output-packets {
               type int32;
             }
           }
           container ipv6-total-statistics {
             leaf input-bytes {
               type int32;
             }
             leaf output-bytes {
               type int32;
             }
             leaf input-packets {
               type int32;
             }
             leaf output-packets {
               type int32;
             }
           }
         }
         container interface-set-queue-information {
           container queue-counters {
             description
               "Queue counter statistics";
             leaf queue-counters-error-message {
               type string;
               description
                 "Queue statistics not available for this interface";
             }
             list queue {
               description
                 "Counters for a single queue";
               leaf queue-number {
                 type int32;
                 description
                   "Queue number";
               }
               leaf queue-counters-queued-packets {
                 type uint64;
                 description
                   "Queued packet count";
               }
               leaf queue-counters-trans-packets {
                 type uint64;
                 description
                   "Total number of transmitted packets";
               }
               leaf queue-counters-total-drop-packets {
                 type uint64;
                 description
                   "Number of total packets dropped at the queue";
               }
               leaf forwarding-class-name {
                 type string;
                 description
                   "Forwarding class name associated with queue";
               }
               leaf queue-counters-queued-packets-rate {
                 type uint64;
                 description
                   "Rate at which packets are queued";
               }
               leaf queue-counters-queued-bytes {
                 type uint64;
                 description
                   "Queued bytes count";
               }
               leaf queue-counters-queued-bytes-rate {
                 type uint64;
                 description
                   "Rate at which bytes are queued";
               }
               leaf queue-counters-queued-packets-na {
                 type string;
                 description
                   "Queued packets not available";
               }
               leaf queue-counters-queued-bytes-na {
                 type string;
                 description
                   "Queued bytes not available";
               }
               leaf queue-counters-trans-packets-rate {
                 type uint64;
                 description
                   "Rate at which packets are transmitted";
               }
               leaf queue-counters-trans-bytes {
                 type uint64;
                 description
                   "Total number of transmitted bytes";
               }
               leaf queue-counters-trans-bytes-rate {
                 type uint64;
                 description
                   "Rate at which bytes are transmitted";
               }
               leaf queue-counters-tail-drop-packets-na {
                 type string;
                 description
                   "Number of packets dropped due to tail drop not available";
               }
               leaf queue-counters-tail-drop-packets {
                 type uint64;
                 description
                   "Number of packets dropped at the tail of the queue";
               }
               leaf queue-counters-tail-drop-packets-rate {
                 type uint64;
                 description
                   "Rate at which packets are dropped at tail of queue";
               }
               leaf queue-counters-tail-drop-bytes {
                 type uint64;
                 description
                   "Number of packets dropped at tail drop of the queue";
               }
               leaf queue-counters-tail-drop-bytes-rate {
                 type uint64;
                 description
                   "Number of packets dropped at tail drop of the queue";
               }
               leaf queue-counters-rate-limit-drop-packets-na {
                 type string;
                 description
                   "Number of packets dropped due to rate-limit drop not 
                   available";
               }
               leaf queue-counters-rate-limit-drop-packets {
                 type uint64;
                 description
                   "Number of packets dropped by rate-limit for the queue";
               }
               leaf queue-counters-rate-limit-drop-packets-rate {
                 type uint64;
                 description
                   "Rate at which packets are dropped by rate-limit for the 
                   queue";
               }
               leaf queue-counters-rate-limit-drop-bytes-na {
                 type string;
                 description
                   "Number of bytes dropped due to tail drop not available";
               }
               leaf queue-counters-rate-limit-drop-bytes {
                 type uint64;
                 description
                   "Number of bytes dropped at the tail of the queue";
               }
               leaf queue-counters-rate-limit-drop-bytes-rate {
                 type uint64;
                 description
                   "Rate at which bytes are dropped at the tail of the queue";
               }
               leaf queue-counters-red-packets-na {
                 type string;
                 description
                   "Number of packets dropped due to RED not available";
               }
               leaf queue-counters-red-packets {
                 type uint64;
                 description
                   "Number of packets dropped due to RED";
               }
               leaf queue-counters-red-packets-rate {
                 type uint64;
                 description
                   "Rate at which packets are dropped due to RED";
               }
               leaf queue-counters-red-packets-ln {
                 type uint64;
                 description
                   "Number of RED dropped low-loss, non-TCP packets";
               }
               leaf queue-counters-red-packets-rate-ln {
                 type uint64;
                 description
                   "RED drop rate for low-loss, non-TCP packets";
               }
               leaf queue-counters-red-packets-lt {
                 type uint64;
                 description
                   "Number of RED dropped of low-loss, TCP packets";
               }
               leaf queue-counters-red-packets-rate-lt {
                 type uint64;
                 description
                   "RED drop rate for low-loss, TCP packets";
               }
               leaf queue-counters-red-packets-hn {
                 type uint64;
                 description
                   "Number of RED dropped high-loss, non-TCP packets";
               }
               leaf queue-counters-red-packets-rate-hn {
                 type uint64;
                 description
                   "RED drop rate for high-loss, non-TCP packets";
               }
               leaf queue-counters-red-packets-ht {
                 type uint64;
                 description
                   "Number of RED dropped high-loss, TCP packets";
               }
               leaf queue-counters-red-packets-rate-ht {
                 type uint64;
                 description
                   "RED drop rate for high-loss, TCP packets";
               }
               leaf queue-counters-red-packets-low {
                 type uint64;
                 description
                   "Number of RED dropped low-loss packets";
               }
               leaf queue-counters-red-packets-rate-low {
                 type uint64;
                 description
                   "RED drop rate for low-loss packets";
               }
               leaf queue-counters-red-packets-medium-low {
                 type uint64;
                 description
                   "Number of RED dropped medium-low-loss packets";
               }
               leaf queue-counters-red-packets-rate-medium-low {
                 type uint64;
                 description
                   "RED drop rate for medium-low-loss packets";
               }
               leaf queue-counters-red-packets-medium-high {
                 type uint64;
                 description
                   "Number of RED dropped medium-high-loss packets";
               }
               leaf queue-counters-red-packets-rate-medium-high {
                 type uint64;
                 description
                   "RED drop rate for medium-high-loss packets";
               }
               leaf queue-counters-red-packets-medium {
                 type uint64;
                 description
                   "Number of RED dropped medium-loss packets";
               }
               leaf queue-counters-red-packets-rate-medium {
                 type uint64;
                 description
                   "RED drop rate for medium-loss packets";
               }
               leaf queue-counters-red-packets-high {
                 type uint64;
                 description
                   "Number of RED dropped high-loss packets";
               }
               leaf queue-counters-red-packets-rate-high {
                 type uint64;
                 description
                   "RED drop rate for high-loss packets";
               }
               leaf queue-counters-red-bytes-na {
                 type string;
                 description
                   "Number of bytes dropped due to RED not available";
               }
               leaf queue-counters-red-bytes {
                 type uint64;
                 description
                   "Number of bytes dropped due to RED";
               }
               leaf queue-counters-red-bytes-rate {
                 type uint64;
                 description
                   "Rate at which bytes are dropped due to RED";
               }
               leaf queue-counters-red-bytes-ln {
                 type uint64;
                 description
                   "Number of RED dropped low-loss, non-TCP bytes";
               }
               leaf queue-counters-red-bytes-rate-ln {
                 type uint64;
                 description
                   "RED drop rate for low-loss, non-TCP bytes";
               }
               leaf queue-counters-red-bytes-lt {
                 type uint64;
                 description
                   "Number of RED dropped low-loss, TCP bytes";
               }
               leaf queue-counters-red-bytes-rate-lt {
                 type uint64;
                 description
                   "RED drop rate for low-loss, TCP bytes";
               }
               leaf queue-counters-red-bytes-hn {
                 type uint64;
                 description
                   "Number of RED dropped high-loss, non-TCP bytes";
               }
               leaf queue-counters-red-bytes-rate-hn {
                 type uint64;
                 description
                   "RED drop rate for high-loss, non-TCP bytes";
               }
               leaf queue-counters-red-bytes-ht {
                 type uint64;
                 description
                   "Number of RED dropped high-loss, TCP bytes";
               }
               leaf queue-counters-red-bytes-rate-ht {
                 type uint64;
                 description
                   "RED drop rate for high-loss, TCP bytes";
               }
               leaf queue-counters-red-bytes-low {
                 type uint64;
                 description
                   "Number of RED dropped low-loss bytes";
               }
               leaf queue-counters-red-bytes-rate-low {
                 type uint64;
                 description
                   "RED drop rate for low-loss bytes";
               }
               leaf queue-counters-red-bytes-medium-low {
                 type uint64;
                 description
                   "Number of RED dropped medium-low-loss bytes";
               }
               leaf queue-counters-red-bytes-rate-medium-low {
                 type uint64;
                 description
                   "RED drop rate for medium-low-loss bytes";
               }
               leaf queue-counters-red-bytes-medium-high {
                 type uint64;
                 description
                   "Number of RED dropped medium-high-loss bytes";
               }
               leaf queue-counters-red-bytes-rate-medium-high {
                 type uint64;
                 description
                   "RED drop rate for medium-high-loss bytes";
               }
               leaf queue-counters-red-bytes-medium {
                 type uint64;
                 description
                   "Number of RED dropped medium-loss bytes";
               }
               leaf queue-counters-red-bytes-rate-medium {
                 type uint64;
                 description
                   "RED drop rate for medium-loss bytes";
               }
               leaf queue-counters-red-bytes-high {
                 type uint64;
                 description
                   "Number of RED dropped high-loss bytes";
               }
               leaf queue-counters-red-bytes-rate-high {
                 type uint64;
                 description
                   "RED drop rate for high-loss bytes";
               }
               leaf queue-counters-timestamp {
                 type uint64;
                 description
                   "Last packet enqueued timestamp";
               }
               leaf queue-counters-total-drop-packets-rate {
                 type uint64;
                 description
                   "Number of total packets dropped at the queue";
               }
               leaf queue-counters-total-drop-bytes {
                 type uint64;
                 description
                   "Number of total packets dropped at the queue";
               }
               leaf queue-counters-total-drop-bytes-rate {
                 type uint64;
                 description
                   "Number of total packets dropped at the queue";
               }
               leaf queue-counters-reserved-buffer-packets {
                 type int32;
                 description
                   "Queues's usage of reserved buffer pool in pkts";
               }
               leaf queue-counters-reserved-buffer-bytes {
                 type int32;
                 description
                   "Queues's usage of reserved buffer pool in bytes";
               }
               leaf queue-counters-shared-buffer-packets {
                 type int32;
                 description
                   "Queues's usage of shared buffer pool in pkts";
               }
               leaf queue-counters-shared-buffer-bytes {
                 type int32;
                 description
                   "Queues's usage of shared buffer pool in bytes";
               }
               leaf queue-counters-depth-average {
                 type int32;
                 description
                   "Time averaged queue depth";
               }
               leaf queue-counters-depth-current {
                 type int32;
                 description
                   "Current instantaneous queue depth";
               }
               leaf queue-counters-depth-peak {
                 type int32;
                 description
                   "Peak queue depth";
               }
               leaf queue-counters-depth-max {
                 type int32;
                 description
                   "Maximum queue depth attained";
               }
               leaf queue-counters-srx-reserved-buffer-bytes {
                 type int32;
                 description
                   "Queues's usage of reserved buffer pool in bytes";
               }
               leaf queue-counters-srx-depth-current {
                 type int32;
                 description
                   "Current instantaneous queue depth";
               }
             }
             container interface-cos-short-summary {
               description
                 "Summary of queue information on an interface";
               leaf intf-cos-queue-type {
                 type string;
                 description
                   "Interface queue type";
               }
               leaf intf-cos-num-queues-supported {
                 type int32;
                 description
                   "Number of queues supported on this interface";
               }
               leaf intf-cos-num-queues-in-use {
                 type int32;
                 description
                   "Number of queues currently in use on this interface";
               }
               leaf intf-cos-queue-dedicated-or-shared {
                 type string;
                 description
                   "Interface has dedicated or shared queues";
               }
               leaf intf-cos-sched-resource-type {
                 type string;
                 description
                   "Interface scheduling resource type";
               }
               leaf intf-cos-sched-resource-usage-mic-limit {
                 type int32;
                 description
                   "MIC/PIC scheduling resource usage limit";
               }
               leaf intf-cos-sched-resource-usage-mic-count {
                 type int32;
                 description
                   "MIC/PIC scheduling resource usage count";
               }
               leaf intf-cos-sched-resource-usage-port-limit {
                 type int32;
                 description
                   "Interface scheduling resource limit";
               }
               leaf intf-cos-sched-resource-usage-port-count {
                 type int32;
                 description
                   "Interface scheduling resource usage";
               }
             }
             container interface-cos-summary {
               description
                 "Summary of forwarding class and queue information on an 
                 interface";
               leaf intf-cos-forwarding-classes-supported {
                 type int32;
                 description
                   "Number of forwarding classes supported on this interface";
               }
               leaf intf-cos-forwarding-classes-in-use {
                 type int32;
                 description
                   "Number of forwarding classes currently in use on this 
                   interface";
               }
               leaf intf-cos-queue-type {
                 type string;
                 description
                   "Interface queue type";
               }
               leaf intf-cos-num-queues-supported {
                 type int32;
                 description
                   "Number of queues supported on this interface";
               }
               leaf intf-cos-num-queues-in-use {
                 type int32;
                 description
                   "Number of queues currently in use on this interface";
               }
               leaf intf-cos-queue-dedicated-or-shared {
                 type string;
                 description
                   "Interface has dedicated or shared queues";
               }
               leaf intf-cos-sched-resource-type {
                 type string;
                 description
                   "Interface scheduling resource type";
               }
               leaf intf-cos-sched-resource-usage-mic-limit {
                 type int32;
                 description
                   "MIC/PIC scheduling resource usage limit";
               }
               leaf intf-cos-sched-resource-usage-mic-count {
                 type int32;
                 description
                   "MIC/PIC scheduling resource usage count";
               }
               leaf intf-cos-sched-resource-usage-port-limit {
                 type int32;
                 description
                   "Interface scheduling resource limit";
               }
               leaf intf-cos-sched-resource-usage-port-count {
                 type int32;
                 description
                   "Interface scheduling resource usage";
               }
               leaf intf-cos-burst-size-for-ifl {
                 type int32;
                 description
                   "Burst size for the logical interface";
               }
             }
           }
           container ingress-queue-counters {
             description
               "Ingress queue counter statistics";
             list queue {
               description
                 "Counters for a single queue";
               leaf queue-number {
                 type int32;
                 description
                   "Queue number";
               }
               leaf forwarding-class-name {
                 type string;
                 description
                   "Forwarding class name associated with queue";
               }
               leaf queue-counters-queued-packets {
                 type uint64;
                 description
                   "Queued packet count";
               }
               leaf queue-counters-queued-packets-rate {
                 type uint64;
                 description
                   "Rate at which packets are queued";
               }
               leaf queue-counters-queued-bytes {
                 type uint64;
                 description
                   "Queued bytes count";
               }
               leaf queue-counters-queued-bytes-rate {
                 type uint64;
                 description
                   "Rate at which bytes are queued";
               }
               leaf queue-counters-queued-packets-na {
                 type string;
                 description
                   "Queued packets not available";
               }
               leaf queue-counters-queued-bytes-na {
                 type string;
                 description
                   "Queued bytes not available";
               }
               leaf queue-counters-trans-packets {
                 type uint64;
                 description
                   "Total number of transmitted packets";
               }
               leaf queue-counters-trans-packets-rate {
                 type uint64;
                 description
                   "Rate at which packets are transmitted";
               }
               leaf queue-counters-trans-bytes {
                 type uint64;
                 description
                   "Total number of transmitted bytes";
               }
               leaf queue-counters-trans-bytes-rate {
                 type uint64;
                 description
                   "Rate at which bytes are transmitted";
               }
               leaf queue-counters-tail-drop-packets-na {
                 type string;
                 description
                   "Number of packets dropped due to tail drop not available";
               }
               leaf queue-counters-tail-drop-packets {
                 type uint64;
                 description
                   "Number of packets dropped at the tail of the queue";
               }
               leaf queue-counters-tail-drop-packets-rate {
                 type uint64;
                 description
                   "Rate at which packets are dropped at tail of queue";
               }
               leaf queue-counters-tail-drop-bytes {
                 type uint64;
                 description
                   "Number of packets dropped at tail drop of the queue";
               }
               leaf queue-counters-tail-drop-bytes-rate {
                 type uint64;
                 description
                   "Number of packets dropped at tail drop of the queue";
               }
               leaf queue-counters-rate-limit-drop-packets-na {
                 type string;
                 description
                   "Number of packets dropped due to rate-limit drop not 
                   available";
               }
               leaf queue-counters-rate-limit-drop-packets {
                 type uint64;
                 description
                   "Number of packets dropped by rate-limit for the queue";
               }
               leaf queue-counters-rate-limit-drop-packets-rate {
                 type uint64;
                 description
                   "Rate at which packets are dropped by rate-limit for the 
                   queue";
               }
               leaf queue-counters-rate-limit-drop-bytes-na {
                 type string;
                 description
                   "Number of bytes dropped due to tail drop not available";
               }
               leaf queue-counters-rate-limit-drop-bytes {
                 type uint64;
                 description
                   "Number of bytes dropped at the tail of the queue";
               }
               leaf queue-counters-rate-limit-drop-bytes-rate {
                 type uint64;
                 description
                   "Rate at which bytes are dropped at the tail of the queue";
               }
               leaf queue-counters-red-packets-na {
                 type string;
                 description
                   "Number of packets dropped due to RED not available";
               }
               leaf queue-counters-red-packets {
                 type uint64;
                 description
                   "Number of packets dropped due to RED";
               }
               leaf queue-counters-red-packets-rate {
                 type uint64;
                 description
                   "Rate at which packets are dropped due to RED";
               }
               leaf queue-counters-red-packets-ln {
                 type uint64;
                 description
                   "Number of RED dropped low-loss, non-TCP packets";
               }
               leaf queue-counters-red-packets-rate-ln {
                 type uint64;
                 description
                   "RED drop rate for low-loss, non-TCP packets";
               }
               leaf queue-counters-red-packets-lt {
                 type uint64;
                 description
                   "Number of RED dropped of low-loss, TCP packets";
               }
               leaf queue-counters-red-packets-rate-lt {
                 type uint64;
                 description
                   "RED drop rate for low-loss, TCP packets";
               }
               leaf queue-counters-red-packets-hn {
                 type uint64;
                 description
                   "Number of RED dropped high-loss, non-TCP packets";
               }
               leaf queue-counters-red-packets-rate-hn {
                 type uint64;
                 description
                   "RED drop rate for high-loss, non-TCP packets";
               }
               leaf queue-counters-red-packets-ht {
                 type uint64;
                 description
                   "Number of RED dropped high-loss, TCP packets";
               }
               leaf queue-counters-red-packets-rate-ht {
                 type uint64;
                 description
                   "RED drop rate for high-loss, TCP packets";
               }
               leaf queue-counters-red-packets-low {
                 type uint64;
                 description
                   "Number of RED dropped low-loss packets";
               }
               leaf queue-counters-red-packets-rate-low {
                 type uint64;
                 description
                   "RED drop rate for low-loss packets";
               }
               leaf queue-counters-red-packets-medium-low {
                 type uint64;
                 description
                   "Number of RED dropped medium-low-loss packets";
               }
               leaf queue-counters-red-packets-rate-medium-low {
                 type uint64;
                 description
                   "RED drop rate for medium-low-loss packets";
               }
               leaf queue-counters-red-packets-medium-high {
                 type uint64;
                 description
                   "Number of RED dropped medium-high-loss packets";
               }
               leaf queue-counters-red-packets-rate-medium-high {
                 type uint64;
                 description
                   "RED drop rate for medium-high-loss packets";
               }
               leaf queue-counters-red-packets-medium {
                 type uint64;
                 description
                   "Number of RED dropped medium-loss packets";
               }
               leaf queue-counters-red-packets-rate-medium {
                 type uint64;
                 description
                   "RED drop rate for medium-loss packets";
               }
               leaf queue-counters-red-packets-high {
                 type uint64;
                 description
                   "Number of RED dropped high-loss packets";
               }
               leaf queue-counters-red-packets-rate-high {
                 type uint64;
                 description
                   "RED drop rate for high-loss packets";
               }
               leaf queue-counters-red-bytes-na {
                 type string;
                 description
                   "Number of bytes dropped due to RED not available";
               }
               leaf queue-counters-red-bytes {
                 type uint64;
                 description
                   "Number of bytes dropped due to RED";
               }
               leaf queue-counters-red-bytes-rate {
                 type uint64;
                 description
                   "Rate at which bytes are dropped due to RED";
               }
               leaf queue-counters-red-bytes-ln {
                 type uint64;
                 description
                   "Number of RED dropped low-loss, non-TCP bytes";
               }
               leaf queue-counters-red-bytes-rate-ln {
                 type uint64;
                 description
                   "RED drop rate for low-loss, non-TCP bytes";
               }
               leaf queue-counters-red-bytes-lt {
                 type uint64;
                 description
                   "Number of RED dropped low-loss, TCP bytes";
               }
               leaf queue-counters-red-bytes-rate-lt {
                 type uint64;
                 description
                   "RED drop rate for low-loss, TCP bytes";
               }
               leaf queue-counters-red-bytes-hn {
                 type uint64;
                 description
                   "Number of RED dropped high-loss, non-TCP bytes";
               }
               leaf queue-counters-red-bytes-rate-hn {
                 type uint64;
                 description
                   "RED drop rate for high-loss, non-TCP bytes";
               }
               leaf queue-counters-red-bytes-ht {
                 type uint64;
                 description
                   "Number of RED dropped high-loss, TCP bytes";
               }
               leaf queue-counters-red-bytes-rate-ht {
                 type uint64;
                 description
                   "RED drop rate for high-loss, TCP bytes";
               }
               leaf queue-counters-red-bytes-low {
                 type uint64;
                 description
                   "Number of RED dropped low-loss bytes";
               }
               leaf queue-counters-red-bytes-rate-low {
                 type uint64;
                 description
                   "RED drop rate for low-loss bytes";
               }
               leaf queue-counters-red-bytes-medium-low {
                 type uint64;
                 description
                   "Number of RED dropped medium-low-loss bytes";
               }
               leaf queue-counters-red-bytes-rate-medium-low {
                 type uint64;
                 description
                   "RED drop rate for medium-low-loss bytes";
               }
               leaf queue-counters-red-bytes-medium-high {
                 type uint64;
                 description
                   "Number of RED dropped medium-high-loss bytes";
               }
               leaf queue-counters-red-bytes-rate-medium-high {
                 type uint64;
                 description
                   "RED drop rate for medium-high-loss bytes";
               }
               leaf queue-counters-red-bytes-medium {
                 type uint64;
                 description
                   "Number of RED dropped medium-loss bytes";
               }
               leaf queue-counters-red-bytes-rate-medium {
                 type uint64;
                 description
                   "RED drop rate for medium-loss bytes";
               }
               leaf queue-counters-red-bytes-high {
                 type uint64;
                 description
                   "Number of RED dropped high-loss bytes";
               }
               leaf queue-counters-red-bytes-rate-high {
                 type uint64;
                 description
                   "RED drop rate for high-loss bytes";
               }
               leaf queue-counters-timestamp {
                 type uint64;
                 description
                   "Last packet enqueued timestamp";
               }
               leaf queue-counters-total-drop-packets {
                 type uint64;
                 description
                   "Number of total packets dropped at the queue";
               }
               leaf queue-counters-total-drop-packets-rate {
                 type uint64;
                 description
                   "Number of total packets dropped at the queue";
               }
               leaf queue-counters-total-drop-bytes {
                 type uint64;
                 description
                   "Number of total packets dropped at the queue";
               }
               leaf queue-counters-total-drop-bytes-rate {
                 type uint64;
                 description
                   "Number of total packets dropped at the queue";
               }
               leaf queue-counters-reserved-buffer-packets {
                 type int32;
                 description
                   "Queues's usage of reserved buffer pool in pkts";
               }
               leaf queue-counters-reserved-buffer-bytes {
                 type int32;
                 description
                   "Queues's usage of reserved buffer pool in bytes";
               }
               leaf queue-counters-shared-buffer-packets {
                 type int32;
                 description
                   "Queues's usage of shared buffer pool in pkts";
               }
               leaf queue-counters-shared-buffer-bytes {
                 type int32;
                 description
                   "Queues's usage of shared buffer pool in bytes";
               }
               leaf queue-counters-depth-average {
                 type int32;
                 description
                   "Time averaged queue depth";
               }
               leaf queue-counters-depth-current {
                 type int32;
                 description
                   "Current instantaneous queue depth";
               }
               leaf queue-counters-depth-peak {
                 type int32;
                 description
                   "Peak queue depth";
               }
               leaf queue-counters-depth-max {
                 type int32;
                 description
                   "Maximum queue depth attained";
               }
               leaf queue-counters-srx-reserved-buffer-bytes {
                 type int32;
                 description
                   "Queues's usage of reserved buffer pool in bytes";
               }
               leaf queue-counters-srx-depth-current {
                 type int32;
                 description
                   "Current instantaneous queue depth";
               }
             }
             container interface-cos-summary {
               description
                 "Summary of forwarding class and queue information on an 
                 interface";
               leaf intf-cos-forwarding-classes-supported {
                 type int32;
                 description
                   "Number of forwarding classes supported on this interface";
               }
               leaf intf-cos-forwarding-classes-in-use {
                 type int32;
                 description
                   "Number of forwarding classes currently in use on this 
                   interface";
               }
               leaf intf-cos-queue-type {
                 type string;
                 description
                   "Interface queue type";
               }
               leaf intf-cos-num-queues-supported {
                 type int32;
                 description
                   "Number of queues supported on this interface";
               }
               leaf intf-cos-num-queues-in-use {
                 type int32;
                 description
                   "Number of queues currently in use on this interface";
               }
               leaf intf-cos-queue-dedicated-or-shared {
                 type string;
                 description
                   "Interface has dedicated or shared queues";
               }
               leaf intf-cos-sched-resource-type {
                 type string;
                 description
                   "Interface scheduling resource type";
               }
               leaf intf-cos-sched-resource-usage-mic-limit {
                 type int32;
                 description
                   "MIC/PIC scheduling resource usage limit";
               }
               leaf intf-cos-sched-resource-usage-mic-count {
                 type int32;
                 description
                   "MIC/PIC scheduling resource usage count";
               }
               leaf intf-cos-sched-resource-usage-port-limit {
                 type int32;
                 description
                   "Interface scheduling resource limit";
               }
               leaf intf-cos-sched-resource-usage-port-count {
                 type int32;
                 description
                   "Interface scheduling resource usage";
               }
               leaf intf-cos-burst-size-for-ifl {
                 type int32;
                 description
                   "Burst size for the logical interface";
               }
             }
             container interface-cos-short-summary {
               description
                 "Summary of queue information on an interface";
               leaf intf-cos-queue-type {
                 type string;
                 description
                   "Interface queue type";
               }
               leaf intf-cos-num-queues-supported {
                 type int32;
                 description
                   "Number of queues supported on this interface";
               }
               leaf intf-cos-num-queues-in-use {
                 type int32;
                 description
                   "Number of queues currently in use on this interface";
               }
               leaf intf-cos-queue-dedicated-or-shared {
                 type string;
                 description
                   "Interface has dedicated or shared queues";
               }
               leaf intf-cos-sched-resource-type {
                 type string;
                 description
                   "Interface scheduling resource type";
               }
               leaf intf-cos-sched-resource-usage-mic-limit {
                 type int32;
                 description
                   "MIC/PIC scheduling resource usage limit";
               }
               leaf intf-cos-sched-resource-usage-mic-count {
                 type int32;
                 description
                   "MIC/PIC scheduling resource usage count";
               }
               leaf intf-cos-sched-resource-usage-port-limit {
                 type int32;
                 description
                   "Interface scheduling resource limit";
               }
               leaf intf-cos-sched-resource-usage-port-count {
                 type int32;
                 description
                   "Interface scheduling resource usage";
               }
             }
             container queue-num-forwarding-class-name-map {
               leaf queue-number {
                 type int32;
                 description
                   "Queue number";
               }
               leaf forwarding-class-name {
                 type string;
                 description
                   "Forwarding class name associated with queue";
               }
             }
           }
         }
         leaf interface-set-index {
           type uint64;
           description
             "Class-of-service logical interface index";
         }
         leaf snmp-index {
           type int32;
           description
             "SNMP ifIndex for this interface";
         }
         list interface-set-member-list {
           leaf interface-set-member {
             type string;
           }
         }
         container aci-vlan-iflset-information {
           leaf agent-circuit-id {
             type string;
             description
               "Agent Circuit ID";
           }
           leaf agent-remote-id {
             type string;
             description
               "Agent Remote ID";
           }
         }
         container line-identity-iflset-information {
           leaf agent-circuit-id {
             type string;
             description
               "Agent Circuit ID";
           }
           leaf agent-remote-id {
             type string;
             description
               "Agent Remote ID";
           }
         }
         container pppoe-uifl-iflset-information {
           leaf dynamic-profile {
             type string;
             description
               "Dynamic Profile name";
           }
           leaf max-sessions {
             type int32;
             description
               "Maximum number of PPPoE sessions";
           }
           leaf max-sessions-vsa-ignore {
             type string;
             description
               "Ignore max-sessions VSA";
           }
         }
         list lag-targeting-summary {
           leaf targeting-intf-name {
             type string;
           }
           leaf targeting-intf-type {
             type string;
           }
           leaf targeting-intf-link-state {
             type string;
           }
         }
       }
     }
     container interface-filter-information {
       list physical-interface {
         key "name";
         description
           "Information about a single physical interface";
         leaf name {
           type string;
           description
             "Name of this item";
         }
         leaf admin-status {
           type string;
           description
             "Desired state of the interface";
         }
         leaf oper-status {
           type string;
           description
             "Current operational state of the interface";
         }
         leaf esi-source-bmac {
           type jt:mac-addr;
           description
             "Ethernet segment source B-MAC for this interface";
         }
         leaf sonet-payload-pointer-curptr {
           type string;
           description
             "Value of the SONET/SDH payload pointer, derived from the H1 
             and H2 overhead bytes";
         }
         leaf sonet-payload-pointer-ptrinc-count {
           type string;
           description
             "Number of times the value of the SONET/SDH payload pointer had
             positive justification";
         }
         leaf sonet-payload-pointer-ptrdec-count {
           type string;
           description
             "Number of times the value of the SONET/SDH payload pointer had
             negative justification";
         }
         leaf sonet-payload-pointer-newptr-ndf-count {
           type string;
           description
             "Number of times a new payload pointer was created with the New
             Data Found flag set";
         }
         leaf link-partner-status {
           type string;
           description
             "Auto-negotiation status of link partner";
         }
         container optics-properties {
           description
             "Optics properties";
           leaf wavelength {
             type string;
             description
               "Wavelength of optics in nanometers";
           }
           leaf frequency {
             type string;
             description
               "Frequency of optics in terahertz";
           }
         }
         container queue-counters {
           description
             "Queue counter statistics";
           leaf queue-counters-error-message {
             type string;
             description
               "Queue statistics not available for this interface";
           }
           list queue {
             description
               "Counters for a single queue";
             leaf queue-number {
               type int32;
               description
                 "Queue number";
             }
             leaf queue-counters-queued-packets {
               type uint64;
               description
                 "Queued packet count";
             }
             leaf queue-counters-trans-packets {
               type uint64;
               description
                 "Total number of transmitted packets";
             }
             leaf queue-counters-total-drop-packets {
               type uint64;
               description
                 "Number of total packets dropped at the queue";
             }
             leaf forwarding-class-name {
               type string;
               description
                 "Forwarding class name associated with queue";
             }
             leaf queue-counters-queued-packets-rate {
               type uint64;
               description
                 "Rate at which packets are queued";
             }
             leaf queue-counters-queued-bytes {
               type uint64;
               description
                 "Queued bytes count";
             }
             leaf queue-counters-queued-bytes-rate {
               type uint64;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets-rate {
               type uint64;
               description
                 "Rate at which packets are transmitted";
             }
             leaf queue-counters-trans-bytes {
               type uint64;
               description
                 "Total number of transmitted bytes";
             }
             leaf queue-counters-trans-bytes-rate {
               type uint64;
               description
                 "Rate at which bytes are transmitted";
             }
             leaf queue-counters-tail-drop-packets-na {
               type string;
               description
                 "Number of packets dropped due to tail drop not available";
             }
             leaf queue-counters-tail-drop-packets {
               type uint64;
               description
                 "Number of packets dropped at the tail of the queue";
             }
             leaf queue-counters-tail-drop-packets-rate {
               type uint64;
               description
                 "Rate at which packets are dropped at tail of queue";
             }
             leaf queue-counters-tail-drop-bytes {
               type uint64;
               description
                 "Number of packets dropped at tail drop of the queue";
             }
             leaf queue-counters-tail-drop-bytes-rate {
               type uint64;
               description
                 "Number of packets dropped at tail drop of the queue";
             }
             leaf queue-counters-rate-limit-drop-packets-na {
               type string;
               description
                 "Number of packets dropped due to rate-limit drop not 
                 available";
             }
             leaf queue-counters-rate-limit-drop-packets {
               type uint64;
               description
                 "Number of packets dropped by rate-limit for the queue";
             }
             leaf queue-counters-rate-limit-drop-packets-rate {
               type uint64;
               description
                 "Rate at which packets are dropped by rate-limit for the 
                 queue";
             }
             leaf queue-counters-rate-limit-drop-bytes-na {
               type string;
               description
                 "Number of bytes dropped due to tail drop not available";
             }
             leaf queue-counters-rate-limit-drop-bytes {
               type uint64;
               description
                 "Number of bytes dropped at the tail of the queue";
             }
             leaf queue-counters-rate-limit-drop-bytes-rate {
               type uint64;
               description
                 "Rate at which bytes are dropped at the tail of the queue";
             }
             leaf queue-counters-red-packets-na {
               type string;
               description
                 "Number of packets dropped due to RED not available";
             }
             leaf queue-counters-red-packets {
               type uint64;
               description
                 "Number of packets dropped due to RED";
             }
             leaf queue-counters-red-packets-rate {
               type uint64;
               description
                 "Rate at which packets are dropped due to RED";
             }
             leaf queue-counters-red-packets-ln {
               type uint64;
               description
                 "Number of RED dropped low-loss, non-TCP packets";
             }
             leaf queue-counters-red-packets-rate-ln {
               type uint64;
               description
                 "RED drop rate for low-loss, non-TCP packets";
             }
             leaf queue-counters-red-packets-lt {
               type uint64;
               description
                 "Number of RED dropped of low-loss, TCP packets";
             }
             leaf queue-counters-red-packets-rate-lt {
               type uint64;
               description
                 "RED drop rate for low-loss, TCP packets";
             }
             leaf queue-counters-red-packets-hn {
               type uint64;
               description
                 "Number of RED dropped high-loss, non-TCP packets";
             }
             leaf queue-counters-red-packets-rate-hn {
               type uint64;
               description
                 "RED drop rate for high-loss, non-TCP packets";
             }
             leaf queue-counters-red-packets-ht {
               type uint64;
               description
                 "Number of RED dropped high-loss, TCP packets";
             }
             leaf queue-counters-red-packets-rate-ht {
               type uint64;
               description
                 "RED drop rate for high-loss, TCP packets";
             }
             leaf queue-counters-red-packets-low {
               type uint64;
               description
                 "Number of RED dropped low-loss packets";
             }
             leaf queue-counters-red-packets-rate-low {
               type uint64;
               description
                 "RED drop rate for low-loss packets";
             }
             leaf queue-counters-red-packets-medium-low {
               type uint64;
               description
                 "Number of RED dropped medium-low-loss packets";
             }
             leaf queue-counters-red-packets-rate-medium-low {
               type uint64;
               description
                 "RED drop rate for medium-low-loss packets";
             }
             leaf queue-counters-red-packets-medium-high {
               type uint64;
               description
                 "Number of RED dropped medium-high-loss packets";
             }
             leaf queue-counters-red-packets-rate-medium-high {
               type uint64;
               description
                 "RED drop rate for medium-high-loss packets";
             }
             leaf queue-counters-red-packets-medium {
               type uint64;
               description
                 "Number of RED dropped medium-loss packets";
             }
             leaf queue-counters-red-packets-rate-medium {
               type uint64;
               description
                 "RED drop rate for medium-loss packets";
             }
             leaf queue-counters-red-packets-high {
               type uint64;
               description
                 "Number of RED dropped high-loss packets";
             }
             leaf queue-counters-red-packets-rate-high {
               type uint64;
               description
                 "RED drop rate for high-loss packets";
             }
             leaf queue-counters-red-bytes-na {
               type string;
               description
                 "Number of bytes dropped due to RED not available";
             }
             leaf queue-counters-red-bytes {
               type uint64;
               description
                 "Number of bytes dropped due to RED";
             }
             leaf queue-counters-red-bytes-rate {
               type uint64;
               description
                 "Rate at which bytes are dropped due to RED";
             }
             leaf queue-counters-red-bytes-ln {
               type uint64;
               description
                 "Number of RED dropped low-loss, non-TCP bytes";
             }
             leaf queue-counters-red-bytes-rate-ln {
               type uint64;
               description
                 "RED drop rate for low-loss, non-TCP bytes";
             }
             leaf queue-counters-red-bytes-lt {
               type uint64;
               description
                 "Number of RED dropped low-loss, TCP bytes";
             }
             leaf queue-counters-red-bytes-rate-lt {
               type uint64;
               description
                 "RED drop rate for low-loss, TCP bytes";
             }
             leaf queue-counters-red-bytes-hn {
               type uint64;
               description
                 "Number of RED dropped high-loss, non-TCP bytes";
             }
             leaf queue-counters-red-bytes-rate-hn {
               type uint64;
               description
                 "RED drop rate for high-loss, non-TCP bytes";
             }
             leaf queue-counters-red-bytes-ht {
               type uint64;
               description
                 "Number of RED dropped high-loss, TCP bytes";
             }
             leaf queue-counters-red-bytes-rate-ht {
               type uint64;
               description
                 "RED drop rate for high-loss, TCP bytes";
             }
             leaf queue-counters-red-bytes-low {
               type uint64;
               description
                 "Number of RED dropped low-loss bytes";
             }
             leaf queue-counters-red-bytes-rate-low {
               type uint64;
               description
                 "RED drop rate for low-loss bytes";
             }
             leaf queue-counters-red-bytes-medium-low {
               type uint64;
               description
                 "Number of RED dropped medium-low-loss bytes";
             }
             leaf queue-counters-red-bytes-rate-medium-low {
               type uint64;
               description
                 "RED drop rate for medium-low-loss bytes";
             }
             leaf queue-counters-red-bytes-medium-high {
               type uint64;
               description
                 "Number of RED dropped medium-high-loss bytes";
             }
             leaf queue-counters-red-bytes-rate-medium-high {
               type uint64;
               description
                 "RED drop rate for medium-high-loss bytes";
             }
             leaf queue-counters-red-bytes-medium {
               type uint64;
               description
                 "Number of RED dropped medium-loss bytes";
             }
             leaf queue-counters-red-bytes-rate-medium {
               type uint64;
               description
                 "RED drop rate for medium-loss bytes";
             }
             leaf queue-counters-red-bytes-high {
               type uint64;
               description
                 "Number of RED dropped high-loss bytes";
             }
             leaf queue-counters-red-bytes-rate-high {
               type uint64;
               description
                 "RED drop rate for high-loss bytes";
             }
             leaf queue-counters-timestamp {
               type uint64;
               description
                 "Last packet enqueued timestamp";
             }
             leaf queue-counters-total-drop-packets-rate {
               type uint64;
               description
                 "Number of total packets dropped at the queue";
             }
             leaf queue-counters-total-drop-bytes {
               type uint64;
               description
                 "Number of total packets dropped at the queue";
             }
             leaf queue-counters-total-drop-bytes-rate {
               type uint64;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-short-summary {
             description
               "Summary of queue information on an interface";
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
         }
         container voq-counters {
           description
             "VOQ counter statistics";
           leaf voq-counters-error-message {
             type string;
             description
               "VOQ statistics not available for this interface";
           }
           container voq {
             description
               "Counters for a single voq";
             container fpc {
               description
                 "Counters for a single FPC";
               leaf fpc-no {
                 type int32;
                 description
                   "FPC number";
               }
               container pfe {
                 description
                   "Counters for a single PFE";
                 leaf-list pfe-no {
                   type int32;
                   description
                     "PFE number";
                 }
                 leaf voq-counters-tail-drop-packets {
                   type int32;
                   description
                     "Tail DROP packet count";
                 }
                 leaf voq-counters-tail-drop-packets-rate {
                   type int32;
                   description
                     "Rate at which tail packets are dropped";
                 }
                 leaf voq-counters-tail-drop-bytes {
                   type int32;
                   description
                     "Tail DROP bytes count";
                 }
                 leaf voq-counters-tail-drop-bytes-rate {
                   type int32;
                   description
                     "Rate at which tail bytes are dropped";
                 }
                 leaf voq-counters-drop-packets {
                   type int32;
                   description
                     "DROP packet count";
                 }
                 leaf voq-counters-drop-packets-rate {
                   type int32;
                   description
                     "Rate at which packets are dropped";
                 }
                 leaf voq-counters-drop-bytes {
                   type int32;
                   description
                     "DROP bytes count";
                 }
                 leaf voq-counters-drop-bytes-rate {
                   type int32;
                   description
                     "Rate at which bytes are dropped";
                 }
               }
             }
             leaf queue-number {
               type int32;
               description
                 "Queue number";
             }
             leaf forwarding-class-name {
               type string;
               description
                 "Forwarding class name associated with queue";
             }
           }
         }
         container smart-sfp-av-titan-statistics {
           description
             "AimValley Smart SFP statistics";
           leaf smart-sfp-av-titan-error-message {
             type string;
             description
               "AV Smart SFP un-available";
           }
           container smart-sfp-av-titan-eth-port-statistics {
             leaf rx-crct-frames {
               type uint32;
             }
             leaf rx-crct-bytes {
               type uint32;
             }
             leaf rx-fragments {
               type uint32;
             }
             leaf rx-crct-unicast-frames {
               type uint32;
             }
             leaf rx-crct-multicast-frames {
               type uint32;
             }
             leaf rx-crct-broadcast-frames {
               type uint32;
             }
             leaf rx-err-fcs-frames {
               type uint32;
             }
             leaf rx-len-err-frames {
               type uint32;
             }
             leaf rx-undersize-frames {
               type uint32;
             }
             leaf rx-oversize-frames {
               type uint32;
             }
             leaf rx-inv-vlan-mismatch-frames {
               type uint32;
             }
             leaf rx-discarded-frames {
               type uint32;
             }
             leaf rx-dropped-q-overflow-frames {
               type uint32;
             }
             leaf tx-frames {
               type uint32;
             }
             leaf tx-bytes {
               type uint32;
             }
             leaf tx-unicast-frames {
               type uint32;
             }
             leaf tx-multicast-frames {
               type uint32;
             }
             leaf tx-broadcast-frames {
               type uint32;
             }
           }
           container smart-sfp-av-titan-iwf-statistics {
             leaf rx-packets {
               type uint32;
             }
             leaf tx-packets {
               type uint32;
             }
             leaf malformed-packets {
               type uint32;
             }
             leaf reordered-packets {
               type uint32;
             }
             leaf misordered-dropped-packets {
               type uint32;
             }
             leaf missing-packets {
               type uint32;
             }
             leaf played-out-packets {
               type uint32;
             }
             leaf jb-overrun {
               type uint32;
             }
             leaf jb-underrun {
               type uint32;
             }
           }
           container smart-sfp-av-titan-ds3-statistics {
             leaf rx-bpvexzerrors {
               type uint32;
             }
             leaf rx-cvperrors {
               type uint32;
             }
             leaf b3-errors {
               type uint32;
             }
           }
           container smart-sfp-av-titan-stm-statistics {
             leaf rx-b1-errors {
               type uint32;
             }
             leaf tx-b1-errors {
               type uint32;
             }
           }
         }
         container smart-sfp-av-titan-defects {
           description
             "AimValley Smart SFP defects";
           container smart-sfp-av-titan-defect-list {
             leaf sfp-tdm-defects {
               type string;
             }
             leaf sfp-system-defects {
               type string;
             }
           }
         }
         container forwarding-class-counters {
           description
             "Forwarding-class counter statistics";
           leaf forwarding-class-counters-error-message {
             type string;
             description
               "Forwarding-class statistics not available for this interface";
           }
           container ipv4-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container ipv6-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container mpls-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container layer2-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container other-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container protocol-aggregate-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container forwarding-class-statistics {
             container protocol-aggregate-forwarding-class-counters {
             }
             container ipv4-forwarding-class-counters {
             }
             container ipv6-forwarding-class-counters {
             }
             container mpls-forwarding-class-counters {
             }
             container layer2-forwarding-class-counters {
             }
             container other-forwarding-class-counters {
             }
           }
           container forwarding-class-accounting-parameters {
             leaf forwarding-class-accounting-for-protocol {
               type string;
             }
             leaf forwarding-class-accounting-for-traffic-direction {
               type string;
             }
             leaf forwarding-class-accounting-for-traffic-type {
               type string;
             }
             leaf forwarding-class-accounting-overhead-bytes {
               type uint32;
             }
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container keepalive-statistics {
           description
             "Keepalive statistics for this interface";
           leaf keepalive-lmi-descriptor {
             type string;
           }
           leaf keepalive-input-count {
             type int32;
           }
           leaf keepalive-input-time {
             type string;
           }
           leaf keepalive-output-count {
             type int32;
           }
           leaf keepalive-output-time {
             type string;
           }
         }
         container optics-bit-rate {
           leaf bit-rate {
             type string;
             description
               " Optics Bit Rate";
           }
         }
         container optics-fec-statistics {
           leaf fec-corrected-errors {
             type int32;
           }
           leaf fec-valid-time {
             type int32;
           }
           leaf fec-corrected-error-ratio {
             type int32;
           }
           leaf fec-uncorrected-words {
             type int32;
           }
         }
         container traffic-statistics {
           leaf input-bps {
             type int32;
           }
           leaf input-pps {
             type int32;
           }
           leaf output-bps {
             type int32;
           }
           leaf output-pps {
             type int32;
           }
           leaf input-packets {
             type int32;
           }
           leaf output-packets {
             type int32;
           }
           leaf input-bytes {
             type int32;
           }
           leaf output-bytes {
             type int32;
           }
           container ipv6-transit-statistics {
             leaf input-bytes {
               type int32;
             }
             leaf output-bytes {
               type int32;
             }
             leaf input-packets {
               type int32;
             }
             leaf output-packets {
               type int32;
             }
           }
           container ipv6-total-statistics {
             leaf input-bytes {
               type int32;
             }
             leaf output-bytes {
               type int32;
             }
             leaf input-packets {
               type int32;
             }
             leaf output-packets {
               type int32;
             }
           }
         }
         container multicast-statistics {
           description
             "Multicast statistics for interface";
           leaf multicast-statistics-header {
             type empty;
           }
           container ipv4-multicast-statistics {
             description
               "IPV4 multicast statistics for interface";
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
           container ipv6-multicast-statistics {
             description
               "IPV6 multicast statistics for interface";
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
         }
         container ingress-traffic-statistics {
           description
             "Traffic statistics at ingress before entering Packet 
             Forwarding Engine";
           leaf input-bps {
             type int32;
           }
           leaf input-pps {
             type int32;
           }
           leaf input-drop-bps {
             type int32;
             description
               "Drop rate at ingress in bits per second ";
           }
           leaf input-drop-pps {
             type int32;
             description
               "Drop rate at ingress in packets per second ";
           }
           leaf input-bytes {
             type int32;
           }
           leaf input-packets {
             type int32;
           }
           leaf input-drop-bytes {
             type int32;
             description
               "Drop statistics at ingress in bytes";
           }
           leaf input-drop-packets {
             type int32;
             description
               "Drop statistics at ingress in packets";
           }
         }
         container active-alarms {
         }
         container active-defects {
         }
         container media-state-information {
         }
         container sonet-errors {
           list media-alarm {
             leaf media-alarm-name {
               type string;
             }
             leaf media-alarm-count {
               type int32;
             }
           }
         }
         container sonet-physical-information {
           list media-alarm {
             leaf media-alarm-name {
               type string;
             }
             leaf media-alarm-seconds {
               type int32;
             }
             leaf media-alarm-count {
               type int32;
             }
             leaf media-alarm-state {
               type string;
             }
           }
         }
         container sonet-section-information {
           list media-alarm {
             leaf media-alarm-name {
               type string;
             }
             leaf media-alarm-seconds {
               type int32;
             }
             leaf media-alarm-count {
               type int32;
             }
             leaf media-alarm-state {
               type string;
             }
           }
         }
         container sonet-line-information {
           list media-alarm {
             leaf media-alarm-name {
               type string;
             }
             leaf media-alarm-seconds {
               type int32;
             }
             leaf media-alarm-count {
               type int32;
             }
             leaf media-alarm-state {
               type string;
             }
           }
         }
         container sonet-path-information {
           list media-alarm {
             leaf media-alarm-name {
               type string;
             }
             leaf media-alarm-seconds {
               type int32;
             }
             leaf media-alarm-count {
               type int32;
             }
             leaf media-alarm-state {
               type string;
             }
           }
         }
         container sonet-vt-information {
           list media-alarm {
             leaf media-alarm-name {
               type string;
             }
             leaf media-alarm-seconds {
               type int32;
             }
             leaf media-alarm-count {
               type int32;
             }
             leaf media-alarm-state {
               type string;
             }
           }
         }
         container otn-errors {
           list media-alarm {
             leaf media-alarm-name {
               type string;
             }
             leaf media-alarm-count {
               type int32;
             }
           }
         }
         container otn-fec-statistics {
           leaf fec-corrected-errors {
             type int32;
           }
           leaf fec-valid-time {
             type int32;
           }
           leaf fec-corrected-error-ratio {
             type int32;
           }
           leaf fec-uncorrected-words {
             type int32;
           }
         }
         container otn-fec-alarms {
           description
             "OTN degraded and excessive FEC error rates";
           list media-alarm {
             leaf media-alarm-name {
               type string;
             }
             leaf media-alarm-seconds {
               type int32;
             }
             leaf media-alarm-count {
               type int32;
             }
             leaf media-alarm-state {
               type string;
             }
           }
         }
         container otn-fec-mode {
           leaf fec-mode {
             type string;
             description
               "Optics FEC mode";
           }
         }
         container otn-otn-mode {
           leaf otn-mode {
             type string;
           }
         }
         container otn-otn-rate {
           leaf otn-rate {
             type string;
           }
         }
         container otn-otn-loopback {
           leaf otn-loopback {
             type string;
           }
         }
         container otn-local-loopback {
           leaf local-loopback {
             type string;
           }
         }
         container otn-payload-prbs {
           leaf payload-prbs {
             type string;
           }
         }
         container otn-laser-enable {
           leaf laser-enable {
             type string;
             description
               "Optics laser status";
           }
         }
         container media-information {
           description
             "Information about media alarms";
           leaf media-type {
             type string;
             description
               "Type of media this information is for";
           }
           list media-alarm {
             leaf media-alarm-name {
               type string;
             }
             leaf media-alarm-count {
               type int32;
             }
             leaf media-alarm-seconds {
               type int32;
             }
             leaf media-alarm-state {
               type string;
             }
             leaf ce-counter-name {
               type string;
               description
                 "Circuit Emulation counter information";
             }
             leaf ce-counter-packets {
               type int32;
               description
                 "Circuit Emulation number of packets";
             }
             leaf ce-counter-bytes {
               type int32;
               description
                 "Circuit Emulation number of bytes";
             }
             leaf ce-counter-count {
               type int32;
               description
                 "Circuit Emulation number of event occurrences";
             }
           }
           leaf ds1-timeslots {
             type string;
           }
           leaf ds1-line-encoding {
             type string;
           }
           leaf ds1-byte-encoding {
             type string;
           }
           leaf ds1-data-inversion {
             type string;
           }
           leaf idle-cycle-flag {
             type string;
           }
           leaf start-end-flag {
             type string;
           }
           leaf ds0-byte-encoding {
             type string;
           }
           leaf ds0-data-inversion {
             type string;
           }
           leaf e3-data-inversion {
             type string;
           }
           leaf ds1-buildout {
             type string;
             description
               "Number of feet";
           }
         }
         container ethernet-pcs-statistics {
           description
             "Ethernet PCS statistics";
           leaf bit-error-seconds {
             type int32;
             description
               "Bit error duration";
           }
           leaf errored-blocks-seconds {
             type int32;
             description
               "Errored blocks duration";
           }
         }
         container ethernet-fec-mode {
           description
             "Ethernet FEC Mode";
           leaf enabled_fec_mode {
             type string;
             description
               "Enabled FEC mode: <NONE/FEC74/FEC91/FEC108>";
           }
         }
         container ethernet-fec-statistics {
           description
             "Ethernet FEC statistics";
           leaf fec_ccw_count {
             type int32;
             description
               "FEC Corrected Error Count";
           }
           leaf fec_nccw_count {
             type int32;
             description
               "FEC Uncorrected Error Count";
           }
           leaf fec_ccw_error_rate {
             type int32;
             description
               "FEC Corrected Error Rate (errors/sec)";
           }
           leaf fec_nccw_error_rate {
             type int32;
             description
               "FEC Uncorrected Error Rate (errors/sec)";
           }
         }
         container ctle {
           description
             "Ctle ";
           leaf ctle_value {
             type int32;
             description
               "Ctle value";
           }
         }
         container pre-emphasis {
           description
             "Pre-emphasis ";
           leaf pre_emphasis_value {
             type int32;
             description
               "Pre-emphasis value";
           }
         }
         container differential-amplitude {
           description
             "Differential-amplitude ";
           leaf differential_amplitude_value {
             type int32;
             description
               "Differential-amplitude value";
           }
         }
         container ethernet-mac-statistics {
           description
             "Ethernet MAC statistics";
           leaf input-bytes {
             type int32;
           }
           leaf input-packets {
             type int32;
           }
           leaf output-bytes {
             type int32;
           }
           leaf output-packets {
             type int32;
           }
           leaf input-undersized-frames {
             type int32;
           }
           leaf input-unicasts {
             type int32;
           }
           leaf output-unicasts {
             type int32;
           }
           leaf input-broadcasts {
             type int32;
           }
           leaf output-broadcasts {
             type int32;
           }
           leaf input-multicasts {
             type int32;
           }
           leaf output-multicasts {
             type int32;
           }
           leaf input-crc-errors {
             type int32;
           }
           leaf output-crc-errors {
             type int32;
           }
           leaf input-fifo-errors {
             type int32;
           }
           leaf output-fifo-errors {
             type int32;
           }
           leaf input-dma-errors {
             type int32;
           }
           leaf output-dma-errors {
             type int32;
           }
           leaf input-mac-control-frames {
             type int32;
           }
           leaf output-mac-control-frames {
             type int32;
           }
           leaf input-mac-pause-frames {
             type int32;
           }
           leaf output-mac-pause-frames {
             type int32;
           }
           leaf input-oversized-frames {
             type int32;
           }
           leaf input-jabber-frames {
             type int32;
           }
           leaf input-fragment-frames {
             type int32;
           }
           leaf input-vlan-tagged-frames {
             type int32;
           }
           leaf input-code-violations {
             type int32;
           }
           leaf input-total-errors {
             type int32;
           }
           leaf output-total-errors {
             type int32;
           }
           leaf input-policer-frame-drops {
             type int32;
           }
           leaf input-policer-byte-drops {
             type int32;
           }
         }
         container ethernet-prbs-mode {
           description
             "PRBS Mode";
           leaf prbs-mode {
             type string;
             description
               "PRBS Mode: <Enabled/Disabled>";
           }
         }
         container ethernet-prbs-statistics {
           description
             "Ethernet PRBS statistics";
           leaf prbs-lane {
             type int32;
             description
               "PRBS Lane";
           }
           leaf prbs-state {
             type string;
             description
               "PRBS State";
           }
           leaf prbs-error-count {
             type int32;
             description
               "PRBS Error Count";
           }
         }
         container smart-sfp-configurable-type {
           leaf smart-sfp-tdm-management {
             type string;
           }
         }
         container smart-sfp-type {
           leaf smart-sfp-module-type {
             type string;
           }
           leaf smart-sfp-present {
             type string;
           }
         }
         container smart-sfp-config {
           leaf tdm-loopback {
             type string;
           }
           leaf dmac-check-enable {
             type string;
           }
           leaf encap-ecid {
             type int32;
           }
           leaf decap-ecid {
             type int32;
           }
           leaf vlan-id-1 {
             type int32;
           }
           leaf vlan-id-2 {
             type int32;
           }
           leaf mode {
             type string;
           }
           leaf chan-dmac {
             type jt:mac-addr;
           }
         }
         container smart-sfp-oc3-statistics {
           leaf fcs-error-count {
             type uint32;
           }
           leaf sec-sefs {
             type uint32;
           }
           leaf sec-es {
             type uint32;
           }
           leaf sec-es-min15 {
             type uint32;
           }
           leaf sec-ses {
             type uint32;
           }
           leaf sec-ses-min15 {
             type uint32;
           }
           leaf sec-cv {
             type uint32;
           }
           leaf sec-cv-min15 {
             type uint32;
           }
           leaf line-es {
             type uint32;
           }
           leaf line-es-min15 {
             type uint32;
           }
           leaf line-ses {
             type uint32;
           }
           leaf line-ses-min15 {
             type uint32;
           }
           leaf line-cv {
             type uint32;
           }
           leaf line-cv-min15 {
             type uint32;
           }
           leaf line-uas {
             type uint32;
           }
           leaf line-uas-min15 {
             type uint32;
           }
           leaf path-es {
             type uint32;
           }
           leaf path-es-min15 {
             type uint32;
           }
           leaf path-ses {
             type uint32;
           }
           leaf path-ses-min15 {
             type uint32;
           }
           leaf path-cv {
             type uint32;
           }
           leaf path-cv-min15 {
             type uint32;
           }
           leaf path-uas {
             type uint32;
           }
           leaf path-uas-min15 {
             type uint32;
           }
         }
         container smart-sfp-e1t1-statistics {
           leaf e1t1-es {
             type uint32;
           }
           leaf e1t1-es-min15 {
             type uint32;
           }
           leaf e1t1-ses {
             type uint32;
           }
           leaf e1t1-ses-min15 {
             type uint32;
           }
           leaf e1t1-uas {
             type uint32;
           }
           leaf e1t1-uas-min15 {
             type uint32;
           }
           leaf e1t1-bes {
             type uint32;
           }
           leaf e1t1-bes-min15 {
             type uint32;
           }
           leaf e1t1-les {
             type uint32;
           }
           leaf e1t1-les-min15 {
             type uint32;
           }
           leaf e1t1-pes {
             type uint32;
           }
           leaf e1t1-pes-min15 {
             type uint32;
           }
           leaf e1t1-psess {
             type uint32;
           }
           leaf e1t1-psess-min15 {
             type uint32;
           }
           leaf e1t1-ces {
             type uint32;
           }
           leaf e1t1-ces-min15 {
             type uint32;
           }
           leaf e1t1-cses {
             type uint32;
           }
           leaf e1t1-cses-min15 {
             type uint32;
           }
           leaf e1t1-sefs {
             type uint32;
           }
           leaf e1t1-sefs-min15 {
             type uint32;
           }
         }
         container smart-sfp-e3t3-statistics {
           leaf e3t3-les {
             type uint32;
           }
           leaf e3t3-les-min15 {
             type uint32;
           }
           leaf e3t3-pes {
             type uint32;
           }
           leaf e3t3-pes-min15 {
             type uint32;
           }
           leaf e3t3-psess {
             type uint32;
           }
           leaf e3t3-psess-min15 {
             type uint32;
           }
           leaf e3t3-ces {
             type uint32;
           }
           leaf e3t3-ces-min15 {
             type uint32;
           }
           leaf e3t3-cses {
             type uint32;
           }
           leaf e3t3-cses-min15 {
             type uint32;
           }
           leaf e3t3-sefs {
             type uint32;
           }
           leaf e3t3-sefs-min15 {
             type uint32;
           }
           leaf e3t3-uas {
             type uint32;
           }
           leaf e3t3-uas-min15 {
             type uint32;
           }
         }
         container fibrechannel-port-flow-control {
           description
             "Fibre Channel interface flow control";
           leaf fibrechannel-port-flow-control-mode {
             type string;
           }
           list fibrechannel-port-flow-control-credits {
             description
               "Generic flow control credits";
             leaf fibrechannel-port-flow-control-credits-subject {
               type string;
             }
             leaf fibrechannel-port-flow-control-credits-assigned {
               type uint64;
             }
             leaf fibrechannel-port-flow-control-credits-available {
               type uint64;
             }
           }
         }
         container fibrechannel-mac-statistics {
           description
             "Fibre Channel MAC statistics";
           container fibrechannel-mac-statistics-generic {
             leaf link-failures {
               type uint64;
             }
             leaf loss-of-sync {
               type uint64;
             }
             leaf loss-of-signal {
               type uint64;
             }
             leaf sw-link-resets {
               type uint64;
             }
             leaf buffer-to-buffer-credit-recovery-lost-frames {
               type uint64;
             }
             leaf buffer-to-buffer-credit-recovery-lost-rrdys {
               type uint64;
             }
           }
           container fibrechannel-mac-statistics-received {
             leaf rx-class-2-frames {
               type uint64;
             }
             leaf rx-class-2-octets {
               type uint64;
             }
             leaf rx-class-3-frames {
               type uint64;
             }
             leaf rx-class-3-octets {
               type uint64;
             }
             leaf rx-class-f-frames {
               type uint64;
             }
             leaf rx-class-f-octets {
               type uint64;
             }
             leaf class-2-discards {
               type uint64;
             }
             leaf class-3-discards {
               type uint64;
             }
             leaf class-f-discards {
               type uint64;
             }
             leaf rx-frames-too-long {
               type uint64;
             }
             leaf rx-frames-too-short {
               type uint64;
             }
             leaf rx-missing-eof {
               type uint64;
             }
             leaf rx-invalid-crcs {
               type uint64;
             }
             leaf rx-link-resets {
               type uint64;
             }
             leaf rx-link-reset-responses {
               type uint64;
             }
             leaf rx-offlines {
               type uint64;
             }
             leaf rx-not-operationals {
               type uint64;
             }
             leaf rx-invalid-tx-words {
               type uint64;
             }
             leaf rx-encoding-disparity-errors {
               type uint64;
             }
             leaf rx-delimiter-errors {
               type uint64;
             }
             leaf rx-input-buffers-full {
               type uint64;
             }
             leaf rx-invalid-ordered-sets {
               type uint64;
             }
             leaf rx-prim-seq-protocol-errors {
               type uint64;
             }
             leaf rx-other-errors {
               type uint64;
             }
           }
           container fibrechannel-mac-statistics-transmitted {
             leaf tx-class-2-frames {
               type uint64;
             }
             leaf tx-class-2-octets {
               type uint64;
             }
             leaf tx-class-3-frames {
               type uint64;
             }
             leaf tx-class-3-octets {
               type uint64;
             }
             leaf tx-class-f-frames {
               type uint64;
             }
             leaf tx-class-f-octets {
               type uint64;
             }
             leaf tx-link-resets {
               type uint64;
             }
             leaf tx-link-reset-responses {
               type uint64;
             }
             leaf tx-offlines {
               type uint64;
             }
             leaf tx-not-operationals {
               type uint64;
             }
             leaf tx-bb-credit-zeroes {
               type uint64;
             }
             leaf tx-other-errors {
               type uint64;
             }
           }
         }
         container ethernet-filter-statistics {
           description
             "Ethernet filter statistics";
           leaf input-reject-count {
             type int32;
           }
           leaf output-packet-pad-count {
             type int32;
           }
           leaf output-packet-error-count {
             type int32;
           }
           leaf input-packets {
             type int32;
           }
           leaf input-reject-destination-address-count {
             type int32;
           }
           leaf input-reject-source-address-count {
             type int32;
           }
           leaf output-packets {
             type int32;
           }
           leaf cam-destination-filter-count {
             type int32;
           }
           leaf cam-source-filter-count {
             type int32;
           }
         }
         container ethernet-autonegotiation {
           description
             "Ethernet autonegotiation information";
         }
         container mac-database {
         }
         container dsl-information {
           description
             "Operational information and statistics for ADSL interfaces";
           container dsl-statistics {
             leaf interleaved-rx-cells {
               type int32;
               description
                 "Interleaved receiver cells";
             }
             leaf fast-rx-cells {
               type int32;
               description
                 "Fast receiver cells";
             }
             leaf interleaved-tx-cells {
               type int32;
               description
                 "Interleaved transmitter cells";
             }
             leaf fast-tx-cells {
               type int32;
               description
                 "Fast transmitter cells";
             }
           }
         }
         container vdsl-information {
           description
             "Operational information and statistics for VDSL interfaces";
         }
         container shdsl-information {
           description
             "Operational information and statistics for SHDSL interfaces";
         }
         container efm-information {
           description
             "Operational information and statistics for EFM interfaces";
           container efm-line-statistics {
             container active-alarms-efm {
             }
             container active-defects-efm {
             }
             container media-information {
               description
                 "Information about media alarms";
               leaf media-type {
                 type string;
                 description
                   "Type of media this information is for";
               }
               list media-alarm {
                 leaf media-alarm-name {
                   type string;
                 }
                 leaf media-alarm-count {
                   type int32;
                 }
                 leaf media-alarm-seconds {
                   type int32;
                 }
                 leaf media-alarm-state {
                   type string;
                 }
                 leaf ce-counter-name {
                   type string;
                   description
                     "Circuit Emulation counter information";
                 }
                 leaf ce-counter-packets {
                   type int32;
                   description
                     "Circuit Emulation number of packets";
                 }
                 leaf ce-counter-bytes {
                   type int32;
                   description
                     "Circuit Emulation number of bytes";
                 }
                 leaf ce-counter-count {
                   type int32;
                   description
                     "Circuit Emulation number of event occurrences";
                 }
               }
               leaf ds1-timeslots {
                 type string;
               }
               leaf ds1-line-encoding {
                 type string;
               }
               leaf ds1-byte-encoding {
                 type string;
               }
               leaf ds1-data-inversion {
                 type string;
               }
               leaf idle-cycle-flag {
                 type string;
               }
               leaf start-end-flag {
                 type string;
               }
               leaf ds0-byte-encoding {
                 type string;
               }
               leaf ds0-data-inversion {
                 type string;
               }
               leaf e3-data-inversion {
                 type string;
               }
               leaf ds1-buildout {
                 type string;
                 description
                   "Number of feet";
               }
             }
             container shdsl-information {
               description
                 "Operational information and statistics for SHDSL 
                 interfaces";
             }
           }
         }
         container atm-information {
           description
             "Operational information and statistics for ATM interfaces";
           container plcp-defects {
           }
           container atm-defects {
           }
         }
         container serial-information {
           description
             "Serial interfaces information and statistics";
           leaf dce-loopback-override {
             type string;
           }
           container eia530-control-signal {
           }
         }
         container virtual-path-information {
           description
             "Operational information and statistics for a virtual path";
           leaf cdvt {
             type int32;
           }
           container traffic-statistics {
             leaf input-bps {
               type int32;
             }
             leaf input-pps {
               type int32;
             }
             leaf output-bps {
               type int32;
             }
             leaf output-pps {
               type int32;
             }
             leaf input-packets {
               type int32;
             }
             leaf output-packets {
               type int32;
             }
             leaf input-bytes {
               type int32;
             }
             leaf output-bytes {
               type int32;
             }
             container ipv6-transit-statistics {
               leaf input-bytes {
                 type int32;
               }
               leaf output-bytes {
                 type int32;
               }
               leaf input-packets {
                 type int32;
               }
               leaf output-packets {
                 type int32;
               }
             }
             container ipv6-total-statistics {
               leaf input-bytes {
                 type int32;
               }
               leaf output-bytes {
                 type int32;
               }
               leaf input-packets {
                 type int32;
               }
               leaf output-packets {
                 type int32;
               }
             }
           }
         }
         container ct3-information {
           list interface-tx-queue {
             leaf output-drops-bytes {
               type int32;
             }
           }
         }
         container cds1-information {
           list interface-tx-queue {
             leaf output-drops-bytes {
               type int32;
             }
           }
         }
         container nxds0-information {
           list interface-tx-queue {
             leaf output-drops-bytes {
               type int32;
             }
           }
         }
         list logical-interface {
           key "name";
           description
             "Information about a single logical interface";
           leaf name {
             type string;
             description
               "Name of this item";
           }
           leaf admin-status {
             type string;
             description
               "Desired state of the interface";
           }
           leaf oper-status {
             type string;
             description
               "Current operational state of the interface";
           }
           leaf vrfname {
             type string;
             description
               "Routing instance name";
           }
           leaf zonename {
             type string;
             description
               "Zone name";
           }
           leaf subunit {
             type int32;
             description
               "Subunit for this interface";
           }
           leaf dialer-time-to-disconnect {
             type string;
             description
               "Time for dialer to disconnect due to idle timeout";
           }
           leaf lcp-state {
             type string;
             description
               "State of the Line Control Protocol";
           }
           leaf chap-state {
             type string;
             description
               "State of the Challenge Handshake Authentication Protocol";
           }
           leaf pap-state {
             type string;
             description
               "State of the Password Authentication Protocol";
           }
           container pppoe-information {
             description
               "PPPoE information";
             list pppoe-interface {
               leaf state {
                 type string;
                 description
                   "State";
               }
               leaf session-id {
                 type string;
                 description
                   "Session ID";
               }
               leaf ac-name-session {
                 type string;
                 description
                   "Session AC name";
               }
               leaf remote-mac {
                 type string;
                 description
                   "Remote MAC address";
               }
               leaf ac-name-config {
                 type string;
                 description
                   "Configured AC name";
               }
               leaf service-name {
                 type string;
                 description
                   "Service name";
               }
               leaf auto-reconnect {
                 type string;
                 description
                   "Autoreconnect timeout";
               }
               leaf idle-timeout {
                 type string;
                 description
                   "Idle timeout";
               }
               leaf underlying-interface-name {
                 type string;
                 description
                   "Underlying interface name";
               }
               leaf underlying-interface-index {
                 type string;
                 description
                   "Underlying interface index";
               }
               leaf padg-credits {
                 type int32;
                 description
                   "PADG transmit credits";
               }
               leaf pppoe-credit-scale-factor {
                 type string;
                 description
                   "Scaling factor";
               }
               leaf ignore-eol-tag {
                 type string;
                 description
                   "Ignore End-of-List TAG";
               }
               leaf ppp-max-payload-tag {
                 type int32;
                 description
                   "PPP-Max-Payload TAG";
               }
               leaf interface-name {
                 type string;
                 description
                   "Class-of-service interface name";
               }
               leaf interface-index {
                 type uint32;
                 description
                   "Class-of-service interface index";
               }
               leaf aci-iflset-name {
                 type string;
                 description
                   "ACI Interface Set name";
               }
               leaf aci-iflset-index {
                 type string;
                 description
                   "ACI Interface Set index";
               }
               leaf ifl-type {
                 type string;
                 description
                   "Type";
               }
               leaf session-uptime {
                 type string;
                 description
                   "Duration for which the session has been up";
               }
               leaf dynamic-profile {
                 type string;
                 description
                   "Dynamic Profile name";
               }
               leaf pppoe-credits {
                 type string;
                 description
                   "Forwarding credit balances";
               }
               leaf dynamic-interface-bandwidth {
                 type string;
                 description
                   "Dynamic interface bandwidth";
               }
               leaf agent-circuit-id {
                 type string;
                 description
                   "Agent Circuit ID";
               }
               leaf agent-remote-id {
                 type string;
                 description
                   "Agent Remote ID";
               }
               leaf padm-motm {
                 type string;
                 description
                   "PADM Message of the Moment tag";
               }
               leaf padm-hurl {
                 type string;
                 description
                   "PADM HTTP URL tag";
               }
             }
           }
           container pppoe-underlying-information {
             description
               "PPPoE Underlying information";
             list pppoe-underlying-interface {
               leaf dynamic-profile {
                 type string;
                 description
                   "Dynamic Profile name";
               }
               leaf service-name-table {
                 type string;
                 description
                   "Name of Service Name Table";
               }
               leaf max-sessions {
                 type int32;
                 description
                   "Maximum number of PPPoE sessions";
               }
               leaf max-sessions-vsa-ignore {
                 type string;
                 description
                   "Ignore max-sessions VSA";
               }
               leaf duplicate-protection {
                 type string;
                 description
                   "Duplicate protection mode";
               }
               leaf short-cycle-protection {
                 type string;
                 description
                   "Short cycle protection mode";
               }
               leaf direct-connect {
                 type string;
                 description
                   "Direct connect mode";
               }
               leaf ac-name {
                 type string;
                 description
                   "Access Concentrator name";
               }
               leaf underlying-interface-name {
                 type string;
                 description
                   "Underlying interface name";
               }
               leaf underlying-interface-index {
                 type string;
                 description
                   "Underlying interface index";
               }
               leaf encapsulation-type-identifier {
                 type string;
                 description
                   "Encapsulation type identifier";
               }
               leaf state {
                 type string;
                 description
                   "State";
               }
               leaf active-sessions {
                 type int32;
                 description
                   "Number of active PPPoE sessions";
               }
               leaf aci-autosensing {
                 type string;
                 description
                   "ACI VLAN Autosensing mode";
               }
               leaf line-identity-autosensing {
                 type string;
                 description
                   "Line Identity Autosensing mode";
               }
             }
           }
           container aci-vlan-information {
             leaf dynamic-profile {
               type string;
               description
                 "Dynamic Profile name";
             }
           }
           container line-identity-information {
             leaf dynamic-profile {
               type string;
               description
                 "Dynamic Profile name";
             }
             leaf circuit-id {
               type string;
               description
                 "Aci vlan attribute";
             }
             leaf remote-id {
               type string;
               description
                 "Aci vlan attribute";
             }
             leaf accept-no-ids {
               type string;
               description
                 "Aci vlan attribute";
             }
           }
           container demux-information {
             description
               "Demux information";
             container demux-interface {
               leaf demux-underlying-interface-name {
                 type string;
                 description
                   "Underlying interface name";
               }
               leaf demux-underlying-interface-index {
                 type string;
                 description
                   "Underlying interface index";
               }
               leaf demux-inet-prefix-type {
                 type string;
                 description
                   "Prefix type";
               }
               leaf demux-inet-prefix-count {
                 type string;
                 description
                   "IPv4 Prefix count";
               }
               leaf demux-inet-prefix {
                 type string;
                 description
                   "IPv4 Prefix";
               }
               leaf demux-inet6-prefix-type {
                 type string;
                 description
                   "Prefix type";
               }
               leaf demux-inet6-prefix-count {
                 type string;
                 description
                   "IPv6 Prefix count";
               }
               leaf demux-inet6-prefix {
                 type string;
                 description
                   "IPv6 Prefix";
               }
             }
           }
           container dual-ad-icl-color-information {
             container dual-ad-icl-color-info {
               description
                 "Dual-AD ICL Color Information";
               leaf dual-ad-icl-color-type {
                 type uint32;
                 description
                   "Dual-AD ICL Color Type";
               }
               leaf dual-ad-icl-color {
                 type uint32;
                 description
                   "Dual-AD ICL Color";
               }
             }
           }
           container dialer-information {
             description
               "Dialer information";
             leaf dialer-time-to-disconnect {
               type string;
               description
                 "Time for dialer to disconnect due to idle timeout";
             }
             container dialer-interface {
               leaf dialer-interface-name {
                 type string;
                 description
                   "Interface name";
               }
               leaf dialer-interface-state {
                 type string;
                 description
                   "Dialer interface state";
               }
               leaf pool-id {
                 type string;
                 description
                   "Pool identifier";
               }
               leaf primary-interface {
                 type string;
                 description
                   "Primary interface";
               }
               leaf activation-delay {
                 type string;
                 description
                   "Activation delay";
               }
               leaf deactivation-delay {
                 type string;
                 description
                   "Deactivation delay";
               }
               leaf activation-delay-elapsed {
                 type string;
                 description
                   "Activation delay elapsed";
               }
               leaf deactivation-delay-elapsed {
                 type string;
                 description
                   "Deactivation delay elapsed";
               }
               leaf call-idle-timeout {
                 type string;
                 description
                   "Call idle timeout";
               }
               leaf initial-route-check {
                 type string;
                 description
                   "Initial route check delay";
               }
               leaf redial-delay {
                 type string;
                 description
                   "Delay before dialer dials out again (seconds)";
               }
               leaf callback-wait-period {
                 type string;
                 description
                   "Delay before dialer attempts callback (seconds)";
               }
               leaf callback-wait-period-elapsed {
                 type string;
                 description
                   "Number of seconds in callback wait period that have 
                   elapsed";
               }
               leaf load-threshold {
                 type string;
                 description
                   "Load threshold that determines when interfaces are added
                   to bundle";
               }
               leaf load-interval {
                 type string;
                 description
                   "Interval over which average load is calculated";
               }
               container dialer-interface-flags {
                 description
                   "Flags indicating interface configuration";
                 leaf backup {
                   type empty;
                   description
                     "Dialer backup";
                 }
                 leaf multilink {
                   type empty;
                   description
                     "Dialer multilink";
                 }
                 leaf watchlist {
                   type empty;
                   description
                     "Dialer watchlist";
                 }
                 leaf interesting-detected {
                   type empty;
                   description
                     "Interesting packet detected";
                 }
               }
             }
           }
           container shared-interface-information {
             description
               "Shared interface information";
             container shared-interface-logical-interface {
               description
                 "Shared interface logical interface";
               leaf peer-interface-name {
                 type string;
                 description
                   "Peer interface name";
               }
               leaf interface-shared-with {
                 type string;
                 description
                   "Logical interface owner";
               }
               leaf rx-fe {
                 type string;
                 description
                   "Rx tunnel token forwarding element";
               }
               leaf rx-nhid {
                 type string;
                 description
                   "Rx tunnel token next hop index";
               }
               leaf tx-fe {
                 type string;
                 description
                   "Tx tunnel token forwarding element";
               }
               leaf tx-nhid {
                 type string;
                 description
                   "Tx tunnel token next hop index";
               }
             }
           }
           container mac-database {
           }
           container queue-counters {
             description
               "Queue counter statistics";
             leaf queue-counters-error-message {
               type string;
               description
                 "Queue statistics not available for this interface";
             }
             list queue {
               description
                 "Counters for a single queue";
               leaf queue-number {
                 type int32;
                 description
                   "Queue number";
               }
               leaf queue-counters-queued-packets {
                 type uint64;
                 description
                   "Queued packet count";
               }
               leaf queue-counters-trans-packets {
                 type uint64;
                 description
                   "Total number of transmitted packets";
               }
               leaf queue-counters-total-drop-packets {
                 type uint64;
                 description
                   "Number of total packets dropped at the queue";
               }
               leaf forwarding-class-name {
                 type string;
                 description
                   "Forwarding class name associated with queue";
               }
               leaf queue-counters-queued-packets-rate {
                 type uint64;
                 description
                   "Rate at which packets are queued";
               }
               leaf queue-counters-queued-bytes {
                 type uint64;
                 description
                   "Queued bytes count";
               }
               leaf queue-counters-queued-bytes-rate {
                 type uint64;
                 description
                   "Rate at which bytes are queued";
               }
               leaf queue-counters-queued-packets-na {
                 type string;
                 description
                   "Queued packets not available";
               }
               leaf queue-counters-queued-bytes-na {
                 type string;
                 description
                   "Queued bytes not available";
               }
               leaf queue-counters-trans-packets-rate {
                 type uint64;
                 description
                   "Rate at which packets are transmitted";
               }
               leaf queue-counters-trans-bytes {
                 type uint64;
                 description
                   "Total number of transmitted bytes";
               }
               leaf queue-counters-trans-bytes-rate {
                 type uint64;
                 description
                   "Rate at which bytes are transmitted";
               }
               leaf queue-counters-tail-drop-packets-na {
                 type string;
                 description
                   "Number of packets dropped due to tail drop not available";
               }
               leaf queue-counters-tail-drop-packets {
                 type uint64;
                 description
                   "Number of packets dropped at the tail of the queue";
               }
               leaf queue-counters-tail-drop-packets-rate {
                 type uint64;
                 description
                   "Rate at which packets are dropped at tail of queue";
               }
               leaf queue-counters-tail-drop-bytes {
                 type uint64;
                 description
                   "Number of packets dropped at tail drop of the queue";
               }
               leaf queue-counters-tail-drop-bytes-rate {
                 type uint64;
                 description
                   "Number of packets dropped at tail drop of the queue";
               }
               leaf queue-counters-rate-limit-drop-packets-na {
                 type string;
                 description
                   "Number of packets dropped due to rate-limit drop not 
                   available";
               }
               leaf queue-counters-rate-limit-drop-packets {
                 type uint64;
                 description
                   "Number of packets dropped by rate-limit for the queue";
               }
               leaf queue-counters-rate-limit-drop-packets-rate {
                 type uint64;
                 description
                   "Rate at which packets are dropped by rate-limit for the 
                   queue";
               }
               leaf queue-counters-rate-limit-drop-bytes-na {
                 type string;
                 description
                   "Number of bytes dropped due to tail drop not available";
               }
               leaf queue-counters-rate-limit-drop-bytes {
                 type uint64;
                 description
                   "Number of bytes dropped at the tail of the queue";
               }
               leaf queue-counters-rate-limit-drop-bytes-rate {
                 type uint64;
                 description
                   "Rate at which bytes are dropped at the tail of the queue";
               }
               leaf queue-counters-red-packets-na {
                 type string;
                 description
                   "Number of packets dropped due to RED not available";
               }
               leaf queue-counters-red-packets {
                 type uint64;
                 description
                   "Number of packets dropped due to RED";
               }
               leaf queue-counters-red-packets-rate {
                 type uint64;
                 description
                   "Rate at which packets are dropped due to RED";
               }
               leaf queue-counters-red-packets-ln {
                 type uint64;
                 description
                   "Number of RED dropped low-loss, non-TCP packets";
               }
               leaf queue-counters-red-packets-rate-ln {
                 type uint64;
                 description
                   "RED drop rate for low-loss, non-TCP packets";
               }
               leaf queue-counters-red-packets-lt {
                 type uint64;
                 description
                   "Number of RED dropped of low-loss, TCP packets";
               }
               leaf queue-counters-red-packets-rate-lt {
                 type uint64;
                 description
                   "RED drop rate for low-loss, TCP packets";
               }
               leaf queue-counters-red-packets-hn {
                 type uint64;
                 description
                   "Number of RED dropped high-loss, non-TCP packets";
               }
               leaf queue-counters-red-packets-rate-hn {
                 type uint64;
                 description
                   "RED drop rate for high-loss, non-TCP packets";
               }
               leaf queue-counters-red-packets-ht {
                 type uint64;
                 description
                   "Number of RED dropped high-loss, TCP packets";
               }
               leaf queue-counters-red-packets-rate-ht {
                 type uint64;
                 description
                   "RED drop rate for high-loss, TCP packets";
               }
               leaf queue-counters-red-packets-low {
                 type uint64;
                 description
                   "Number of RED dropped low-loss packets";
               }
               leaf queue-counters-red-packets-rate-low {
                 type uint64;
                 description
                   "RED drop rate for low-loss packets";
               }
               leaf queue-counters-red-packets-medium-low {
                 type uint64;
                 description
                   "Number of RED dropped medium-low-loss packets";
               }
               leaf queue-counters-red-packets-rate-medium-low {
                 type uint64;
                 description
                   "RED drop rate for medium-low-loss packets";
               }
               leaf queue-counters-red-packets-medium-high {
                 type uint64;
                 description
                   "Number of RED dropped medium-high-loss packets";
               }
               leaf queue-counters-red-packets-rate-medium-high {
                 type uint64;
                 description
                   "RED drop rate for medium-high-loss packets";
               }
               leaf queue-counters-red-packets-medium {
                 type uint64;
                 description
                   "Number of RED dropped medium-loss packets";
               }
               leaf queue-counters-red-packets-rate-medium {
                 type uint64;
                 description
                   "RED drop rate for medium-loss packets";
               }
               leaf queue-counters-red-packets-high {
                 type uint64;
                 description
                   "Number of RED dropped high-loss packets";
               }
               leaf queue-counters-red-packets-rate-high {
                 type uint64;
                 description
                   "RED drop rate for high-loss packets";
               }
               leaf queue-counters-red-bytes-na {
                 type string;
                 description
                   "Number of bytes dropped due to RED not available";
               }
               leaf queue-counters-red-bytes {
                 type uint64;
                 description
                   "Number of bytes dropped due to RED";
               }
               leaf queue-counters-red-bytes-rate {
                 type uint64;
                 description
                   "Rate at which bytes are dropped due to RED";
               }
               leaf queue-counters-red-bytes-ln {
                 type uint64;
                 description
                   "Number of RED dropped low-loss, non-TCP bytes";
               }
               leaf queue-counters-red-bytes-rate-ln {
                 type uint64;
                 description
                   "RED drop rate for low-loss, non-TCP bytes";
               }
               leaf queue-counters-red-bytes-lt {
                 type uint64;
                 description
                   "Number of RED dropped low-loss, TCP bytes";
               }
               leaf queue-counters-red-bytes-rate-lt {
                 type uint64;
                 description
                   "RED drop rate for low-loss, TCP bytes";
               }
               leaf queue-counters-red-bytes-hn {
                 type uint64;
                 description
                   "Number of RED dropped high-loss, non-TCP bytes";
               }
               leaf queue-counters-red-bytes-rate-hn {
                 type uint64;
                 description
                   "RED drop rate for high-loss, non-TCP bytes";
               }
               leaf queue-counters-red-bytes-ht {
                 type uint64;
                 description
                   "Number of RED dropped high-loss, TCP bytes";
               }
               leaf queue-counters-red-bytes-rate-ht {
                 type uint64;
                 description
                   "RED drop rate for high-loss, TCP bytes";
               }
               leaf queue-counters-red-bytes-low {
                 type uint64;
                 description
                   "Number of RED dropped low-loss bytes";
               }
               leaf queue-counters-red-bytes-rate-low {
                 type uint64;
                 description
                   "RED drop rate for low-loss bytes";
               }
               leaf queue-counters-red-bytes-medium-low {
                 type uint64;
                 description
                   "Number of RED dropped medium-low-loss bytes";
               }
               leaf queue-counters-red-bytes-rate-medium-low {
                 type uint64;
                 description
                   "RED drop rate for medium-low-loss bytes";
               }
               leaf queue-counters-red-bytes-medium-high {
                 type uint64;
                 description
                   "Number of RED dropped medium-high-loss bytes";
               }
               leaf queue-counters-red-bytes-rate-medium-high {
                 type uint64;
                 description
                   "RED drop rate for medium-high-loss bytes";
               }
               leaf queue-counters-red-bytes-medium {
                 type uint64;
                 description
                   "Number of RED dropped medium-loss bytes";
               }
               leaf queue-counters-red-bytes-rate-medium {
                 type uint64;
                 description
                   "RED drop rate for medium-loss bytes";
               }
               leaf queue-counters-red-bytes-high {
                 type uint64;
                 description
                   "Number of RED dropped high-loss bytes";
               }
               leaf queue-counters-red-bytes-rate-high {
                 type uint64;
                 description
                   "RED drop rate for high-loss bytes";
               }
               leaf queue-counters-timestamp {
                 type uint64;
                 description
                   "Last packet enqueued timestamp";
               }
               leaf queue-counters-total-drop-packets-rate {
                 type uint64;
                 description
                   "Number of total packets dropped at the queue";
               }
               leaf queue-counters-total-drop-bytes {
                 type uint64;
                 description
                   "Number of total packets dropped at the queue";
               }
               leaf queue-counters-total-drop-bytes-rate {
                 type uint64;
                 description
                   "Number of total packets dropped at the queue";
               }
               leaf queue-counters-reserved-buffer-packets {
                 type int32;
                 description
                   "Queues's usage of reserved buffer pool in pkts";
               }
               leaf queue-counters-reserved-buffer-bytes {
                 type int32;
                 description
                   "Queues's usage of reserved buffer pool in bytes";
               }
               leaf queue-counters-shared-buffer-packets {
                 type int32;
                 description
                   "Queues's usage of shared buffer pool in pkts";
               }
               leaf queue-counters-shared-buffer-bytes {
                 type int32;
                 description
                   "Queues's usage of shared buffer pool in bytes";
               }
               leaf queue-counters-depth-average {
                 type int32;
                 description
                   "Time averaged queue depth";
               }
               leaf queue-counters-depth-current {
                 type int32;
                 description
                   "Current instantaneous queue depth";
               }
               leaf queue-counters-depth-peak {
                 type int32;
                 description
                   "Peak queue depth";
               }
               leaf queue-counters-depth-max {
                 type int32;
                 description
                   "Maximum queue depth attained";
               }
               leaf queue-counters-srx-reserved-buffer-bytes {
                 type int32;
                 description
                   "Queues's usage of reserved buffer pool in bytes";
               }
               leaf queue-counters-srx-depth-current {
                 type int32;
                 description
                   "Current instantaneous queue depth";
               }
             }
             container interface-cos-short-summary {
               description
                 "Summary of queue information on an interface";
               leaf intf-cos-queue-type {
                 type string;
                 description
                   "Interface queue type";
               }
               leaf intf-cos-num-queues-supported {
                 type int32;
                 description
                   "Number of queues supported on this interface";
               }
               leaf intf-cos-num-queues-in-use {
                 type int32;
                 description
                   "Number of queues currently in use on this interface";
               }
               leaf intf-cos-queue-dedicated-or-shared {
                 type string;
                 description
                   "Interface has dedicated or shared queues";
               }
               leaf intf-cos-sched-resource-type {
                 type string;
                 description
                   "Interface scheduling resource type";
               }
               leaf intf-cos-sched-resource-usage-mic-limit {
                 type int32;
                 description
                   "MIC/PIC scheduling resource usage limit";
               }
               leaf intf-cos-sched-resource-usage-mic-count {
                 type int32;
                 description
                   "MIC/PIC scheduling resource usage count";
               }
               leaf intf-cos-sched-resource-usage-port-limit {
                 type int32;
                 description
                   "Interface scheduling resource limit";
               }
               leaf intf-cos-sched-resource-usage-port-count {
                 type int32;
                 description
                   "Interface scheduling resource usage";
               }
             }
             container interface-cos-summary {
               description
                 "Summary of forwarding class and queue information on an 
                 interface";
               leaf intf-cos-forwarding-classes-supported {
                 type int32;
                 description
                   "Number of forwarding classes supported on this interface";
               }
               leaf intf-cos-forwarding-classes-in-use {
                 type int32;
                 description
                   "Number of forwarding classes currently in use on this 
                   interface";
               }
               leaf intf-cos-queue-type {
                 type string;
                 description
                   "Interface queue type";
               }
               leaf intf-cos-num-queues-supported {
                 type int32;
                 description
                   "Number of queues supported on this interface";
               }
               leaf intf-cos-num-queues-in-use {
                 type int32;
                 description
                   "Number of queues currently in use on this interface";
               }
               leaf intf-cos-queue-dedicated-or-shared {
                 type string;
                 description
                   "Interface has dedicated or shared queues";
               }
               leaf intf-cos-sched-resource-type {
                 type string;
                 description
                   "Interface scheduling resource type";
               }
               leaf intf-cos-sched-resource-usage-mic-limit {
                 type int32;
                 description
                   "MIC/PIC scheduling resource usage limit";
               }
               leaf intf-cos-sched-resource-usage-mic-count {
                 type int32;
                 description
                   "MIC/PIC scheduling resource usage count";
               }
               leaf intf-cos-sched-resource-usage-port-limit {
                 type int32;
                 description
                   "Interface scheduling resource limit";
               }
               leaf intf-cos-sched-resource-usage-port-count {
                 type int32;
                 description
                   "Interface scheduling resource usage";
               }
               leaf intf-cos-burst-size-for-ifl {
                 type int32;
                 description
                   "Burst size for the logical interface";
               }
             }
           }
           container ingress-queue-counters {
             description
               "Ingress queue counter statistics";
             list queue {
               description
                 "Counters for a single queue";
               leaf queue-number {
                 type int32;
                 description
                   "Queue number";
               }
               leaf forwarding-class-name {
                 type string;
                 description
                   "Forwarding class name associated with queue";
               }
               leaf queue-counters-queued-packets {
                 type uint64;
                 description
                   "Queued packet count";
               }
               leaf queue-counters-queued-packets-rate {
                 type uint64;
                 description
                   "Rate at which packets are queued";
               }
               leaf queue-counters-queued-bytes {
                 type uint64;
                 description
                   "Queued bytes count";
               }
               leaf queue-counters-queued-bytes-rate {
                 type uint64;
                 description
                   "Rate at which bytes are queued";
               }
               leaf queue-counters-queued-packets-na {
                 type string;
                 description
                   "Queued packets not available";
               }
               leaf queue-counters-queued-bytes-na {
                 type string;
                 description
                   "Queued bytes not available";
               }
               leaf queue-counters-trans-packets {
                 type uint64;
                 description
                   "Total number of transmitted packets";
               }
               leaf queue-counters-trans-packets-rate {
                 type uint64;
                 description
                   "Rate at which packets are transmitted";
               }
               leaf queue-counters-trans-bytes {
                 type uint64;
                 description
                   "Total number of transmitted bytes";
               }
               leaf queue-counters-trans-bytes-rate {
                 type uint64;
                 description
                   "Rate at which bytes are transmitted";
               }
               leaf queue-counters-tail-drop-packets-na {
                 type string;
                 description
                   "Number of packets dropped due to tail drop not available";
               }
               leaf queue-counters-tail-drop-packets {
                 type uint64;
                 description
                   "Number of packets dropped at the tail of the queue";
               }
               leaf queue-counters-tail-drop-packets-rate {
                 type uint64;
                 description
                   "Rate at which packets are dropped at tail of queue";
               }
               leaf queue-counters-tail-drop-bytes {
                 type uint64;
                 description
                   "Number of packets dropped at tail drop of the queue";
               }
               leaf queue-counters-tail-drop-bytes-rate {
                 type uint64;
                 description
                   "Number of packets dropped at tail drop of the queue";
               }
               leaf queue-counters-rate-limit-drop-packets-na {
                 type string;
                 description
                   "Number of packets dropped due to rate-limit drop not 
                   available";
               }
               leaf queue-counters-rate-limit-drop-packets {
                 type uint64;
                 description
                   "Number of packets dropped by rate-limit for the queue";
               }
               leaf queue-counters-rate-limit-drop-packets-rate {
                 type uint64;
                 description
                   "Rate at which packets are dropped by rate-limit for the 
                   queue";
               }
               leaf queue-counters-rate-limit-drop-bytes-na {
                 type string;
                 description
                   "Number of bytes dropped due to tail drop not available";
               }
               leaf queue-counters-rate-limit-drop-bytes {
                 type uint64;
                 description
                   "Number of bytes dropped at the tail of the queue";
               }
               leaf queue-counters-rate-limit-drop-bytes-rate {
                 type uint64;
                 description
                   "Rate at which bytes are dropped at the tail of the queue";
               }
               leaf queue-counters-red-packets-na {
                 type string;
                 description
                   "Number of packets dropped due to RED not available";
               }
               leaf queue-counters-red-packets {
                 type uint64;
                 description
                   "Number of packets dropped due to RED";
               }
               leaf queue-counters-red-packets-rate {
                 type uint64;
                 description
                   "Rate at which packets are dropped due to RED";
               }
               leaf queue-counters-red-packets-ln {
                 type uint64;
                 description
                   "Number of RED dropped low-loss, non-TCP packets";
               }
               leaf queue-counters-red-packets-rate-ln {
                 type uint64;
                 description
                   "RED drop rate for low-loss, non-TCP packets";
               }
               leaf queue-counters-red-packets-lt {
                 type uint64;
                 description
                   "Number of RED dropped of low-loss, TCP packets";
               }
               leaf queue-counters-red-packets-rate-lt {
                 type uint64;
                 description
                   "RED drop rate for low-loss, TCP packets";
               }
               leaf queue-counters-red-packets-hn {
                 type uint64;
                 description
                   "Number of RED dropped high-loss, non-TCP packets";
               }
               leaf queue-counters-red-packets-rate-hn {
                 type uint64;
                 description
                   "RED drop rate for high-loss, non-TCP packets";
               }
               leaf queue-counters-red-packets-ht {
                 type uint64;
                 description
                   "Number of RED dropped high-loss, TCP packets";
               }
               leaf queue-counters-red-packets-rate-ht {
                 type uint64;
                 description
                   "RED drop rate for high-loss, TCP packets";
               }
               leaf queue-counters-red-packets-low {
                 type uint64;
                 description
                   "Number of RED dropped low-loss packets";
               }
               leaf queue-counters-red-packets-rate-low {
                 type uint64;
                 description
                   "RED drop rate for low-loss packets";
               }
               leaf queue-counters-red-packets-medium-low {
                 type uint64;
                 description
                   "Number of RED dropped medium-low-loss packets";
               }
               leaf queue-counters-red-packets-rate-medium-low {
                 type uint64;
                 description
                   "RED drop rate for medium-low-loss packets";
               }
               leaf queue-counters-red-packets-medium-high {
                 type uint64;
                 description
                   "Number of RED dropped medium-high-loss packets";
               }
               leaf queue-counters-red-packets-rate-medium-high {
                 type uint64;
                 description
                   "RED drop rate for medium-high-loss packets";
               }
               leaf queue-counters-red-packets-medium {
                 type uint64;
                 description
                   "Number of RED dropped medium-loss packets";
               }
               leaf queue-counters-red-packets-rate-medium {
                 type uint64;
                 description
                   "RED drop rate for medium-loss packets";
               }
               leaf queue-counters-red-packets-high {
                 type uint64;
                 description
                   "Number of RED dropped high-loss packets";
               }
               leaf queue-counters-red-packets-rate-high {
                 type uint64;
                 description
                   "RED drop rate for high-loss packets";
               }
               leaf queue-counters-red-bytes-na {
                 type string;
                 description
                   "Number of bytes dropped due to RED not available";
               }
               leaf queue-counters-red-bytes {
                 type uint64;
                 description
                   "Number of bytes dropped due to RED";
               }
               leaf queue-counters-red-bytes-rate {
                 type uint64;
                 description
                   "Rate at which bytes are dropped due to RED";
               }
               leaf queue-counters-red-bytes-ln {
                 type uint64;
                 description
                   "Number of RED dropped low-loss, non-TCP bytes";
               }
               leaf queue-counters-red-bytes-rate-ln {
                 type uint64;
                 description
                   "RED drop rate for low-loss, non-TCP bytes";
               }
               leaf queue-counters-red-bytes-lt {
                 type uint64;
                 description
                   "Number of RED dropped low-loss, TCP bytes";
               }
               leaf queue-counters-red-bytes-rate-lt {
                 type uint64;
                 description
                   "RED drop rate for low-loss, TCP bytes";
               }
               leaf queue-counters-red-bytes-hn {
                 type uint64;
                 description
                   "Number of RED dropped high-loss, non-TCP bytes";
               }
               leaf queue-counters-red-bytes-rate-hn {
                 type uint64;
                 description
                   "RED drop rate for high-loss, non-TCP bytes";
               }
               leaf queue-counters-red-bytes-ht {
                 type uint64;
                 description
                   "Number of RED dropped high-loss, TCP bytes";
               }
               leaf queue-counters-red-bytes-rate-ht {
                 type uint64;
                 description
                   "RED drop rate for high-loss, TCP bytes";
               }
               leaf queue-counters-red-bytes-low {
                 type uint64;
                 description
                   "Number of RED dropped low-loss bytes";
               }
               leaf queue-counters-red-bytes-rate-low {
                 type uint64;
                 description
                   "RED drop rate for low-loss bytes";
               }
               leaf queue-counters-red-bytes-medium-low {
                 type uint64;
                 description
                   "Number of RED dropped medium-low-loss bytes";
               }
               leaf queue-counters-red-bytes-rate-medium-low {
                 type uint64;
                 description
                   "RED drop rate for medium-low-loss bytes";
               }
               leaf queue-counters-red-bytes-medium-high {
                 type uint64;
                 description
                   "Number of RED dropped medium-high-loss bytes";
               }
               leaf queue-counters-red-bytes-rate-medium-high {
                 type uint64;
                 description
                   "RED drop rate for medium-high-loss bytes";
               }
               leaf queue-counters-red-bytes-medium {
                 type uint64;
                 description
                   "Number of RED dropped medium-loss bytes";
               }
               leaf queue-counters-red-bytes-rate-medium {
                 type uint64;
                 description
                   "RED drop rate for medium-loss bytes";
               }
               leaf queue-counters-red-bytes-high {
                 type uint64;
                 description
                   "Number of RED dropped high-loss bytes";
               }
               leaf queue-counters-red-bytes-rate-high {
                 type uint64;
                 description
                   "RED drop rate for high-loss bytes";
               }
               leaf queue-counters-timestamp {
                 type uint64;
                 description
                   "Last packet enqueued timestamp";
               }
               leaf queue-counters-total-drop-packets {
                 type uint64;
                 description
                   "Number of total packets dropped at the queue";
               }
               leaf queue-counters-total-drop-packets-rate {
                 type uint64;
                 description
                   "Number of total packets dropped at the queue";
               }
               leaf queue-counters-total-drop-bytes {
                 type uint64;
                 description
                   "Number of total packets dropped at the queue";
               }
               leaf queue-counters-total-drop-bytes-rate {
                 type uint64;
                 description
                   "Number of total packets dropped at the queue";
               }
               leaf queue-counters-reserved-buffer-packets {
                 type int32;
                 description
                   "Queues's usage of reserved buffer pool in pkts";
               }
               leaf queue-counters-reserved-buffer-bytes {
                 type int32;
                 description
                   "Queues's usage of reserved buffer pool in bytes";
               }
               leaf queue-counters-shared-buffer-packets {
                 type int32;
                 description
                   "Queues's usage of shared buffer pool in pkts";
               }
               leaf queue-counters-shared-buffer-bytes {
                 type int32;
                 description
                   "Queues's usage of shared buffer pool in bytes";
               }
               leaf queue-counters-depth-average {
                 type int32;
                 description
                   "Time averaged queue depth";
               }
               leaf queue-counters-depth-current {
                 type int32;
                 description
                   "Current instantaneous queue depth";
               }
               leaf queue-counters-depth-peak {
                 type int32;
                 description
                   "Peak queue depth";
               }
               leaf queue-counters-depth-max {
                 type int32;
                 description
                   "Maximum queue depth attained";
               }
               leaf queue-counters-srx-reserved-buffer-bytes {
                 type int32;
                 description
                   "Queues's usage of reserved buffer pool in bytes";
               }
               leaf queue-counters-srx-depth-current {
                 type int32;
                 description
                   "Current instantaneous queue depth";
               }
             }
             container interface-cos-summary {
               description
                 "Summary of forwarding class and queue information on an 
                 interface";
               leaf intf-cos-forwarding-classes-supported {
                 type int32;
                 description
                   "Number of forwarding classes supported on this interface";
               }
               leaf intf-cos-forwarding-classes-in-use {
                 type int32;
                 description
                   "Number of forwarding classes currently in use on this 
                   interface";
               }
               leaf intf-cos-queue-type {
                 type string;
                 description
                   "Interface queue type";
               }
               leaf intf-cos-num-queues-supported {
                 type int32;
                 description
                   "Number of queues supported on this interface";
               }
               leaf intf-cos-num-queues-in-use {
                 type int32;
                 description
                   "Number of queues currently in use on this interface";
               }
               leaf intf-cos-queue-dedicated-or-shared {
                 type string;
                 description
                   "Interface has dedicated or shared queues";
               }
               leaf intf-cos-sched-resource-type {
                 type string;
                 description
                   "Interface scheduling resource type";
               }
               leaf intf-cos-sched-resource-usage-mic-limit {
                 type int32;
                 description
                   "MIC/PIC scheduling resource usage limit";
               }
               leaf intf-cos-sched-resource-usage-mic-count {
                 type int32;
                 description
                   "MIC/PIC scheduling resource usage count";
               }
               leaf intf-cos-sched-resource-usage-port-limit {
                 type int32;
                 description
                   "Interface scheduling resource limit";
               }
               leaf intf-cos-sched-resource-usage-port-count {
                 type int32;
                 description
                   "Interface scheduling resource usage";
               }
               leaf intf-cos-burst-size-for-ifl {
                 type int32;
                 description
                   "Burst size for the logical interface";
               }
             }
             container interface-cos-short-summary {
               description
                 "Summary of queue information on an interface";
               leaf intf-cos-queue-type {
                 type string;
                 description
                   "Interface queue type";
               }
               leaf intf-cos-num-queues-supported {
                 type int32;
                 description
                   "Number of queues supported on this interface";
               }
               leaf intf-cos-num-queues-in-use {
                 type int32;
                 description
                   "Number of queues currently in use on this interface";
               }
               leaf intf-cos-queue-dedicated-or-shared {
                 type string;
                 description
                   "Interface has dedicated or shared queues";
               }
               leaf intf-cos-sched-resource-type {
                 type string;
                 description
                   "Interface scheduling resource type";
               }
               leaf intf-cos-sched-resource-usage-mic-limit {
                 type int32;
                 description
                   "MIC/PIC scheduling resource usage limit";
               }
               leaf intf-cos-sched-resource-usage-mic-count {
                 type int32;
                 description
                   "MIC/PIC scheduling resource usage count";
               }
               leaf intf-cos-sched-resource-usage-port-limit {
                 type int32;
                 description
                   "Interface scheduling resource limit";
               }
               leaf intf-cos-sched-resource-usage-port-count {
                 type int32;
                 description
                   "Interface scheduling resource usage";
               }
             }
             container queue-num-forwarding-class-name-map {
               leaf queue-number {
                 type int32;
                 description
                   "Queue number";
               }
               leaf forwarding-class-name {
                 type string;
                 description
                   "Forwarding class name associated with queue";
               }
             }
           }
           container forwarding-class-counters {
             description
               "Forwarding-class counter statistics";
             leaf forwarding-class-counters-error-message {
               type string;
               description
                 "Forwarding-class statistics not available for this 
                 interface";
             }
             container ipv4-forwarding-class-counters {
               leaf forwarding-class-stats-type {
                 type string;
               }
               container per-forwarding-class-counters {
                 leaf fc_name_header {
                   type string;
                 }
                 leaf forwarding-class-name {
                   type string;
                   description
                     "Forwarding class name associated with queue";
                 }
                 leaf fc-input-bytes {
                   type int32;
                 }
                 leaf fc-input-bytes-rate {
                   type int32;
                   description
                     "Input bytes rate";
                 }
                 leaf fc-output-bytes {
                   type int32;
                 }
                 leaf fc-output-bytes-rate {
                   type int32;
                   description
                     "Output bytes rate";
                 }
                 leaf fc-input-packets {
                   type int32;
                 }
                 leaf fc-input-packets-rate {
                   type int32;
                   description
                     "Input packets rate";
                 }
                 leaf fc-output-packets {
                   type int32;
                 }
                 leaf fc-output-packets-rate {
                   type int32;
                   description
                     "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container ipv6-forwarding-class-counters {
               leaf forwarding-class-stats-type {
                 type string;
               }
               container per-forwarding-class-counters {
                 leaf fc_name_header {
                   type string;
                 }
                 leaf forwarding-class-name {
                   type string;
                   description
                     "Forwarding class name associated with queue";
                 }
                 leaf fc-input-bytes {
                   type int32;
                 }
                 leaf fc-input-bytes-rate {
                   type int32;
                   description
                     "Input bytes rate";
                 }
                 leaf fc-output-bytes {
                   type int32;
                 }
                 leaf fc-output-bytes-rate {
                   type int32;
                   description
                     "Output bytes rate";
                 }
                 leaf fc-input-packets {
                   type int32;
                 }
                 leaf fc-input-packets-rate {
                   type int32;
                   description
                     "Input packets rate";
                 }
                 leaf fc-output-packets {
                   type int32;
                 }
                 leaf fc-output-packets-rate {
                   type int32;
                   description
                     "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container mpls-forwarding-class-counters {
               leaf forwarding-class-stats-type {
                 type string;
               }
               container per-forwarding-class-counters {
                 leaf fc_name_header {
                   type string;
                 }
                 leaf forwarding-class-name {
                   type string;
                   description
                     "Forwarding class name associated with queue";
                 }
                 leaf fc-input-bytes {
                   type int32;
                 }
                 leaf fc-input-bytes-rate {
                   type int32;
                   description
                     "Input bytes rate";
                 }
                 leaf fc-output-bytes {
                   type int32;
                 }
                 leaf fc-output-bytes-rate {
                   type int32;
                   description
                     "Output bytes rate";
                 }
                 leaf fc-input-packets {
                   type int32;
                 }
                 leaf fc-input-packets-rate {
                   type int32;
                   description
                     "Input packets rate";
                 }
                 leaf fc-output-packets {
                   type int32;
                 }
                 leaf fc-output-packets-rate {
                   type int32;
                   description
                     "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container layer2-forwarding-class-counters {
               leaf forwarding-class-stats-type {
                 type string;
               }
               container per-forwarding-class-counters {
                 leaf fc_name_header {
                   type string;
                 }
                 leaf forwarding-class-name {
                   type string;
                   description
                     "Forwarding class name associated with queue";
                 }
                 leaf fc-input-bytes {
                   type int32;
                 }
                 leaf fc-input-bytes-rate {
                   type int32;
                   description
                     "Input bytes rate";
                 }
                 leaf fc-output-bytes {
                   type int32;
                 }
                 leaf fc-output-bytes-rate {
                   type int32;
                   description
                     "Output bytes rate";
                 }
                 leaf fc-input-packets {
                   type int32;
                 }
                 leaf fc-input-packets-rate {
                   type int32;
                   description
                     "Input packets rate";
                 }
                 leaf fc-output-packets {
                   type int32;
                 }
                 leaf fc-output-packets-rate {
                   type int32;
                   description
                     "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container other-forwarding-class-counters {
               leaf forwarding-class-stats-type {
                 type string;
               }
               container per-forwarding-class-counters {
                 leaf fc_name_header {
                   type string;
                 }
                 leaf forwarding-class-name {
                   type string;
                   description
                     "Forwarding class name associated with queue";
                 }
                 leaf fc-input-bytes {
                   type int32;
                 }
                 leaf fc-input-bytes-rate {
                   type int32;
                   description
                     "Input bytes rate";
                 }
                 leaf fc-output-bytes {
                   type int32;
                 }
                 leaf fc-output-bytes-rate {
                   type int32;
                   description
                     "Output bytes rate";
                 }
                 leaf fc-input-packets {
                   type int32;
                 }
                 leaf fc-input-packets-rate {
                   type int32;
                   description
                     "Input packets rate";
                 }
                 leaf fc-output-packets {
                   type int32;
                 }
                 leaf fc-output-packets-rate {
                   type int32;
                   description
                     "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container protocol-aggregate-forwarding-class-counters {
               leaf forwarding-class-stats-type {
                 type string;
               }
               container per-forwarding-class-counters {
                 leaf fc_name_header {
                   type string;
                 }
                 leaf forwarding-class-name {
                   type string;
                   description
                     "Forwarding class name associated with queue";
                 }
                 leaf fc-input-bytes {
                   type int32;
                 }
                 leaf fc-input-bytes-rate {
                   type int32;
                   description
                     "Input bytes rate";
                 }
                 leaf fc-output-bytes {
                   type int32;
                 }
                 leaf fc-output-bytes-rate {
                   type int32;
                   description
                     "Output bytes rate";
                 }
                 leaf fc-input-packets {
                   type int32;
                 }
                 leaf fc-input-packets-rate {
                   type int32;
                   description
                     "Input packets rate";
                 }
                 leaf fc-output-packets {
                   type int32;
                 }
                 leaf fc-output-packets-rate {
                   type int32;
                   description
                     "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container forwarding-class-statistics {
               container protocol-aggregate-forwarding-class-counters {
               }
               container ipv4-forwarding-class-counters {
               }
               container ipv6-forwarding-class-counters {
               }
               container mpls-forwarding-class-counters {
               }
               container layer2-forwarding-class-counters {
               }
               container other-forwarding-class-counters {
               }
             }
             container forwarding-class-accounting-parameters {
               leaf forwarding-class-accounting-for-protocol {
                 type string;
               }
               leaf forwarding-class-accounting-for-traffic-direction {
                 type string;
               }
               leaf forwarding-class-accounting-for-traffic-type {
                 type string;
               }
               leaf forwarding-class-accounting-overhead-bytes {
                 type uint32;
               }
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container multilink-bundle-options {
             leaf filler-packet-interval {
               type int32;
             }
           }
           container multilink-traffic-statistics {
             container bundle {
             }
             container class {
               description
                 "Multilink class traffic statistics";
             }
             container multilink-detail-statistics {
               container bundle-detail {
               }
               container class-detail {
               }
             }
             container crtp {
               container crtp-sessions {
                 leaf input-frames {
                   type int32;
                 }
                 leaf output-frames {
                   type int32;
                 }
               }
               list crtp-statistics {
                 key "name";
                 leaf name {
                   type string;
                   description
                     "Name of this item";
                 }
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
             }
           }
           container traffic-statistics {
             leaf input-bps {
               type int32;
             }
             leaf input-pps {
               type int32;
             }
             leaf output-bps {
               type int32;
             }
             leaf output-pps {
               type int32;
             }
             leaf input-packets {
               type int32;
             }
             leaf output-packets {
               type int32;
             }
             leaf input-bytes {
               type int32;
             }
             leaf output-bytes {
               type int32;
             }
             container ipv6-transit-statistics {
               leaf input-bytes {
                 type int32;
               }
               leaf output-bytes {
                 type int32;
               }
               leaf input-packets {
                 type int32;
               }
               leaf output-packets {
                 type int32;
               }
             }
             container ipv6-total-statistics {
               leaf input-bytes {
                 type int32;
               }
               leaf output-bytes {
                 type int32;
               }
               leaf input-packets {
                 type int32;
               }
               leaf output-packets {
                 type int32;
               }
             }
           }
           container multicast-statistics {
             description
               "Multicast statistics for interface";
             leaf multicast-statistics-header {
               type empty;
             }
             container ipv4-multicast-statistics {
               description
                 "IPV4 multicast statistics for interface";
               leaf input-bytes {
                 type int32;
               }
               leaf input-bps {
                 type int32;
               }
               leaf output-bytes {
                 type int32;
               }
               leaf output-bps {
                 type int32;
               }
               leaf input-packets {
                 type int32;
               }
               leaf input-pps {
                 type int32;
               }
               leaf output-packets {
                 type int32;
               }
               leaf output-pps {
                 type int32;
               }
             }
             container ipv6-multicast-statistics {
               description
                 "IPV6 multicast statistics for interface";
               leaf input-bytes {
                 type int32;
               }
               leaf input-bps {
                 type int32;
               }
               leaf output-bytes {
                 type int32;
               }
               leaf output-bps {
                 type int32;
               }
               leaf input-packets {
                 type int32;
               }
               leaf input-pps {
                 type int32;
               }
               leaf output-packets {
                 type int32;
               }
               leaf output-pps {
                 type int32;
               }
             }
           }
           container ingress-traffic-statistics {
             description
               "Traffic statistics at ingress before entering Packet 
               Forwarding Engine";
             leaf input-bps {
               type int32;
             }
             leaf input-pps {
               type int32;
             }
             leaf input-drop-bps {
               type int32;
               description
                 "Drop rate at ingress in bits per second ";
             }
             leaf input-drop-pps {
               type int32;
               description
                 "Drop rate at ingress in packets per second ";
             }
             leaf input-bytes {
               type int32;
             }
             leaf input-packets {
               type int32;
             }
             leaf input-drop-bytes {
               type int32;
               description
                 "Drop statistics at ingress in bytes";
             }
             leaf input-drop-packets {
               type int32;
               description
                 "Drop statistics at ingress in packets";
             }
           }
           container transit-traffic-statistics {
             description
               "Statistics for traffic passing through the Packet Forwarding
               Engine";
           }
           container keepalive-statistics {
             description
               "Keepalive statistics for this interface";
             leaf keepalive-lmi-descriptor {
               type string;
             }
             leaf keepalive-input-count {
               type int32;
             }
             leaf keepalive-input-time {
               type string;
             }
             leaf keepalive-output-count {
               type int32;
             }
             leaf keepalive-output-time {
               type string;
             }
           }
           container virtual-circuit-information {
             description
               "Operational information and statistics for a virtual circuit";
             container traffic-statistics {
               leaf input-bps {
                 type int32;
               }
               leaf input-pps {
                 type int32;
               }
               leaf output-bps {
                 type int32;
               }
               leaf output-pps {
                 type int32;
               }
               leaf input-packets {
                 type int32;
               }
               leaf output-packets {
                 type int32;
               }
               leaf input-bytes {
                 type int32;
               }
               leaf output-bytes {
                 type int32;
               }
               container ipv6-transit-statistics {
                 leaf input-bytes {
                   type int32;
                 }
                 leaf output-bytes {
                   type int32;
                 }
                 leaf input-packets {
                   type int32;
                 }
                 leaf output-packets {
                   type int32;
                 }
               }
               container ipv6-total-statistics {
                 leaf input-bytes {
                   type int32;
                 }
                 leaf output-bytes {
                   type int32;
                 }
                 leaf input-packets {
                   type int32;
                 }
                 leaf output-packets {
                   type int32;
                 }
               }
             }
             container atm-cos-information {
               leaf vc-cos-mode {
                 type string;
                 description
                   "Virtual circuit CoS scheduling mode";
               }
               list atm-cos-queue {
                 container atm-cos-queue-parameters {
                   leaf cos-forwarding-class-name {
                     type string;
                     description
                       "Forwarding class name associated with queue";
                   }
                   leaf cos-queue-number {
                     type int32;
                     description
                       "Queue number";
                   }
                   leaf scheduling-priority {
                     type string;
                     description
                       "Scheduling priority";
                   }
                   leaf transmit-weight-cells {
                     type int32;
                     description
                       "Weight to apply to scheduling as number of cells";
                   }
                   leaf transmit-weight-percent {
                     type int32;
                     description
                       "Weight to apply to scheduling as fill percentage";
                   }
                   leaf epd-threshold {
                     type int32;
                     description
                       "Early packet drop threshold";
                   }
                   leaf epd-threshold-plp0 {
                     type int32;
                     description
                       "Early packet drop threshold for PLP 0";
                   }
                   leaf epd-threshold-plp1 {
                     type int32;
                     description
                       "Early packet drop threshold for PLP 1";
                   }
                   container linear-red-drop-profile {
                     leaf queue-depth {
                       type uint32;
                       description
                         "Instantaneous queue depth";
                     }
                     leaf low-red {
                       type int32;
                       description
                         "Fill level percentage when linear RED is applied 
                         for low PLP";
                     }
                     leaf high-red {
                       type int32;
                       description
                         "Fill level percentage when linear RED is applied 
                         for high PLP";
                     }
                     leaf max-low-red {
                       type int32;
                       description
                         "Fill level percentage with 100% packet drop for 
                         low PLP";
                     }
                     leaf max-high-red {
                       type int32;
                       description
                         "Fill level percentage with 100% packet drop for 
                         high PLP";
                     }
                   }
                 }
                 container atm-cos-queue-statistics {
                   leaf atm-output-bytes {
                     type int32;
                   }
                   leaf atm-output-packets {
                     type int32;
                   }
                   leaf atm-packet-drops {
                     type int32;
                   }
                 }
                 container atm-cos-plp-statistics {
                   leaf atm-plp0-output-bytes {
                     type int32;
                   }
                   leaf atm-plp1-output-bytes {
                     type int32;
                   }
                   leaf atm-plp0-output-packets {
                     type int32;
                   }
                   leaf atm-plp1-output-packets {
                     type int32;
                   }
                   leaf atm-plp0-byte-drops {
                     type int32;
                   }
                   leaf atm-plp1-byte-drops {
                     type int32;
                   }
                   leaf atm-plp0-packet-drops {
                     type int32;
                   }
                   leaf atm-plp1-packet-drops {
                     type int32;
                   }
                 }
               }
             }
           }
           list filter-information {
             leaf filter-family {
               type string;
               description
                 "Protocol family of the filter";
             }
             leaf-list filter-input {
               type string;
               description
                 "Name of the input filter";
             }
             leaf-list filter-output {
               type string;
               description
                 "Name of the output filter";
             }
           }
           list address-family {
             leaf local-bias-information {
               type string;
             }
             leaf ft-iff-dest-port {
               type uint32;
               description
                 "Destination UDP port to be used for this family";
             }
             container pppoe-underlying-information {
               description
                 "PPPoE Underlying information";
               list pppoe-underlying-interface {
                 leaf dynamic-profile {
                   type string;
                   description
                     "Dynamic Profile name";
                 }
                 leaf service-name-table {
                   type string;
                   description
                     "Name of Service Name Table";
                 }
                 leaf max-sessions {
                   type int32;
                   description
                     "Maximum number of PPPoE sessions";
                 }
                 leaf max-sessions-vsa-ignore {
                   type string;
                   description
                     "Ignore max-sessions VSA";
                 }
                 leaf duplicate-protection {
                   type string;
                   description
                     "Duplicate protection mode";
                 }
                 leaf short-cycle-protection {
                   type string;
                   description
                     "Short cycle protection mode";
                 }
                 leaf direct-connect {
                   type string;
                   description
                     "Direct connect mode";
                 }
                 leaf ac-name {
                   type string;
                   description
                     "Access Concentrator name";
                 }
                 leaf underlying-interface-name {
                   type string;
                   description
                     "Underlying interface name";
                 }
                 leaf underlying-interface-index {
                   type string;
                   description
                     "Underlying interface index";
                 }
                 leaf encapsulation-type-identifier {
                   type string;
                   description
                     "Encapsulation type identifier";
                 }
                 leaf state {
                   type string;
                   description
                     "State";
                 }
                 leaf active-sessions {
                   type int32;
                   description
                     "Number of active PPPoE sessions";
                 }
                 leaf aci-autosensing {
                   type string;
                   description
                     "ACI VLAN Autosensing mode";
                 }
                 leaf line-identity-autosensing {
                   type string;
                   description
                     "Line Identity Autosensing mode";
                 }
               }
             }
             list interface-address {
             }
             container destination-class-statistics {
               description
                 "Destination class usage (DCU) statistics";
             }
             container source-class-statistics {
               description
                 "Source class usage (SCU) statistics";
             }
           }
           list bridge-iff-properties {
             description
               "Information about Ethernet-switching address family";
           }
           container l2circuit-info {
             leaf out-of-sequence {
               type int32;
             }
             leaf denied-packets {
               type int32;
             }
             leaf cell-bundle-size {
               type int32;
             }
             leaf cell-bundle-timeout {
               type int32;
             }
             leaf cell-timeout-count {
               type int32;
             }
           }
           container media-information {
             description
               "Information about media alarms";
             leaf media-type {
               type string;
               description
                 "Type of media this information is for";
             }
             list media-alarm {
               leaf media-alarm-name {
                 type string;
               }
               leaf media-alarm-count {
                 type int32;
               }
               leaf media-alarm-seconds {
                 type int32;
               }
               leaf media-alarm-state {
                 type string;
               }
               leaf ce-counter-name {
                 type string;
                 description
                   "Circuit Emulation counter information";
               }
               leaf ce-counter-packets {
                 type int32;
                 description
                   "Circuit Emulation number of packets";
               }
               leaf ce-counter-bytes {
                 type int32;
                 description
                   "Circuit Emulation number of bytes";
               }
               leaf ce-counter-count {
                 type int32;
                 description
                   "Circuit Emulation number of event occurrences";
               }
             }
             leaf ds1-timeslots {
               type string;
             }
             leaf ds1-line-encoding {
               type string;
             }
             leaf ds1-byte-encoding {
               type string;
             }
             leaf ds1-data-inversion {
               type string;
             }
             leaf idle-cycle-flag {
               type string;
             }
             leaf start-end-flag {
               type string;
             }
             leaf ds0-byte-encoding {
               type string;
             }
             leaf ds0-data-inversion {
               type string;
             }
             leaf e3-data-inversion {
               type string;
             }
             leaf ds1-buildout {
               type string;
               description
                 "Number of feet";
             }
           }
           list macsec-statistics {
             description
               "Information about MAC Security statistics details";
             leaf interface-name {
               type string;
               description
                 "Class-of-service interface name";
             }
             leaf encrypted-packets {
               type uint64;
               description
                 "Macsec encrypted packets sent";
             }
             leaf encrypted-bytes {
               type uint64;
               description
                 "Macsec encrypted bytes sent";
             }
             leaf protected-packets {
               type uint64;
               description
                 "Macsec packets sent with only integrity protection";
             }
             leaf protected-bytes {
               type uint64;
               description
                 "Macsec bytes sent with only integrity protection";
             }
             leaf ok-packets {
               type uint64;
               description
                 "Macsec packets accepted";
             }
             leaf decrypted-bytes {
               type uint64;
               description
                 "Macsec received bytes decrypted";
             }
             leaf decrypted-packets {
               type uint64;
               description
                 "Macsec received packets decrypted";
             }
             leaf validated-packets {
               type uint64;
               description
                 "Macsec received packets validated";
             }
             leaf validated-bytes {
               type uint64;
               description
                 "Macsec received bytes validated";
             }
             leaf untagged-packets {
               type uint64;
               description
                 "Macsec untagged packets";
             }
             leaf toolong-packets {
               type uint64;
               description
                 "Macsec too long packets transmitted on a secure channel";
             }
             leaf control-packets {
               type uint64;
               description
                 "Macsec control packets received on a secure channel";
             }
             leaf tagged-miss-packets {
               type uint64;
               description
                 "Macsec tagged miss packets received on a secure channel";
             }
             leaf untagged-hit-packets {
               type uint64;
               description
                 "Macsec untagged hit packets received on a secure channel";
             }
             leaf notag-packets {
               type uint64;
               description
                 "Macsec no tag packets received on a secure channel";
             }
             leaf badtag-packets {
               type uint64;
               description
                 "Macsec bad tag packets received on a secure channel";
             }
             leaf unknown-sci-packets {
               type uint64;
               description
                 "Macsec unknown sci packets received on a secure channel";
             }
             leaf no-sci-packets {
               type uint64;
               description
                 "Macsec no sci packets received on a secure channel";
             }
             leaf control-pass-packets {
               type uint64;
               description
                 "Macsec allowed control packets received on a secure 
                 channel";
             }
             leaf uncontrol-pass-packets {
               type uint64;
               description
                 "Macsec allowed uncontrol packets received on a secure 
                 channel";
             }
             leaf control-fail-packets {
               type uint64;
               description
                 "Macsec dropped control packets received on a secure 
                 channel";
             }
             leaf uncontrol-fail-packets {
               type uint64;
               description
                 "Macsec dropped uncontrol packets received on a secure 
                 channel";
             }
             leaf hit-dropped-packets {
               type uint64;
               description
                 "Macsec hit dropped packets received on a security channel";
             }
             leaf notusing-sa-packets {
               type uint64;
               description
                 "Macsec not using sa packets received on a security channel";
             }
             leaf unused-sa-packets {
               type uint64;
               description
                 "Macsec unused sa packets received on a security channel";
             }
             leaf late-packets {
               type uint64;
               description
                 "Macsec late packets dropped on a security channel";
             }
             leaf delayed-packets {
               type uint64;
               description
                 "Macsec delayed packets accepted on a security channel";
             }
             leaf unchecked-packets {
               type uint64;
               description
                 "Macsec unchecked packets accepted on a security channel";
             }
             leaf notvalid-packets {
               type uint64;
               description
                 "Macsec not valid packets dropped on a security channel";
             }
             leaf invalid-packets {
               type uint64;
               description
                 "Macsec invalid packets accepted on a security channel";
             }
             list secure-channel-sent {
               leaf encrypted-packets {
                 type uint64;
                 description
                   "Macsec encrypted packets sent";
               }
               leaf encrypted-bytes {
                 type uint64;
                 description
                   "Macsec encrypted bytes sent";
               }
               leaf protected-packets {
                 type uint64;
                 description
                   "Macsec packets sent with only integrity protection";
               }
               leaf protected-bytes {
                 type uint64;
                 description
                   "Macsec bytes sent with only integrity protection";
               }
             }
             list secure-association-sent {
               leaf encrypted-packets {
                 type uint64;
                 description
                   "Macsec encrypted packets sent";
               }
               leaf encrypted-bytes {
                 type uint64;
                 description
                   "Macsec encrypted bytes sent";
               }
               leaf protected-packets {
                 type uint64;
                 description
                   "Macsec packets sent with only integrity protection";
               }
               leaf protected-bytes {
                 type uint64;
                 description
                   "Macsec bytes sent with only integrity protection";
               }
             }
             list secure-channel-received {
               leaf ok-packets {
                 type uint64;
                 description
                   "Macsec packets accepted";
               }
               leaf decrypted-packets {
                 type uint64;
                 description
                   "Macsec received packets decrypted";
               }
               leaf decrypted-bytes {
                 type uint64;
                 description
                   "Macsec received bytes decrypted";
               }
               leaf validated-packets {
                 type uint64;
                 description
                   "Macsec received packets validated";
               }
               leaf validated-bytes {
                 type uint64;
                 description
                   "Macsec received bytes validated";
               }
             }
             list secure-association-received {
               leaf ok-packets {
                 type uint64;
                 description
                   "Macsec packets accepted";
               }
               leaf decrypted-packets {
                 type uint64;
                 description
                   "Macsec received packets decrypted";
               }
               leaf decrypted-bytes {
                 type uint64;
                 description
                   "Macsec received bytes decrypted";
               }
               leaf validated-packets {
                 type uint64;
                 description
                   "Macsec received packets validated";
               }
               leaf validated-bytes {
                 type uint64;
                 description
                   "Macsec received bytes validated";
               }
             }
             list macsec-error-information {
               list secure-channel-sent-errors {
                 leaf untagged-packets {
                   type uint64;
                   description
                     "Macsec untagged packets";
                 }
                 leaf toolong-packets {
                   type uint64;
                   description
                     "Macsec too long packets transmitted on a secure 
                     channel";
                 }
               }
               list secure-channel-received-errors {
                 leaf control-packets {
                   type uint64;
                   description
                     "Macsec control packets received on a secure channel";
                 }
                 leaf tagged-miss-packets {
                   type uint64;
                   description
                     "Macsec tagged miss packets received on a secure 
                     channel";
                 }
                 leaf untagged-hit-packets {
                   type uint64;
                   description
                     "Macsec untagged hit packets received on a secure 
                     channel";
                 }
                 leaf untagged-packets {
                   type uint64;
                   description
                     "Macsec untagged packets";
                 }
                 leaf notag-packets {
                   type uint64;
                   description
                     "Macsec no tag packets received on a secure channel";
                 }
                 leaf badtag-packets {
                   type uint64;
                   description
                     "Macsec bad tag packets received on a secure channel";
                 }
                 leaf unknown-sci-packets {
                   type uint64;
                   description
                     "Macsec unknown sci packets received on a secure 
                     channel";
                 }
                 leaf no-sci-packets {
                   type uint64;
                   description
                     "Macsec no sci packets received on a secure channel";
                 }
                 leaf control-pass-packets {
                   type uint64;
                   description
                     "Macsec allowed control packets received on a secure 
                     channel";
                 }
                 leaf control-fail-packets {
                   type uint64;
                   description
                     "Macsec dropped control packets received on a secure 
                     channel";
                 }
                 leaf uncontrol-pass-packets {
                   type uint64;
                   description
                     "Macsec allowed uncontrol packets received on a secure 
                     channel";
                 }
                 leaf uncontrol-fail-packets {
                   type uint64;
                   description
                     "Macsec dropped uncontrol packets received on a secure 
                     channel";
                 }
               }
               list secure-channel-received-extended {
                 leaf hit-dropped-packets {
                   type uint64;
                   description
                     "Macsec hit dropped packets received on a security 
                     channel";
                 }
                 leaf invalid-packets {
                   type uint64;
                   description
                     "Macsec invalid packets accepted on a security channel";
                 }
                 leaf late-packets {
                   type uint64;
                   description
                     "Macsec late packets dropped on a security channel";
                 }
                 leaf delayed-packets {
                   type uint64;
                   description
                     "Macsec delayed packets accepted on a security channel";
                 }
                 leaf unchecked-packets {
                   type uint64;
                   description
                     "Macsec unchecked packets accepted on a security 
                     channel";
                 }
                 leaf notvalid-packets {
                   type uint64;
                   description
                     "Macsec not valid packets dropped on a security channel";
                 }
                 leaf notusing-sa-packets {
                   type uint64;
                   description
                     "Macsec not using sa packets received on a security 
                     channel";
                 }
                 leaf unused-sa-packets {
                   type uint64;
                   description
                     "Macsec unused sa packets received on a security 
                     channel";
                 }
                 leaf untagged-hit-packets {
                   type uint64;
                   description
                     "Macsec untagged hit packets received on a secure 
                     channel";
                 }
               }
             }
           }
           container lag-traffic-statistics {
             container lag-multicast-statistics {
               leaf lag-multicast-statistics-header {
                 type empty;
               }
               container lag-ipv4-multicast-statistics {
                 leaf input-packets {
                   type int32;
                 }
                 leaf input-pps {
                   type int32;
                 }
                 leaf input-bytes {
                   type int32;
                 }
                 leaf input-bps {
                   type int32;
                 }
                 leaf output-packets {
                   type int32;
                 }
                 leaf output-pps {
                   type int32;
                 }
                 leaf output-bytes {
                   type int32;
                 }
                 leaf output-bps {
                   type int32;
                 }
               }
               container lag-ipv6-multicast-statistics {
                 leaf input-packets {
                   type int32;
                 }
                 leaf input-pps {
                   type int32;
                 }
                 leaf input-bytes {
                   type int32;
                 }
                 leaf input-bps {
                   type int32;
                 }
                 leaf output-packets {
                   type int32;
                 }
                 leaf output-pps {
                   type int32;
                 }
                 leaf output-bytes {
                   type int32;
                 }
                 leaf output-bps {
                   type int32;
                 }
               }
             }
             list if-distribution-list-information {
             }
           }
           container layer2-input-policer-statistics {
             description
               "Layer 2 input policer statistics for interface";
             leaf policer-medium-low-frames {
               type int32;
               description
                 "Number of loss priority medium low frames";
             }
             leaf policer-medium-low-bytes {
               type int32;
               description
                 "Number of loss priority medium low bytes";
             }
             leaf policer-medium-low-rate {
               type int32;
               description
                 "Rate of loss priority medium low pkts";
             }
           }
           container layer2-output-policer-statistics {
             description
               "Layer 2 output policer statistics for interface";
             leaf policer-medium-low-frames {
               type int32;
               description
                 "Number of loss priority medium low frames";
             }
             leaf policer-medium-low-bytes {
               type int32;
               description
                 "Number of loss priority medium low bytes";
             }
             leaf policer-medium-low-rate {
               type int32;
               description
                 "Rate of loss priority medium low pkts";
             }
           }
           container mac-policer-information {
             container ether-policer-list {
             }
           }
         }
         container active-alarms-otn {
         }
         container active-defects-otn {
         }
         container active-alarms-optics {
         }
         container active-defects-optics {
         }
         container optics-defect-information {
           list media-alarm {
             leaf media-alarm-name {
               type string;
             }
             leaf media-alarm-seconds {
               type int32;
             }
             leaf media-alarm-count {
               type int32;
             }
             leaf media-alarm-state {
               type string;
             }
           }
         }
         container optics-fec-information {
           list media-alarm {
             leaf media-alarm-name {
               type string;
             }
             leaf media-alarm-seconds {
               type int32;
             }
             leaf media-alarm-count {
               type int32;
             }
             leaf media-alarm-state {
               type string;
             }
           }
         }
         container active-alerts-otn {
         }
         container links {
           description
             "Aggregated SONET/SDH link information";
           list link-entry {
             description
               "SONET/SDH link information";
             leaf sonet-payload-pointer-curptr {
               type string;
               description
                 "Value of the SONET/SDH payload pointer, derived from the 
                 H1 and H2 overhead bytes";
             }
             leaf sonet-payload-pointer-ptrinc-count {
               type string;
               description
                 "Number of times the value of the SONET/SDH payload pointer
                 had positive justification";
             }
             leaf sonet-payload-pointer-ptrdec-count {
               type string;
               description
                 "Number of times the value of the SONET/SDH payload pointer
                 had negative justification";
             }
             leaf sonet-payload-pointer-newptr-ndf-count {
               type string;
               description
                 "Number of times a new payload pointer was created with the
                 New Data Found flag set";
             }
             leaf sonet-rx-overhead {
               type string;
             }
             leaf sonet-tx-overhead {
               type string;
             }
             leaf sonet-rx-path-trace {
               type string;
               description
                 "Received SONET path trace";
             }
             leaf sonet-tx-path-trace {
               type string;
               description
                 "Transmitted SONET path trace";
             }
             container active-alarms {
             }
             container active-defects {
             }
             container sonet-errors {
               list media-alarm {
                 leaf media-alarm-name {
                   type string;
                 }
                 leaf media-alarm-count {
                   type int32;
                 }
               }
             }
             container sonet-physical-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-section-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-line-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-path-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-vt-information {
               list media-alarm {
                 leaf media-alarm-name {
                   type string;
                 }
                 leaf media-alarm-seconds {
                   type int32;
                 }
                 leaf media-alarm-count {
                   type int32;
                 }
                 leaf media-alarm-state {
                   type string;
                 }
               }
             }
             list optics-diagnostics {
               description
                 "Optics diagnostics";
               leaf optic-diagnostics-not-available {
                 type string;
                 description
                   "Optical diagnostics not supported by this transceiver";
               }
               leaf laser-bias-current-not-available {
                 type string;
                 description
                   "Laser bias current measurement not available";
               }
               leaf soa-bias-current-not-available {
                 type string;
                 description
                   "SOA bias current measurement not available";
               }
               leaf laser-tx-power-not-available {
                 type string;
                 description
                   "Laser output power measurement not available";
               }
               leaf module-temperature-not-available {
                 type string;
                 description
                   "Module temperature measurement not available";
               }
               leaf tx-module-temperature-not-available {
                 type string;
                 description
                   "Tx module temperature measurement not available";
               }
               leaf rx-module-temperature-not-available {
                 type string;
                 description
                   "Rx module temperature measurement not available";
               }
               leaf laser-rx-power-not-available {
                 type string;
                 description
                   "Laser receiver optical power measurement not available";
               }
               leaf laser-tx-power-high-alarm-threshold-not-available {
                 type string;
                 description
                   "Laser output power high alarm threshold not available";
               }
               leaf laser-tx-power-low-alarm-threshold-not-available {
                 type string;
                 description
                   "Laser output power low alarm threshold not available";
               }
               leaf laser-tx-power-high-warning-threshold-not-available {
                 type string;
                 description
                   "Laser output power high warning threshold not available";
               }
               leaf laser-tx-power-low-warning-threshold-not-available {
                 type string;
                 description
                   "Laser output power low warning threshold not available";
               }
               leaf laser-bias-current {
                 type string;
                 description
                   "Laser bias current (milliamperes)";
               }
               leaf soa-bias-current {
                 type string;
                 description
                   "SOA bias current (milliamperes)";
               }
               leaf laser-output-power {
                 type string;
                 description
                   "Laser output power (milliwatts)";
               }
               leaf laser-output-power-dbm {
                 type string;
                 description
                   "Laser output power (dBm)";
               }
               leaf module-temperature {
                 type string;
                 description
                   "Module temperature";
               }
               leaf tx-module-temperature {
                 type string;
                 description
                   "Tx module temperature";
               }
               leaf rx-module-temperature {
                 type string;
                 description
                   "Rx module temperature";
               }
               leaf module-voltage {
                 type string;
                 description
                   "Module voltage";
               }
               leaf corrected-error-ratio {
                 type string;
                 description
                   "Corrected error ratio";
               }
               leaf uncorrected-words-ratio {
                 type string;
                 description
                   "Uncorrected words ratio";
               }
               leaf tx-module-voltage {
                 type string;
                 description
                   "Tx module voltage";
               }
               leaf rx-module-voltage {
                 type string;
                 description
                   "Rx module voltage";
               }
               leaf rx-signal-avg-optical-power {
                 type string;
                 description
                   "Receiver signal average power (milliwatts)";
               }
               leaf rx-signal-avg-optical-power-dbm {
                 type string;
                 description
                   "Receiver signal average power (dBm)";
               }
               leaf laser-rx-optical-power {
                 type string;
                 description
                   "Laser receiver optical power (milliwatts)";
               }
               leaf laser-rx-optical-power-dbm {
                 type string;
                 description
                   "Laser receiver optical power (dBm)";
               }
               leaf wavelength-channel {
                 type string;
                 description
                   "Wavelength channel number set";
               }
               leaf wavelength-setpoint {
                 type string;
                 description
                   "Wavelength point set";
               }
               leaf tx-dither {
                 type string;
                 description
                   "Tx dither status";
               }
               leaf frequency-error {
                 type string;
                 description
                   "Frequency error value";
               }
               leaf wavelength-error {
                 type string;
                 description
                   "Wavelength error value";
               }
               leaf laser-bias-current-high-alarm {
                 type string;
                 description
                   "Laser bias current high alarm";
               }
               leaf laser-bias-current-low-alarm {
                 type string;
                 description
                   "Laser bias current low alarm";
               }
               leaf laser-bias-current-high-warn {
                 type string;
                 description
                   "Laser bias current high warning";
               }
               leaf laser-bias-current-low-warn {
                 type string;
                 description
                   "Laser bias current low warning";
               }
               leaf soa-bias-current-high-alarm {
                 type string;
                 description
                   "SOA bias current high alarm";
               }
               leaf soa-bias-current-low-alarm {
                 type string;
                 description
                   "SOA bias current low alarm";
               }
               leaf soa-bias-current-high-warn {
                 type string;
                 description
                   "SOA bias current high warning";
               }
               leaf soa-bias-current-low-warn {
                 type string;
                 description
                   "SOA bias current low warning";
               }
               leaf laser-tx-power-high-alarm {
                 type string;
                 description
                   "Laser output power high alarm";
               }
               leaf laser-tx-power-low-alarm {
                 type string;
                 description
                   "Laser output power low alarm";
               }
               leaf laser-tx-power-high-warn {
                 type string;
                 description
                   "Laser output power high warning";
               }
               leaf laser-tx-power-low-warn {
                 type string;
                 description
                   "Laser output power low warning";
               }
               leaf tx-power-high-alarm {
                 type string;
                 description
                   "Tx power high alarm";
               }
               leaf tx-power-low-alarm {
                 type string;
                 description
                   "Tx power low alarm";
               }
               leaf tx-power-high-warn {
                 type string;
                 description
                   "Tx power high warning";
               }
               leaf tx-power-low-warn {
                 type string;
                 description
                   "Tx power low warning";
               }
               leaf module-temperature-high-alarm {
                 type string;
                 description
                   "Module temperature high alarm";
               }
               leaf module-temperature-low-alarm {
                 type string;
                 description
                   "Module temperature low alarm";
               }
               leaf module-temperature-high-warn {
                 type string;
                 description
                   "Module temperature high warning";
               }
               leaf module-temperature-low-warn {
                 type string;
                 description
                   "Module temperature low warning";
               }
               leaf tx-module-temperature-high-alarm {
                 type string;
                 description
                   "Tx module temperature high alarm";
               }
               leaf tx-module-temperature-low-alarm {
                 type string;
                 description
                   "Tx module temperature low alarm";
               }
               leaf rx-module-temperature-high-alarm {
                 type string;
                 description
                   "Rx module temperature high alarm";
               }
               leaf rx-module-temperature-low-alarm {
                 type string;
                 description
                   "Rx module temperature low alarm";
               }
               leaf module-voltage-high-alarm {
                 type string;
                 description
                   "Module voltage high alarm";
               }
               leaf module-voltage-low-alarm {
                 type string;
                 description
                   "Module voltage low alarm";
               }
               leaf module-voltage-high-warn {
                 type string;
                 description
                   "Module voltage high warning";
               }
               leaf module-voltage-low-warn {
                 type string;
                 description
                   "Module voltage low warning";
               }
               leaf tx-module-voltage-high-alarm {
                 type string;
                 description
                   "Tx module voltage high alarm";
               }
               leaf tx-module-voltage-low-alarm {
                 type string;
                 description
                   "Tx module voltage low alarm";
               }
               leaf rx-module-voltage-high-alarm {
                 type string;
                 description
                   "Rx module voltage high alarm";
               }
               leaf rx-module-voltage-low-alarm {
                 type string;
                 description
                   "Rx module voltage low alarm";
               }
               leaf laser-rx-power-high-alarm {
                 type string;
                 description
                   "Laser receiver power high alarm";
               }
               leaf laser-rx-power-low-alarm {
                 type string;
                 description
                   "Laser receiver power low alarm";
               }
               leaf laser-rx-power-high-warn {
                 type string;
                 description
                   "Laser receiver power high warning";
               }
               leaf laser-rx-power-low-warn {
                 type string;
                 description
                   "Laser receiver power low warning";
               }
               leaf rx-power-high-alarm {
                 type string;
                 description
                   "Receiver power high alarm";
               }
               leaf rx-power-low-alarm {
                 type string;
                 description
                   "Receiver power low alarm";
               }
               leaf rx-power-high-warn {
                 type string;
                 description
                   "Receiver power high warning";
               }
               leaf rx-power-low-warn {
                 type string;
                 description
                   "Receiver power low warning";
               }
               leaf laser-end-of-life-alarm {
                 type string;
                 description
                   "Laser end-of-life alarm";
               }
               leaf laser-wavelength-alarm {
                 type string;
                 description
                   "Laser wavelength alarm";
               }
               leaf laser-bias-current-alarm {
                 type string;
                 description
                   "Laser bias current alarm";
               }
               leaf module-temperature-alarm {
                 type string;
                 description
                   "Module temperature alarm";
               }
               leaf laser-power-alarm {
                 type string;
                 description
                   "Laser power alarm";
               }
               leaf modulator-temperature-alarm {
                 type string;
                 description
                   "Modulator temperature alarm";
               }
               leaf modulator-bias-alarm {
                 type string;
                 description
                   "Modulator bias alarm";
               }
               leaf module-not-ready-alarm {
                 type string;
                 description
                   "Module not ready alarm";
               }
               leaf module-power-down-alarm {
                 type string;
                 description
                   "Module power down alarm";
               }
               leaf module-not-init-done-alarm {
                 type string;
                 description
                   "Module initialization not done alarm";
               }
               leaf module-not-high-power-on-alarm {
                 type string;
                 description
                   "Module not high powered on alarm";
               }
               leaf module-fault-alarm {
                 type string;
                 description
                   "Module in fault state alarm";
               }
               leaf pld-flash-init-fault-alarm {
                 type string;
                 description
                   "PLD or Flash initialization fault alarm";
               }
               leaf power-supply-fault-alarm {
                 type string;
                 description
                   "Power supply fault alarm";
               }
               leaf checksum-fault-alarm {
                 type string;
                 description
                   "Checksum fault alarm";
               }
               leaf apd-supply-fault-alarm {
                 type string;
                 description
                   "APD supply fault alarm";
               }
               leaf tec-fault-alarm {
                 type string;
                 description
                   "TEC fault alarm";
               }
               leaf wavelength-unlocked-alarm {
                 type string;
                 description
                   "Wavelength unlocked alarm";
               }
               leaf tx-tune-alarm {
                 type string;
                 description
                   "Tx tune alarm";
               }
               leaf tx-mux-fifo-error-alarm {
                 type string;
                 description
                   "Tx multiplexer fifo error alarm";
               }
               leaf tx-loss-of-pll-alarm {
                 type string;
                 description
                   "Tx loss of PLL alarm";
               }
               leaf tx-data-not-ready-alarm {
                 type string;
                 description
                   "Tx data not ready alarm";
               }
               leaf tx-not-ready-alarm {
                 type string;
                 description
                   "Tx not ready alarm";
               }
               leaf tx-laser-fault-alarm {
                 type string;
                 description
                   "Tx laser fault alarm";
               }
               leaf tx-laser-disabled-alarm {
                 type string;
                 description
                   "Tx laser disabled alarm";
               }
               leaf tx-loss-of-signal-functionality-alarm {
                 type string;
                 description
                   "Tx loss of signal functionality alarm";
               }
               leaf tx-cdr-loss-of-lock-alarm {
                 type string;
                 description
                   "Tx CDR loss of lock alarm";
               }
               leaf rx-loss-avg-opt-power-alarm {
                 type string;
                 description
                   "Receiver loss of average optical power alarm";
               }
               leaf rx-loss-ac-power-alarm {
                 type string;
                 description
                   "Receiver loss of AC power alarm";
               }
               leaf rx-loss-of-pll-alarm {
                 type string;
                 description
                   "Receiver loss of PLL alarm";
               }
               leaf rx-not-ready-alarm {
                 type string;
                 description
                   "Receiver not ready alarm";
               }
               leaf rx-loss-of-signal-alarm {
                 type string;
                 description
                   "Receiver loss of signal alarm";
               }
               leaf rx-cdr-loss-of-lock-alarm {
                 type string;
                 description
                   "Receiver CDR loss of lock alarm";
               }
               leaf laser-bias-current-high-alarm-threshold {
                 type string;
                 description
                   "Laser bias current high alarm threshold (milliamperes)";
               }
               leaf laser-bias-current-low-alarm-threshold {
                 type string;
                 description
                   "Laser bias current low alarm threshold (milliamperes)";
               }
               leaf laser-bias-current-high-warn-threshold {
                 type string;
                 description
                   "Laser bias current high warning threshold (milliamperes)";
               }
               leaf laser-bias-current-low-warn-threshold {
                 type string;
                 description
                   "Laser bias current low warning threshold (milliamperes)";
               }
               leaf soa-bias-current-high-alarm-threshold {
                 type string;
                 description
                   "SOA bias current high alarm threshold (milliamperes)";
               }
               leaf soa-bias-current-low-alarm-threshold {
                 type string;
                 description
                   "SOA bias current low alarm threshold (milliamperes)";
               }
               leaf soa-bias-current-high-warn-threshold {
                 type string;
                 description
                   "SOA bias current high warning threshold (milliamperes)";
               }
               leaf soa-bias-current-low-warn-threshold {
                 type string;
                 description
                   "SOA bias current low warning threshold (milliamperes)";
               }
               leaf laser-tx-power-high-alarm-threshold {
                 type string;
                 description
                   "Laser transmitter power high alarm threshold 
                   (milliwatts)";
               }
               leaf laser-tx-power-high-alarm-threshold-dbm {
                 type string;
                 description
                   "Laser transmitter power high alarm threshold (dBm)";
               }
               leaf laser-tx-power-low-alarm-threshold {
                 type string;
                 description
                   "Laser transmitter power low alarm threshold (milliwatts)";
               }
               leaf laser-tx-power-low-alarm-threshold-dbm {
                 type string;
                 description
                   "Laser transmitter power low alarm threshold (dBm)";
               }
               leaf laser-tx-power-high-warn-threshold {
                 type string;
                 description
                   "Laser transmitter power high warning threshold 
                   (milliwatts)";
               }
               leaf laser-tx-power-high-warn-threshold-dbm {
                 type string;
                 description
                   "Laser transmitter power high warning threshold (dBm)";
               }
               leaf laser-tx-power-low-warn-threshold {
                 type string;
                 description
                   "Laser transmitter power low warning threshold 
                   (milliwatts)";
               }
               leaf laser-tx-power-low-warn-threshold-dbm {
                 type string;
                 description
                   "Laser transmitter power low warning threshold (dBm)";
               }
               leaf module-temperature-high-alarm-threshold {
                 type string;
                 description
                   "Module temperature high alarm threshold";
               }
               leaf module-temperature-low-alarm-threshold {
                 type string;
                 description
                   "Module temperature low alarm threshold";
               }
               leaf module-temperature-high-warn-threshold {
                 type string;
                 description
                   "Module temperature high warning threshold";
               }
               leaf module-temperature-low-warn-threshold {
                 type string;
                 description
                   "Module temperature low warning threshold";
               }
               leaf laser-temperature-high-alarm-threshold {
                 type string;
                 description
                   "Laser temperature high alarm threshold";
               }
               leaf laser-temperature-low-alarm-threshold {
                 type string;
                 description
                   "Laser temperature low alarm threshold";
               }
               leaf laser-temperature-high-warn-threshold {
                 type string;
                 description
                   "Laser temperature high warning threshold";
               }
               leaf laser-temperature-low-warn-threshold {
                 type string;
                 description
                   "Laser temperature low warning threshold";
               }
               leaf module-voltage-high-alarm-threshold {
                 type string;
                 description
                   "Module voltage high alarm threshold (volts)";
               }
               leaf module-voltage-low-alarm-threshold {
                 type string;
                 description
                   "Module voltage low alarm threshold (volts)";
               }
               leaf module-voltage-high-warn-threshold {
                 type string;
                 description
                   "Module voltage high warning threshold (volts)";
               }
               leaf module-voltage-low-warn-threshold {
                 type string;
                 description
                   "Module voltage low warning threshold (volts)";
               }
               leaf laser-rx-power-high-alarm-threshold {
                 type string;
                 description
                   "Laser receiver power high alarm (milliwatts)";
               }
               leaf laser-rx-power-high-alarm-threshold-dbm {
                 type string;
                 description
                   "Laser receiver power high alarm (dBm)";
               }
               leaf laser-rx-power-low-alarm-threshold {
                 type string;
                 description
                   "Laser receiver power low alarm (milliwatts)";
               }
               leaf laser-rx-power-low-alarm-threshold-dbm {
                 type string;
                 description
                   "Laser receiver power low alarm (dBm)";
               }
               leaf laser-rx-power-high-warn-threshold {
                 type string;
                 description
                   "Laser receiver power high warning (milliwatts)";
               }
               leaf laser-rx-power-high-warn-threshold-dbm {
                 type string;
                 description
                   "Laser receiver power high warning (dBm)";
               }
               leaf laser-rx-power-low-warn-threshold {
                 type string;
                 description
                   "Laser receiver power low warning (milliwatts)";
               }
               leaf laser-rx-power-low-warn-threshold-dbm {
                 type string;
                 description
                   "Laser receiver power low warning (dBm)";
               }
               leaf rx-power-high-alarm-threshold {
                 type string;
                 description
                   "Receiver power high alarm (milliwatts)";
               }
               leaf rx-power-high-alarm-threshold-dbm {
                 type string;
                 description
                   "Receiver power high alarm (dBm)";
               }
               leaf rx-power-low-alarm-threshold {
                 type string;
                 description
                   "Receiver power low alarm (milliwatts)";
               }
               leaf rx-power-low-alarm-threshold-dbm {
                 type string;
                 description
                   "Receiver power low alarm (dBm)";
               }
               leaf rx-power-high-warning-threshold {
                 type string;
                 description
                   "Receiver power high warning (milliwatts)";
               }
               leaf rx-power-high-warning-threshold-dbm {
                 type string;
                 description
                   "Receiver power high warning (dBm)";
               }
               leaf rx-power-low-warning-threshold {
                 type string;
                 description
                   "Receiver power low warning (milliwatts)";
               }
               leaf rx-power-low-warning-threshold-dbm {
                 type string;
                 description
                   "Receiver power low warning (dBm)";
               }
               leaf los-alarm-threshold {
                 type string;
                 description
                   "LOS alarm threshold (milliwatts)";
               }
               leaf los-alarm-threshold-dbm {
                 type string;
                 description
                   "LOS alarm threshold (dBm)";
               }
               leaf los-warning-threshold {
                 type string;
                 description
                   "LOS warning threshold (milliwatts)";
               }
               leaf los-warning-threshold-dbm {
                 type string;
                 description
                   "LOS warning threshold (dBm)";
               }
               leaf dsp-module-state {
                 type string;
                 description
                   "DSP module state";
               }
               leaf output-power {
                 type string;
                 description
                   "Output power (milliwatts)";
               }
               leaf output-power-dbm {
                 type string;
                 description
                   "Output power (dBm)";
               }
               leaf input-power {
                 type string;
                 description
                   "Input power (milliwatts)";
               }
               leaf input-power-dbm {
                 type string;
                 description
                   "Input power (dBm)";
               }
               leaf per-wave-rx-optical-power {
                 type string;
                 description
                   "Per-wavelength receiver optical power (milliwatts)";
               }
               leaf per-wave-rx-optical-power-dbm {
                 type string;
                 description
                   "Per-wavelength receiver optical power (dBm)";
               }
               leaf lane-laser-frequency-error {
                 type string;
                 description
                   "Lane laser frequency error (MHz)";
               }
               leaf tec-current {
                 type string;
                 description
                   "Tec current";
               }
               leaf residual-isi {
                 type string;
                 description
                   "Residual ISI";
               }
               container optics-diagnostics-ot {
                 description
                   "OT interface optics diagnostics";
                 leaf module-temp-fault {
                   type string;
                   description
                     "Module temperature fault";
                 }
                 leaf specific-hw-fault {
                   type string;
                   description
                     "Specific HW fault";
                 }
                 leaf internal-power-fault {
                   type string;
                   description
                     "Internal power fault";
                 }
                 leaf post-therm-fault {
                   type string;
                   description
                     "Power thermal fault";
                 }
                 leaf post-fault {
                   type string;
                   description
                     "Post fault";
                 }
                 leaf command-error {
                   type string;
                   description
                     "Command error";
                 }
                 leaf rx-pll-lock {
                   type string;
                   description
                     "RX PLL lock";
                 }
                 leaf network-lane-los {
                   type string;
                   description
                     "Network Lane LOS";
                 }
                 leaf network-lane-lof {
                   type string;
                   description
                     "Network Lane LOF";
                 }
                 leaf network-lane-oof {
                   type string;
                   description
                     "Network Lane OOF";
                 }
                 leaf network-lane-lom {
                   type string;
                   description
                     "Network Lane LOM";
                 }
                 leaf network-lane-oom {
                   type string;
                   description
                     "Network Lane OOM";
                 }
                 leaf network-lane-otu-bdi {
                   type string;
                   description
                     "Network Lane OTU BDI";
                 }
                 leaf lane-rx-fifo-error {
                   type string;
                   description
                     "Lane RX FIFO error";
                 }
                 leaf tx-reference-clock-fault {
                   type string;
                   description
                     "TX reference clock fault";
                 }
                 leaf rx-modem-sync-fault {
                   type string;
                   description
                     "Rx modem sync fault";
                 }
                 leaf rx-modem-loss-of-lock {
                   type string;
                   description
                     "RX modem loss of lock";
                 }
                 leaf rx-loss-of-alignment {
                   type string;
                   description
                     "RX loss of alignment";
                 }
                 leaf rx-out-of-alignment {
                   type string;
                   description
                     "RX out of alignment";
                 }
                 leaf rx-timing-fault {
                   type string;
                   description
                     "Rx timing fault";
                 }
                 leaf link-msg-data-available {
                   type string;
                   description
                     "Link msg data available";
                 }
                 leaf modulator-bias-control-loop-fail {
                   type string;
                   description
                     "Modulator Bias Control Loop Fail";
                 }
                 leaf itla-fault {
                   type string;
                   description
                     "ITLA fault";
                 }
                 leaf dac-calib-fault {
                   type string;
                   description
                     "DAC calib fault";
                 }
                 leaf adc-calib-fault {
                   type string;
                   description
                     "ADC calib fault";
                 }
                 leaf prom-fault {
                   type string;
                   description
                     "PROM fault";
                 }
                 leaf tx-mod-bias-voa-ctrl-loop-high-alarm {
                   type string;
                   description
                     "TX mod bias VOA ctrl loop high alarm";
                 }
                 leaf tx-mod-bias-voa-ctrl-loop-low-alarm {
                   type string;
                   description
                     "TX mod bias VOA ctrl loop low alarm";
                 }
                 leaf rx-phase-control-loop-high-alarm {
                   type string;
                   description
                     "RX phase control loop high alarm";
                 }
                 leaf rx-phase-control-loop-low-alarm {
                   type string;
                   description
                     "RX phase control loop low alarm";
                 }
                 leaf rx-phase-control-loop-high-warning {
                   type string;
                   description
                     "RX phase control loop high warning";
                 }
                 leaf rx-phase-control-loop-low-warning {
                   type string;
                   description
                     "RX phase control loop low warning";
                 }
                 leaf oa-pump-bias-current-high-alarm {
                   type string;
                   description
                     "OA pump bias current high alarm";
                 }
                 leaf oa-pump-bias-current-low-alarm {
                   type string;
                   description
                     "OA pump bias current low alarm";
                 }
                 leaf oa-pump-bias-current-high-warning {
                   type string;
                   description
                     "OA pump bias current high warning";
                 }
                 leaf oa-pump-bias-current-low-warning {
                   type string;
                   description
                     "OA pump bias current low warning";
                 }
                 leaf tx-jitter-pll-lol-input-nw-lane {
                   type string;
                   description
                     "Tx jitter PLL LOL i/p nw lane";
                 }
                 leaf tx-out-of-alignment {
                   type string;
                   description
                     "TX out of alignment";
                 }
                 leaf tx-cmu-lock-fault {
                   type string;
                   description
                     "Tx CMU lock fault";
                 }
                 leaf adc-signal-below-threshold {
                   type string;
                   description
                     "ADC signal below threshold";
                 }
                 leaf tx-output-power-adjustment-fault {
                   type string;
                   description
                     "Tx output power adjustment fault";
                 }
                 leaf tx-output-mod-converge-fault {
                   type string;
                   description
                     "TX output mod converge fault";
                 }
                 leaf tx-laser-ready-fault {
                   type string;
                   description
                     "Tx laser ready fault";
                 }
                 leaf tx-laser-ready-off-fault {
                   type string;
                   description
                     "Tx laser ready off fault";
                 }
                 leaf tx-asic-ready-fault {
                   type string;
                   description
                     "Tx asic ready fault";
                 }
                 leaf tx-initialization-fault {
                   type string;
                   description
                     "Tx initialization fault";
                 }
                 leaf rx-demodulator-lock-fault {
                   type string;
                   description
                     "Rx demodulator lock fault";
                 }
                 leaf rx-dispersion-lock-fault {
                   type string;
                   description
                     "Rx dispersion lock fault";
                 }
                 leaf rx-adc-output-fault {
                   type string;
                   description
                     "Rx ADC output fault";
                 }
                 leaf rx-optical-input-fault {
                   type string;
                   description
                     "Rx optical input fault";
                 }
                 leaf rx-asic-ready-fault {
                   type string;
                   description
                     "Rx asic ready fault";
                 }
                 leaf rx-initialization-fault {
                   type string;
                   description
                     "Rx initialization fault";
                 }
                 leaf tx-mod-bias-high-alarm {
                   type string;
                   description
                     "TX modulator bias high alarm";
                 }
                 leaf tx-mod-bias-low-alarm {
                   type string;
                   description
                     "TX modulator bias low alarm";
                 }
                 leaf tx-mod-bias-high-warning {
                   type string;
                   description
                     "TX modulator bias high warning";
                 }
                 leaf tx-mod-bias-low-warning {
                   type string;
                   description
                     "TX modulator bias low warning";
                 }
                 leaf rx-pwr-high-alarm {
                   type string;
                   description
                     "RX power high alarm";
                 }
                 leaf rx-pwr-low-alarm {
                   type string;
                   description
                     "RX power low alarm";
                 }
                 leaf rx-pwr-high-warn {
                   type string;
                   description
                     "RX power high warning";
                 }
                 leaf rx-pwr-low-warn {
                   type string;
                   description
                     "RX power low warning";
                 }
                 leaf tx-laser-power-high-alarm {
                   type string;
                   description
                     "TX laser power high alarm";
                 }
                 leaf tx-laser-power-low-alarm {
                   type string;
                   description
                     "TX laser power low alarm";
                 }
                 leaf tx-laser-power-high-warn {
                   type string;
                   description
                     "TX laser power high warning";
                 }
                 leaf tx-laser-power-low-warn {
                   type string;
                   description
                     "TX laser power low warning";
                 }
                 leaf tx-bias-high-alarm {
                   type string;
                   description
                     "TX laser current high alarm";
                 }
                 leaf tx-bias-low-alarm {
                   type string;
                   description
                     "TX laser current low alarm";
                 }
                 leaf tx-bias-high-warn {
                   type string;
                   description
                     "TX laser current high warning";
                 }
                 leaf tx-bias-low-warn {
                   type string;
                   description
                     "TX laser current low warning";
                 }
                 leaf tx-laser-temp-high-alarm {
                   type string;
                   description
                     "TX laser temperature high alarm";
                 }
                 leaf tx-laser-temp-low-alarm {
                   type string;
                   description
                     "TX laser temperature low alarm";
                 }
                 leaf tx-laser-temp-high-warn {
                   type string;
                   description
                     "TX laser temperature high warning";
                 }
                 leaf tx-laser-temp-low-warn {
                   type string;
                   description
                     "TX laser temperature low warning";
                 }
               }
             }
             list optics-diagnostics-vendor-extension {
               description
                 "Optics diagnostics vendor extension";
               leaf optics-vendor-part-number {
                 type string;
                 description
                   "Optics component vendor part number";
               }
               leaf optics-vendor-material-number {
                 type string;
                 description
                   "Optic component vendor material number";
               }
             }
           }
         }
         container peer-configuration-status {
           description
             "Nonmatching DCE end DLCIs";
           leaf peer-nonmatching-dlci {
             type int32;
             description
               "DCE end DLCIs that does not match the DTE";
           }
         }
         container lsi-traffic-statistics {
           leaf input-bytes {
             type int32;
           }
           leaf input-bps {
             type int32;
           }
           leaf input-packets {
             type int32;
           }
           leaf input-pps {
             type int32;
           }
         }
         container stp-traffic-statistics {
           leaf stp-input-bytes-dropped {
             type int32;
             description
               "Drop statistics due to stp state at ingress in bytes";
           }
           leaf stp-output-bytes-dropped {
             type int32;
             description
               "Drop statistics due to stp state at egress in bytes";
           }
           leaf stp-input-packets-dropped {
             type int32;
             description
               "Drop statistics due to stp state at ingress in packets";
           }
           leaf stp-output-packets-dropped {
             type int32;
             description
               "Drop statistics due to stp state at egress in packets";
           }
         }
         container af-fe-info {
         }
         container af-fe-q-pkts {
         }
         container af-fe-q-bytes {
         }
         container chassis-queue-counters {
           description
             "Chassis queue counter statistics";
           container interface-chassis-cos-summary {
             description
               "Packet Forwarding Engine chassis forwarding class and queue 
               information for an interface";
             leaf intf-cos-chassis-num-queues-supported {
               type int32;
               description
                 "Number of Packet Forwarding Engine chassis queues the 
                 interface supports";
             }
             leaf intf-cos-chassis-num-queues-in-use {
               type int32;
               description
                 "Number of Packet Forwarding Engine chassis queues in use 
                 on the interface";
             }
           }
           list queue {
             description
               "Counters for a single queue";
             leaf queue-number {
               type int32;
               description
                 "Queue number";
             }
             leaf forwarding-class-name {
               type string;
               description
                 "Forwarding class name associated with queue";
             }
             leaf queue-counters-queued-packets {
               type uint64;
               description
                 "Queued packet count";
             }
             leaf queue-counters-queued-packets-rate {
               type uint64;
               description
                 "Rate at which packets are queued";
             }
             leaf queue-counters-queued-bytes {
               type uint64;
               description
                 "Queued bytes count";
             }
             leaf queue-counters-queued-bytes-rate {
               type uint64;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets {
               type uint64;
               description
                 "Total number of transmitted packets";
             }
             leaf queue-counters-trans-packets-rate {
               type uint64;
               description
                 "Rate at which packets are transmitted";
             }
             leaf queue-counters-trans-bytes {
               type uint64;
               description
                 "Total number of transmitted bytes";
             }
             leaf queue-counters-trans-bytes-rate {
               type uint64;
               description
                 "Rate at which bytes are transmitted";
             }
             leaf queue-counters-tail-drop-packets-na {
               type string;
               description
                 "Number of packets dropped due to tail drop not available";
             }
             leaf queue-counters-tail-drop-packets {
               type uint64;
               description
                 "Number of packets dropped at the tail of the queue";
             }
             leaf queue-counters-tail-drop-packets-rate {
               type uint64;
               description
                 "Rate at which packets are dropped at tail of queue";
             }
             leaf queue-counters-tail-drop-bytes {
               type uint64;
               description
                 "Number of packets dropped at tail drop of the queue";
             }
             leaf queue-counters-tail-drop-bytes-rate {
               type uint64;
               description
                 "Number of packets dropped at tail drop of the queue";
             }
             leaf queue-counters-rate-limit-drop-packets-na {
               type string;
               description
                 "Number of packets dropped due to rate-limit drop not 
                 available";
             }
             leaf queue-counters-rate-limit-drop-packets {
               type uint64;
               description
                 "Number of packets dropped by rate-limit for the queue";
             }
             leaf queue-counters-rate-limit-drop-packets-rate {
               type uint64;
               description
                 "Rate at which packets are dropped by rate-limit for the 
                 queue";
             }
             leaf queue-counters-rate-limit-drop-bytes-na {
               type string;
               description
                 "Number of bytes dropped due to tail drop not available";
             }
             leaf queue-counters-rate-limit-drop-bytes {
               type uint64;
               description
                 "Number of bytes dropped at the tail of the queue";
             }
             leaf queue-counters-rate-limit-drop-bytes-rate {
               type uint64;
               description
                 "Rate at which bytes are dropped at the tail of the queue";
             }
             leaf queue-counters-red-packets-na {
               type string;
               description
                 "Number of packets dropped due to RED not available";
             }
             leaf queue-counters-red-packets {
               type uint64;
               description
                 "Number of packets dropped due to RED";
             }
             leaf queue-counters-red-packets-rate {
               type uint64;
               description
                 "Rate at which packets are dropped due to RED";
             }
             leaf queue-counters-red-packets-ln {
               type uint64;
               description
                 "Number of RED dropped low-loss, non-TCP packets";
             }
             leaf queue-counters-red-packets-rate-ln {
               type uint64;
               description
                 "RED drop rate for low-loss, non-TCP packets";
             }
             leaf queue-counters-red-packets-lt {
               type uint64;
               description
                 "Number of RED dropped of low-loss, TCP packets";
             }
             leaf queue-counters-red-packets-rate-lt {
               type uint64;
               description
                 "RED drop rate for low-loss, TCP packets";
             }
             leaf queue-counters-red-packets-hn {
               type uint64;
               description
                 "Number of RED dropped high-loss, non-TCP packets";
             }
             leaf queue-counters-red-packets-rate-hn {
               type uint64;
               description
                 "RED drop rate for high-loss, non-TCP packets";
             }
             leaf queue-counters-red-packets-ht {
               type uint64;
               description
                 "Number of RED dropped high-loss, TCP packets";
             }
             leaf queue-counters-red-packets-rate-ht {
               type uint64;
               description
                 "RED drop rate for high-loss, TCP packets";
             }
             leaf queue-counters-red-packets-low {
               type uint64;
               description
                 "Number of RED dropped low-loss packets";
             }
             leaf queue-counters-red-packets-rate-low {
               type uint64;
               description
                 "RED drop rate for low-loss packets";
             }
             leaf queue-counters-red-packets-medium-low {
               type uint64;
               description
                 "Number of RED dropped medium-low-loss packets";
             }
             leaf queue-counters-red-packets-rate-medium-low {
               type uint64;
               description
                 "RED drop rate for medium-low-loss packets";
             }
             leaf queue-counters-red-packets-medium-high {
               type uint64;
               description
                 "Number of RED dropped medium-high-loss packets";
             }
             leaf queue-counters-red-packets-rate-medium-high {
               type uint64;
               description
                 "RED drop rate for medium-high-loss packets";
             }
             leaf queue-counters-red-packets-medium {
               type uint64;
               description
                 "Number of RED dropped medium-loss packets";
             }
             leaf queue-counters-red-packets-rate-medium {
               type uint64;
               description
                 "RED drop rate for medium-loss packets";
             }
             leaf queue-counters-red-packets-high {
               type uint64;
               description
                 "Number of RED dropped high-loss packets";
             }
             leaf queue-counters-red-packets-rate-high {
               type uint64;
               description
                 "RED drop rate for high-loss packets";
             }
             leaf queue-counters-red-bytes-na {
               type string;
               description
                 "Number of bytes dropped due to RED not available";
             }
             leaf queue-counters-red-bytes {
               type uint64;
               description
                 "Number of bytes dropped due to RED";
             }
             leaf queue-counters-red-bytes-rate {
               type uint64;
               description
                 "Rate at which bytes are dropped due to RED";
             }
             leaf queue-counters-red-bytes-ln {
               type uint64;
               description
                 "Number of RED dropped low-loss, non-TCP bytes";
             }
             leaf queue-counters-red-bytes-rate-ln {
               type uint64;
               description
                 "RED drop rate for low-loss, non-TCP bytes";
             }
             leaf queue-counters-red-bytes-lt {
               type uint64;
               description
                 "Number of RED dropped low-loss, TCP bytes";
             }
             leaf queue-counters-red-bytes-rate-lt {
               type uint64;
               description
                 "RED drop rate for low-loss, TCP bytes";
             }
             leaf queue-counters-red-bytes-hn {
               type uint64;
               description
                 "Number of RED dropped high-loss, non-TCP bytes";
             }
             leaf queue-counters-red-bytes-rate-hn {
               type uint64;
               description
                 "RED drop rate for high-loss, non-TCP bytes";
             }
             leaf queue-counters-red-bytes-ht {
               type uint64;
               description
                 "Number of RED dropped high-loss, TCP bytes";
             }
             leaf queue-counters-red-bytes-rate-ht {
               type uint64;
               description
                 "RED drop rate for high-loss, TCP bytes";
             }
             leaf queue-counters-red-bytes-low {
               type uint64;
               description
                 "Number of RED dropped low-loss bytes";
             }
             leaf queue-counters-red-bytes-rate-low {
               type uint64;
               description
                 "RED drop rate for low-loss bytes";
             }
             leaf queue-counters-red-bytes-medium-low {
               type uint64;
               description
                 "Number of RED dropped medium-low-loss bytes";
             }
             leaf queue-counters-red-bytes-rate-medium-low {
               type uint64;
               description
                 "RED drop rate for medium-low-loss bytes";
             }
             leaf queue-counters-red-bytes-medium-high {
               type uint64;
               description
                 "Number of RED dropped medium-high-loss bytes";
             }
             leaf queue-counters-red-bytes-rate-medium-high {
               type uint64;
               description
                 "RED drop rate for medium-high-loss bytes";
             }
             leaf queue-counters-red-bytes-medium {
               type uint64;
               description
                 "Number of RED dropped medium-loss bytes";
             }
             leaf queue-counters-red-bytes-rate-medium {
               type uint64;
               description
                 "RED drop rate for medium-loss bytes";
             }
             leaf queue-counters-red-bytes-high {
               type uint64;
               description
                 "Number of RED dropped high-loss bytes";
             }
             leaf queue-counters-red-bytes-rate-high {
               type uint64;
               description
                 "RED drop rate for high-loss bytes";
             }
             leaf queue-counters-timestamp {
               type uint64;
               description
                 "Last packet enqueued timestamp";
             }
             leaf queue-counters-total-drop-packets {
               type uint64;
               description
                 "Number of total packets dropped at the queue";
             }
             leaf queue-counters-total-drop-packets-rate {
               type uint64;
               description
                 "Number of total packets dropped at the queue";
             }
             leaf queue-counters-total-drop-bytes {
               type uint64;
               description
                 "Number of total packets dropped at the queue";
             }
             leaf queue-counters-total-drop-bytes-rate {
               type uint64;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
         }
         container ingress-queue-counters {
           description
             "Ingress queue counter statistics";
           list queue {
             description
               "Counters for a single queue";
             leaf queue-number {
               type int32;
               description
                 "Queue number";
             }
             leaf forwarding-class-name {
               type string;
               description
                 "Forwarding class name associated with queue";
             }
             leaf queue-counters-queued-packets {
               type uint64;
               description
                 "Queued packet count";
             }
             leaf queue-counters-queued-packets-rate {
               type uint64;
               description
                 "Rate at which packets are queued";
             }
             leaf queue-counters-queued-bytes {
               type uint64;
               description
                 "Queued bytes count";
             }
             leaf queue-counters-queued-bytes-rate {
               type uint64;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets {
               type uint64;
               description
                 "Total number of transmitted packets";
             }
             leaf queue-counters-trans-packets-rate {
               type uint64;
               description
                 "Rate at which packets are transmitted";
             }
             leaf queue-counters-trans-bytes {
               type uint64;
               description
                 "Total number of transmitted bytes";
             }
             leaf queue-counters-trans-bytes-rate {
               type uint64;
               description
                 "Rate at which bytes are transmitted";
             }
             leaf queue-counters-tail-drop-packets-na {
               type string;
               description
                 "Number of packets dropped due to tail drop not available";
             }
             leaf queue-counters-tail-drop-packets {
               type uint64;
               description
                 "Number of packets dropped at the tail of the queue";
             }
             leaf queue-counters-tail-drop-packets-rate {
               type uint64;
               description
                 "Rate at which packets are dropped at tail of queue";
             }
             leaf queue-counters-tail-drop-bytes {
               type uint64;
               description
                 "Number of packets dropped at tail drop of the queue";
             }
             leaf queue-counters-tail-drop-bytes-rate {
               type uint64;
               description
                 "Number of packets dropped at tail drop of the queue";
             }
             leaf queue-counters-rate-limit-drop-packets-na {
               type string;
               description
                 "Number of packets dropped due to rate-limit drop not 
                 available";
             }
             leaf queue-counters-rate-limit-drop-packets {
               type uint64;
               description
                 "Number of packets dropped by rate-limit for the queue";
             }
             leaf queue-counters-rate-limit-drop-packets-rate {
               type uint64;
               description
                 "Rate at which packets are dropped by rate-limit for the 
                 queue";
             }
             leaf queue-counters-rate-limit-drop-bytes-na {
               type string;
               description
                 "Number of bytes dropped due to tail drop not available";
             }
             leaf queue-counters-rate-limit-drop-bytes {
               type uint64;
               description
                 "Number of bytes dropped at the tail of the queue";
             }
             leaf queue-counters-rate-limit-drop-bytes-rate {
               type uint64;
               description
                 "Rate at which bytes are dropped at the tail of the queue";
             }
             leaf queue-counters-red-packets-na {
               type string;
               description
                 "Number of packets dropped due to RED not available";
             }
             leaf queue-counters-red-packets {
               type uint64;
               description
                 "Number of packets dropped due to RED";
             }
             leaf queue-counters-red-packets-rate {
               type uint64;
               description
                 "Rate at which packets are dropped due to RED";
             }
             leaf queue-counters-red-packets-ln {
               type uint64;
               description
                 "Number of RED dropped low-loss, non-TCP packets";
             }
             leaf queue-counters-red-packets-rate-ln {
               type uint64;
               description
                 "RED drop rate for low-loss, non-TCP packets";
             }
             leaf queue-counters-red-packets-lt {
               type uint64;
               description
                 "Number of RED dropped of low-loss, TCP packets";
             }
             leaf queue-counters-red-packets-rate-lt {
               type uint64;
               description
                 "RED drop rate for low-loss, TCP packets";
             }
             leaf queue-counters-red-packets-hn {
               type uint64;
               description
                 "Number of RED dropped high-loss, non-TCP packets";
             }
             leaf queue-counters-red-packets-rate-hn {
               type uint64;
               description
                 "RED drop rate for high-loss, non-TCP packets";
             }
             leaf queue-counters-red-packets-ht {
               type uint64;
               description
                 "Number of RED dropped high-loss, TCP packets";
             }
             leaf queue-counters-red-packets-rate-ht {
               type uint64;
               description
                 "RED drop rate for high-loss, TCP packets";
             }
             leaf queue-counters-red-packets-low {
               type uint64;
               description
                 "Number of RED dropped low-loss packets";
             }
             leaf queue-counters-red-packets-rate-low {
               type uint64;
               description
                 "RED drop rate for low-loss packets";
             }
             leaf queue-counters-red-packets-medium-low {
               type uint64;
               description
                 "Number of RED dropped medium-low-loss packets";
             }
             leaf queue-counters-red-packets-rate-medium-low {
               type uint64;
               description
                 "RED drop rate for medium-low-loss packets";
             }
             leaf queue-counters-red-packets-medium-high {
               type uint64;
               description
                 "Number of RED dropped medium-high-loss packets";
             }
             leaf queue-counters-red-packets-rate-medium-high {
               type uint64;
               description
                 "RED drop rate for medium-high-loss packets";
             }
             leaf queue-counters-red-packets-medium {
               type uint64;
               description
                 "Number of RED dropped medium-loss packets";
             }
             leaf queue-counters-red-packets-rate-medium {
               type uint64;
               description
                 "RED drop rate for medium-loss packets";
             }
             leaf queue-counters-red-packets-high {
               type uint64;
               description
                 "Number of RED dropped high-loss packets";
             }
             leaf queue-counters-red-packets-rate-high {
               type uint64;
               description
                 "RED drop rate for high-loss packets";
             }
             leaf queue-counters-red-bytes-na {
               type string;
               description
                 "Number of bytes dropped due to RED not available";
             }
             leaf queue-counters-red-bytes {
               type uint64;
               description
                 "Number of bytes dropped due to RED";
             }
             leaf queue-counters-red-bytes-rate {
               type uint64;
               description
                 "Rate at which bytes are dropped due to RED";
             }
             leaf queue-counters-red-bytes-ln {
               type uint64;
               description
                 "Number of RED dropped low-loss, non-TCP bytes";
             }
             leaf queue-counters-red-bytes-rate-ln {
               type uint64;
               description
                 "RED drop rate for low-loss, non-TCP bytes";
             }
             leaf queue-counters-red-bytes-lt {
               type uint64;
               description
                 "Number of RED dropped low-loss, TCP bytes";
             }
             leaf queue-counters-red-bytes-rate-lt {
               type uint64;
               description
                 "RED drop rate for low-loss, TCP bytes";
             }
             leaf queue-counters-red-bytes-hn {
               type uint64;
               description
                 "Number of RED dropped high-loss, non-TCP bytes";
             }
             leaf queue-counters-red-bytes-rate-hn {
               type uint64;
               description
                 "RED drop rate for high-loss, non-TCP bytes";
             }
             leaf queue-counters-red-bytes-ht {
               type uint64;
               description
                 "Number of RED dropped high-loss, TCP bytes";
             }
             leaf queue-counters-red-bytes-rate-ht {
               type uint64;
               description
                 "RED drop rate for high-loss, TCP bytes";
             }
             leaf queue-counters-red-bytes-low {
               type uint64;
               description
                 "Number of RED dropped low-loss bytes";
             }
             leaf queue-counters-red-bytes-rate-low {
               type uint64;
               description
                 "RED drop rate for low-loss bytes";
             }
             leaf queue-counters-red-bytes-medium-low {
               type uint64;
               description
                 "Number of RED dropped medium-low-loss bytes";
             }
             leaf queue-counters-red-bytes-rate-medium-low {
               type uint64;
               description
                 "RED drop rate for medium-low-loss bytes";
             }
             leaf queue-counters-red-bytes-medium-high {
               type uint64;
               description
                 "Number of RED dropped medium-high-loss bytes";
             }
             leaf queue-counters-red-bytes-rate-medium-high {
               type uint64;
               description
                 "RED drop rate for medium-high-loss bytes";
             }
             leaf queue-counters-red-bytes-medium {
               type uint64;
               description
                 "Number of RED dropped medium-loss bytes";
             }
             leaf queue-counters-red-bytes-rate-medium {
               type uint64;
               description
                 "RED drop rate for medium-loss bytes";
             }
             leaf queue-counters-red-bytes-high {
               type uint64;
               description
                 "Number of RED dropped high-loss bytes";
             }
             leaf queue-counters-red-bytes-rate-high {
               type uint64;
               description
                 "RED drop rate for high-loss bytes";
             }
             leaf queue-counters-timestamp {
               type uint64;
               description
                 "Last packet enqueued timestamp";
             }
             leaf queue-counters-total-drop-packets {
               type uint64;
               description
                 "Number of total packets dropped at the queue";
             }
             leaf queue-counters-total-drop-packets-rate {
               type uint64;
               description
                 "Number of total packets dropped at the queue";
             }
             leaf queue-counters-total-drop-bytes {
               type uint64;
               description
                 "Number of total packets dropped at the queue";
             }
             leaf queue-counters-total-drop-bytes-rate {
               type uint64;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
           container interface-cos-short-summary {
             description
               "Summary of queue information on an interface";
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           container queue-num-forwarding-class-name-map {
             leaf queue-number {
               type int32;
               description
                 "Queue number";
             }
             leaf forwarding-class-name {
               type string;
               description
                 "Forwarding class name associated with queue";
             }
           }
         }
         container otn-oc-information {
           list media-alarm {
             leaf media-alarm-name {
               type string;
             }
             leaf media-alarm-seconds {
               type int32;
             }
             leaf media-alarm-count {
               type int32;
             }
             leaf media-alarm-state {
               type string;
             }
           }
         }
         container otn-otu-information {
           list media-alarm {
             leaf media-alarm-name {
               type string;
             }
             leaf media-alarm-seconds {
               type int32;
             }
             leaf media-alarm-count {
               type int32;
             }
             leaf media-alarm-state {
               type string;
             }
           }
         }
         container otn-odu-information {
           list media-alarm {
             leaf media-alarm-name {
               type string;
             }
             leaf media-alarm-seconds {
               type int32;
             }
             leaf media-alarm-count {
               type int32;
             }
             leaf media-alarm-state {
               type string;
             }
           }
         }
         container otn-ot-module-information {
           list media-alarm {
             leaf media-alarm-name {
               type string;
             }
             leaf media-alarm-seconds {
               type int32;
             }
             leaf media-alarm-count {
               type int32;
             }
             leaf media-alarm-state {
               type string;
             }
           }
         }
         list otn-odu-tcm-information {
           list media-alarm {
             leaf media-alarm-name {
               type string;
             }
             leaf media-alarm-seconds {
               type int32;
             }
             leaf media-alarm-count {
               type int32;
             }
             leaf media-alarm-state {
               type string;
             }
           }
         }
         container ima-group-information {
           description
             "IMA group alarms";
         }
         container ima-link-information {
           description
             "IMA link alarms";
         }
         container ethernet-mac-pfc-statistics {
           description
             "Ethernet MAC Priority Flow control Statistics";
           leaf mac-pfc-dot1p {
             type int32;
           }
           leaf input-mac-pfc-frames {
             type int32;
           }
           leaf output-mac-pfc-frames {
             type int32;
           }
         }
         container cos-information {
           description
             "Information about class-of-service configuration";
           list cos-stream-information {
             description
               "Information about the traffic stream";
           }
           container cos-forwarding-class-information {
             container fc-map {
               description
                 "Class-of-service forwarding class to queue mapping";
               list fc-map-item {
                 leaf fc-name {
                   type string;
                   description
                     "Class-of-service forwarding class name";
                 }
                 leaf fc-number {
                   type uint32;
                   description
                     "Identifier for Class-of-service forwarding class";
                 }
                 leaf fc-queue-number {
                   type uint32;
                   description
                     "Class-of-service forwarding class queue number";
                 }
                 leaf fc-rqueue-number {
                   type uint32;
                   description
                     "Class-of-service forwarding class restricted queue 
                     number";
                 }
                 leaf fc-priority {
                   type string;
                   description
                     "Class-of-service forwarding class queue priority";
                 }
                 leaf fc-policing-priority {
                   type string;
                   description
                     "Class-of-service forwarding class policing priority";
                 }
                 leaf fc-spu-priority {
                   type string;
                   description
                     "Class-of-service forwarding class spu priority";
                 }
                 leaf fc-no-loss {
                   type string;
                   description
                     "Class-of-service forwarding class no-loss";
                 }
                 leaf fc-pfc-priority {
                   type string;
                   description
                     "Class-of-service forwarding class pfc-priority";
                 }
                 leaf fc-multicast {
                   type string;
                   description
                     "Class-of-service forwarding class multicast";
                 }
                 leaf fc-latency-ecn {
                   type string;
                   description
                     "Class-of-service forwarding class latency ECN";
                 }
               }
             }
           }
           container cos-forwarding-class-map-information {
             container fc-map {
               description
                 "Class-of-service forwarding class to queue mapping";
               list fc-map-item {
                 leaf fc-name {
                   type string;
                   description
                     "Class-of-service forwarding class name";
                 }
                 leaf fc-number {
                   type uint32;
                   description
                     "Identifier for Class-of-service forwarding class";
                 }
                 leaf fc-queue-number {
                   type uint32;
                   description
                     "Class-of-service forwarding class queue number";
                 }
                 leaf fc-rqueue-number {
                   type uint32;
                   description
                     "Class-of-service forwarding class restricted queue 
                     number";
                 }
                 leaf fc-priority {
                   type string;
                   description
                     "Class-of-service forwarding class queue priority";
                 }
                 leaf fc-policing-priority {
                   type string;
                   description
                     "Class-of-service forwarding class policing priority";
                 }
                 leaf fc-spu-priority {
                   type string;
                   description
                     "Class-of-service forwarding class spu priority";
                 }
                 leaf fc-no-loss {
                   type string;
                   description
                     "Class-of-service forwarding class no-loss";
                 }
                 leaf fc-pfc-priority {
                   type string;
                   description
                     "Class-of-service forwarding class pfc-priority";
                 }
                 leaf fc-multicast {
                   type string;
                   description
                     "Class-of-service forwarding class multicast";
                 }
                 leaf fc-latency-ecn {
                   type string;
                   description
                     "Class-of-service forwarding class latency ECN";
                 }
               }
             }
           }
           container cos-classifier-information {
             list classifier {
               description
                 "Class-of-service code point classifier";
               leaf classifier-name {
                 type string;
                 description
                   "Class-of-service classifier name";
               }
               leaf code-point-type {
                 type string;
                 description
                   "Class-of-service code point type";
               }
               leaf table-index {
                 type uint32;
                 description
                   "Table index";
               }
               container classifier-map {
                 list classifier-map-item {
                   leaf code-point {
                     type string;
                     description
                       "Class-of-service code point alias name or bits";
                   }
                   leaf fc-name {
                     type string;
                     description
                       "Class-of-service forwarding class name";
                   }
                   leaf loss-priority {
                     type string;
                     description
                       "Class-of-service loss priority";
                   }
                   leaf cntag-present {
                     type string;
                     description
                       "Class-of-service cntag present";
                   }
                 }
               }
             }
           }
           container cos-loss-priority-map-information {
             list loss-priority-map {
               description
                 "Class-of-service code point loss priority map";
               leaf loss-priority-map-name {
                 type string;
                 description
                   "Name of class-of-service loss priority map";
               }
               leaf code-point-type {
                 type string;
                 description
                   "Class-of-service code point type";
               }
               leaf table-index {
                 type uint32;
                 description
                   "Table index";
               }
               list loss-priority-map-table {
                 list loss-priority-map-item {
                   leaf code-point {
                     type string;
                     description
                       "Class-of-service code point alias name or bits";
                   }
                   leaf loss-priority {
                     type string;
                     description
                       "Class-of-service loss priority";
                   }
                 }
                 list loss-priority-map-table-entry {
                   leaf table-index {
                     type uint32;
                     description
                       "Table index";
                   }
                   leaf code-point {
                     type string;
                     description
                       "Class-of-service code point alias name or bits";
                   }
                   leaf loss-priority {
                     type string;
                     description
                       "Class-of-service loss priority";
                   }
                 }
               }
             }
           }
           container cos-drop-profile-information {
             list drop-profile {
               description
                 "Class-of-service drop profile";
               leaf profile-name {
                 type string;
                 description
                   "Class-of-service drop profile name";
               }
               leaf profile-type {
                 type string;
                 description
                   "Class-of-service drop profile type";
               }
               leaf table-index {
                 type uint32;
                 description
                   "Table index";
               }
               container profile-map {
                 list profile-map-item {
                   leaf fill-level {
                     type uint32;
                     description
                       "Class-of-service drop profile fill level value";
                   }
                   leaf probability {
                     type uint32;
                     description
                       "Class-of-service drop profile probability value";
                   }
                 }
               }
             }
           }
           container cos-mpls-ecn-map-information {
             list cos-mpls-ecn-map-info {
               description
                 "Class-of-service mpls-ecn-map information";
               leaf ecn-capable-exp {
                 type int32;
                 description
                   "ECN capable exp";
               }
               leaf congestion-experienced-exp {
                 type int32;
                 description
                   "Congestion Expereienced exp";
               }
             }
           }
           container cos-monitoring-profile-information {
             list monitoring-profile {
               description
                 "Class-of-service monitoring profile";
               leaf monitoring-profile-name {
                 type string;
                 description
                   "Class-of-service monitoring profile name";
               }
               container export-filters {
                 container export-filter {
                   leaf filter-name {
                     type string;
                     description
                       "Class-of-service monitoring profile filter name";
                   }
                   leaf monitoring-queue-number {
                     type uint32;
                     description
                       "Class-of-service monitoring profile filter queue 
                       value";
                   }
                   leaf peak-queue-length-value {
                     type uint32;
                     description
                       "Class-of-service monitoring profile peak queue 
                       length value";
                   }
                 }
               }
             }
           }
           container cos-rewrite-information {
             list rewrite {
               description
                 "Class-of-service drop profile";
               leaf rewrite-name {
                 type string;
                 description
                   "Class-of-service rewrite rule name";
               }
               leaf code-point-type {
                 type string;
                 description
                   "Class-of-service code point type";
               }
               leaf table-index {
                 type uint32;
                 description
                   "Table index";
               }
               container rewrite-map {
                 list rewrite-map-item {
                   leaf fc-name {
                     type string;
                     description
                       "Class-of-service forwarding class name";
                   }
                   leaf loss-priority {
                     type string;
                     description
                       "Class-of-service loss priority";
                   }
                   leaf code-point {
                     type string;
                     description
                       "Class-of-service code point alias name or bits";
                   }
                 }
               }
             }
           }
           container cos-loss-priority-rewrite-information {
             list loss-priority-rewrite {
               description
                 "Class-of-service loss priority to code point rewrite";
               leaf loss-priority-rewrite-name {
                 type string;
                 description
                   "Name of class-of-service loss priority rewrite";
               }
               leaf code-point-type {
                 type string;
                 description
                   "Class-of-service code point type";
               }
               leaf table-index {
                 type uint32;
                 description
                   "Table index";
               }
               list loss-priority-rewrite-table {
                 list loss-priority-rewrite-item {
                   leaf loss-priority {
                     type string;
                     description
                       "Class-of-service loss priority";
                   }
                   leaf code-point {
                     type string;
                     description
                       "Class-of-service code point alias name or bits";
                   }
                 }
                 list loss-priority-rewrite-table-entry {
                   leaf table-index {
                     type uint32;
                     description
                       "Table index";
                   }
                   leaf loss-priority {
                     type string;
                     description
                       "Class-of-service loss priority";
                   }
                   leaf code-point {
                     type string;
                     description
                       "Class-of-service code point alias name or bits";
                   }
                 }
               }
             }
           }
           container cos-code-point-map-information {
             list code-point-map {
               description
                 "Class-of-service code point alias map";
               leaf code-point-type {
                 type string;
                 description
                   "Class-of-service code point type";
               }
               container alias-map {
                 list alias-map-item {
                   leaf code-point-alias {
                     type string;
                     description
                       "Class-of-service code point alias name";
                   }
                   leaf code-point-bits {
                     type string;
                     description
                       "Class-of-service code point bit sequence";
                   }
                 }
               }
             }
           }
           container cos-fragmentation-map-information {
             list fragmentation-map {
               description
                 "Class-of-service fragmentation map";
               leaf fragmentation-map-name {
                 type string;
                 description
                   "Class-of-service fragmentation map name";
               }
               leaf fragmentation-map-index {
                 type uint32;
                 description
                   "Index number for Class-of-service fragmentation map";
               }
               list fragment-map {
                 leaf fc-name {
                   type string;
                   description
                     "Class-of-service forwarding class name";
                 }
                 leaf no-fragmentation {
                   type empty;
                   description
                     "Do not fragment packets of this class";
                 }
                 leaf fragment-threshold {
                   type string;
                   description
                     "Fragmentation threshold";
                 }
                 leaf fragment-multilink-class {
                   type int32;
                   description
                     "Identifier for multilink class";
                 }
               }
             }
           }
           container cos-translation-table-map-information {
             list translation-table {
               description
                 "Class-of-service code point translation table";
               leaf translation-table-name {
                 type string;
                 description
                   "Class-of-service translation table name";
               }
               leaf translation-table-type {
                 type string;
                 description
                   "Class-of-service translation table type";
               }
               leaf table-index {
                 type uint32;
                 description
                   "Table index";
               }
               container translation-table-map {
                 container translation-table-map-item {
                   leaf from-code-point {
                     type string;
                     description
                       "Class-of-service code point alias name or bits";
                   }
                   leaf to-code-point {
                     type string;
                     description
                       "Class-of-service code point alias name or bits";
                   }
                 }
               }
               list translation-table-entry {
                 leaf table-index {
                   type uint32;
                   description
                     "Table index";
                 }
                 leaf from-code-point {
                   type string;
                   description
                     "Class-of-service code point alias name or bits";
                 }
                 leaf to-code-point {
                   type string;
                   description
                     "Class-of-service code point alias name or bits";
                 }
               }
             }
           }
           container cos-multi-destination-information {
             container sm-md-map {
               leaf scheduler-map-name {
                 type string;
                 description
                   "Class-of-service scheduler map name";
               }
               leaf scheduler-map-index {
                 type uint64;
                 description
                   "Class-of-service scheduler map index";
               }
             }
             container fc-md-map {
               leaf fc-name {
                 type string;
                 description
                   "Class-of-service forwarding class name";
               }
               leaf fc-queue-number {
                 type uint32;
                 description
                   "Class-of-service forwarding class queue number";
               }
             }
             container cls-md-map {
               leaf multidest-classifier-name {
                 type string;
                 description
                   "Multi destination classifier name";
               }
               leaf multidest-classifier-type {
                 type string;
                 description
                   "Multi destination classifier type";
               }
               leaf multidest-classifier-index {
                 type uint32;
                 description
                   "Multi destination classifier id";
               }
             }
           }
           container cos-forwarding-class-set-information {
             list forwarding-class-set {
               description
                 "Class-of-service forwarding class set information";
               list forwarding-class-set-entry {
                 leaf forwarding-class-set-name {
                   type string;
                   description
                     "Class-of-service forwarding class set name";
                 }
                 leaf forwarding-class-set-type {
                   type string;
                   description
                     "Identifier for Class-of-service forwarding class set 
                     type";
                 }
                 leaf forwarding-class-set-index {
                   type uint32;
                   description
                     "Identifier for Class-of-service forwarding class set";
                 }
                 container fc-map {
                   description
                     "Class-of-service forwarding class to queue mapping";
                   list fc-map-item {
                     leaf fc-name {
                       type string;
                       description
                         "Class-of-service forwarding class name";
                     }
                     leaf fc-number {
                       type uint32;
                       description
                         "Identifier for Class-of-service forwarding class";
                     }
                     leaf fc-queue-number {
                       type uint32;
                       description
                         "Class-of-service forwarding class queue number";
                     }
                     leaf fc-rqueue-number {
                       type uint32;
                       description
                         "Class-of-service forwarding class restricted queue
                         number";
                     }
                     leaf fc-priority {
                       type string;
                       description
                         "Class-of-service forwarding class queue priority";
                     }
                     leaf fc-policing-priority {
                       type string;
                       description
                         "Class-of-service forwarding class policing 
                         priority";
                     }
                     leaf fc-spu-priority {
                       type string;
                       description
                         "Class-of-service forwarding class spu priority";
                     }
                     leaf fc-no-loss {
                       type string;
                       description
                         "Class-of-service forwarding class no-loss";
                     }
                     leaf fc-pfc-priority {
                       type string;
                       description
                         "Class-of-service forwarding class pfc-priority";
                     }
                     leaf fc-multicast {
                       type string;
                       description
                         "Class-of-service forwarding class multicast";
                     }
                     leaf fc-latency-ecn {
                       type string;
                       description
                         "Class-of-service forwarding class latency ECN";
                     }
                   }
                 }
               }
             }
           }
           container cos-policy-map-information {
             list policy-map {
               description
                 "Class-of-service Policy-map";
               leaf policy-map-name {
                 type string;
                 description
                   "Class-of-service Policy-map name";
               }
               leaf table-index {
                 type uint32;
                 description
                   "Table index";
               }
               leaf policy-map-user-attribute {
                 type uint32;
                 description
                   "User-defined attribute";
               }
               container policy-map-cp-entries {
                 leaf code-point-type {
                   type string;
                   description
                     "Class-of-service code point type";
                 }
                 leaf code-point {
                   type string;
                   description
                     "Class-of-service code point alias name or bits";
                 }
                 leaf code-point-option {
                   type string;
                   description
                     "Class-of-service code point option flag";
                 }
               }
             }
           }
           container cos-client-info {
             list cos-client {
               description
                 "Class-of-service Junos client information";
               leaf cos-client-info-internal-id {
                 type uint32;
                 description
                   "Junos client internal identifier";
               }
               leaf cos-client-info-requests {
                 type uint32;
                 description
                   "Number of requests from Junos client";
               }
               leaf cos-client-info-responses {
                 type uint32;
                 description
                   "Number of responses to Junos client";
               }
               leaf cos-client-info-failures {
                 type uint32;
                 description
                   "Number of failures while handling Junos client requests";
               }
               leaf cos-client-info-identifier {
                 type string;
                 description
                   "Junos client identifier";
               }
               leaf cos-client-name {
                 type string;
                 description
                   "Junos client name";
               }
               leaf cos-client-state {
                 type string;
                 description
                   "Junos client state information";
               }
               leaf cos-client-internal-name {
                 type string;
                 description
                   "Junos client internal name";
               }
               leaf cos-client-stats {
                 type string;
                 description
                   "Junos client statistics";
               }
               leaf cos-client-failure-stats {
                 type string;
                 description
                   "Junos client failure/error statistics";
               }
               leaf cos-client-validate-failures {
                 type uint32;
                 description
                   "Junos client request validation failures";
               }
               leaf cos-client-ownership-failures {
                 type uint32;
                 description
                   "Junos client ownership validation failures";
               }
               leaf cos-client-info-name {
                 type string;
                 description
                   "CoS client name";
               }
               leaf cos-client-internal-id {
                 type uint32;
                 description
                   "Junos client internal identifier";
               }
               leaf cos-client-requests {
                 type uint64;
                 description
                   "Number of requests from Junos client";
               }
               leaf cos-client-responses {
                 type uint64;
                 description
                   "Number of responses to Junos client";
               }
               leaf cos-client-failures {
                 type uint64;
                 description
                   "Number of failures while handling Junos client requests";
               }
               leaf cos-client-identifier {
                 type string;
                 description
                   "Junos client identifier";
               }
               leaf cos-client-status {
                 type string;
                 description
                   "Junos client status";
               }
               leaf cos-client-connected-time {
                 type string;
                 description
                   "Junos client time of connect";
               }
               leaf cos-client-reconnected-time {
                 type string;
                 description
                   "Junos client time of reconnect";
               }
               leaf cos-client-disconnected-time {
                 type string;
                 description
                   "Junos client time of disconnect";
               }
               leaf cos-client-message-type {
                 type string;
                 description
                   "Junos client message type";
               }
               leaf cos-client-operation-type {
                 type string;
                 description
                   "Junos client operation type";
               }
               leaf-list cos-bind-point-type {
                 type string;
                 description
                   "Class-of-service bind point type";
               }
               leaf-list cos-bind-point-owner-type {
                 type string;
                 description
                   "Class-of-service bind point owner type";
               }
               leaf-list cos-bind-point-owner-internal-id {
                 type uint32;
                 description
                   "Junos client internal identifier";
               }
               leaf-list cos-bind-point-name {
                 type string;
                 description
                   "Class-of-service bind point name";
               }
               leaf cos-bind-point-feature {
                 type string;
                 description
                   "Class-of-service bind point feature name";
               }
               leaf cos-bind-point-feature-object-name {
                 type string;
                 description
                   "Class-of-service bind point feature object name";
               }
             }
           }
           container cos-host-outbound-info {
             list cos-host-outbound-traffic-info {
               description
                 "Class-of-service host-outbound-traffic information";
               leaf cos-host-outbound-traffic-protocol-name {
                 type string;
                 description
                   "CoS host outbound traffic protocol name";
               }
               leaf cos-host-outbound-traffic-dscp {
                 type string;
                 description
                   "CoS host outbound traffic dscp";
               }
               leaf cos-host-outbound-traffic-dot1p {
                 type string;
                 description
                   "CoS host outbound traffic ieee 802.1p";
               }
               leaf cos-host-outbound-traffic-fc-id {
                 type string;
                 description
                   "CoS host outbound traffic forwarding class id";
               }
               leaf cos-host-outbound-traffic-queue-id {
                 type string;
                 description
                   "CoS host outbound traffic queue id";
               }
               leaf cos-host-outbound-traffic-restrict-queue-id {
                 type string;
                 description
                   "CoS host outbound traffic restrict queue id";
               }
               leaf cos-host-outbound-traffic-override-firewall {
                 type string;
                 description
                   "CoS host outbound traffic override firwall action";
               }
               leaf cos-host-outbound-traffic-rw-dot1p {
                 type string;
                 description
                   "CoS host outbound traffic - use ieee 802.1p rewrite 
                   rules";
               }
             }
           }
           container cos-drop-congestion-notification-information {
             list cos-drop-congestion-notification-info {
               description
                 "Class-of-service drop-congestion-notification information";
               leaf cos-dcn-fc-name {
                 type string;
                 description
                   "Cos DCN forwarding class";
               }
               leaf cos-dcn-udp-port {
                 type int32;
                 description
                   "Cos DCN udp port number";
               }
             }
             container cos-drop-congestion-notification-dscp-map {
               list cos-drop-congestion-notification-dscp-map-item {
                 leaf trimmable-dscp {
                   type uint32;
                   description
                     "Trimmable DSCP code-point";
                 }
                 leaf trimmed-dscp {
                   type uint32;
                   description
                     "Trimmed DSCP code-point";
                 }
               }
             }
           }
           container cos-dedicated-buffer-profile-information {
             list dedicated-buffer-profile {
               description
                 "Class-of-service dedicated buffer profile";
               leaf dedicated-buffer-profile-name {
                 type string;
                 description
                   "Class-of-service dedicated buffer profile name";
               }
               leaf dedicated-buffer-profile-index {
                 type int32;
                 description
                   "Class-of-service dedicated buffer profile index";
               }
               leaf ingress-buffer-size {
                 type string;
                 description
                   "Ingress per port dedicated buffer in cells";
               }
               leaf egress-buffer-size {
                 type string;
                 description
                   "Egress per port dedicated buffer in cells";
               }
             }
           }
           container cos-dynamic-threshold-profile-information {
             list dynamic-threshold-profile {
               key "dynamic-threshold-profile-name";
               description
                 "Class-of-service dynamic threshold profile";
               leaf dynamic-threshold-profile-name {
                 type string;
                 description
                   "Class-of-service dynamic threshold profile name";
               }
               leaf dynamic-threshold-profile-index {
                 type uint64;
                 description
                   "Class-of-service dynamic threshold profile index";
               }
               list dynamic-threshold-profile-entry {
                 key "dynamic-threshold-profile-priority-group";
                 description
                   "Class-of-service dynamic threshold profile entry";
                 leaf dynamic-threshold-profile-priority-group {
                   type string;
                   description
                     "Class-of-service dynamic threshold profile priority 
                     group";
                 }
                 leaf dynamic-threshold-profile-threshold-value {
                   type uint32;
                   description
                     "Class-of-service dynamic threshold profile threshold 
                     value";
                 }
               }
             }
           }
           container cos-decn-profile-information {
             list decn-profile {
               description
                 "Class-of-service decn profile";
               leaf decn-profile-name {
                 type string;
                 description
                   "Class-of-service decn profile name";
               }
               leaf decn-profile-index {
                 type uint64;
                 description
                   "Class-of-service decn profile index";
               }
               list decn-profile-queue {
                 description
                   "Class-of-service decn profile queue";
                 leaf dynamic-explicit-congestion-notification-queue {
                   type uint32;
                   description
                     "Class-of-service DECN queue";
                 }
                 leaf dynamic-explicit-congestion-notification-offset {
                   type uint32;
                   description
                     "Class-of-service DECN offset";
                 }
                 leaf dynamic-explicit-congestion-notification-floor {
                   type uint32;
                   description
                     "Class-of-service DECN floor";
                 }
               }
             }
           }
           container cos-scheduler-map-information {
             list scheduler-map {
               description
                 "Class-of-service scheduler map";
               leaf scheduler-map-name {
                 type string;
                 description
                   "Class-of-service scheduler map name";
               }
               leaf scheduler-map-index {
                 type uint64;
                 description
                   "Class-of-service scheduler map index";
               }
               leaf user-plane-name {
                 type string;
                 description
                   "Class-of-service user-plane name for XDA";
               }
               list scheduler {
                 leaf scheduler-name {
                   type string;
                   description
                     "Class-of-service scheduler name";
                 }
                 leaf fc-name {
                   type string;
                   description
                     "Class-of-service forwarding class name";
                 }
                 leaf scheduler-index {
                   type uint64;
                   description
                     "Class of service scheduler index";
                 }
                 leaf scheduler-tx-rate {
                   type string;
                   description
                     "Class-of-service scheduler transmit rate";
                 }
                 leaf scheduler-tx-limit {
                   type string;
                   description
                     "Class-of-service scheduler transmit limit";
                 }
                 leaf scheduler-buffer-size {
                   type string;
                   description
                     "Class-of-service scheduler buffer size";
                 }
                 leaf scheduler-buffer-multicast-share {
                   type uint32;
                   description
                     "Class-of-service scheduler multicast buffer share";
                 }
                 leaf scheduler-buffer-limit {
                   type string;
                   description
                     "Class-of-service scheduler buffer limit";
                 }
                 leaf scheduler-buffer-rate {
                   type string;
                   description
                     "Class-of-service scheduler buffer rate";
                 }
                 leaf scheduler-shared-buffer-maximum-percentage {
                   type uint32;
                   description
                     "Shared Buffer maximum percentage";
                 }
                 leaf scheduler-shared-buffer-multicast-maximum-percentage {
                   type uint32;
                   description
                     "Shared Buffer multicast maximum percentage";
                 }
                 leaf scheduler-buffer-dynamic-threshold {
                   type uint32;
                   description
                     "Queue shared-buffer dynamic threshold";
                 }
                 leaf scheduler-priority {
                   type string;
                   description
                     "Class-of-service scheduler priority";
                 }
                 leaf scheduler-shaping-rate {
                   type string;
                   description
                     "Class-of-service scheduler shaping rate";
                 }
                 leaf scheduler-shaping-rate-burst {
                   type string;
                   description
                     "Class-of-service scheduler shaping rate burst";
                 }
                 leaf scheduler-adjust-minimum {
                   type int32;
                   description
                     "Class-of-service scheduler adjustment minimum rate";
                 }
                 leaf scheduler-adjust-percent {
                   type int32;
                   description
                     "Class-of-service scheduler percent adjustment for a 
                     queue";
                 }
                 leaf scheduler-excess-priority {
                   type string;
                   description
                     "Class-of-service scheduler excess priority";
                 }
                 leaf scheduler-excess-rate {
                   type string;
                   description
                     "Class-of-service scheduler excess rate";
                 }
                 leaf scheduler-explicit-congestion-notification {
                   type string;
                   description
                     "Class-of-service ECN status of queue";
                 }
                 leaf scheduler-ecn-rtlog-rate-limit {
                   type uint32;
                   description
                     "Class-of-service ECN Security Log Rate Limit";
                 }
                 leaf scheduler-ecn-no-pfc-assist {
                   type string;
                   description
                     "Class-of-service ECN no pfc assist";
                 }
                 leaf scheduler-latency-ecn {
                   type string;
                   description
                     "Latency based ECN";
                 }
                 leaf scheduler-latency-ecn-threshold {
                   type uint32;
                   description
                     "Latency threshold";
                 }
                 leaf scheduler-queue-monitoring {
                   type string;
                   description
                     "Class-of-service queue depth monitoring of queue";
                 }
                 leaf scheduler-drop-profile-ln-index {
                   type uint32;
                   description
                     "Class-of-service scheduler drop profile index low, 
                     non-TCP";
                 }
                 leaf scheduler-drop-profile-ln {
                   type string;
                   description
                     "Class-of-service scheduler drop profile low, non-TCP";
                 }
                 leaf scheduler-drop-profile-lt-index {
                   type uint32;
                   description
                     "Class-of-service scheduler drop profile index low, TCP";
                 }
                 leaf scheduler-drop-profile-lt {
                   type string;
                   description
                     "Class-of-service scheduler drop profile low, TCP";
                 }
                 leaf scheduler-drop-profile-hn-index {
                   type uint32;
                   description
                     "Class-of-service scheduler drop profile index high, 
                     non-TCP";
                 }
                 leaf scheduler-drop-profile-hn {
                   type string;
                   description
                     "Class-of-service scheduler drop profile high, non-TCP";
                 }
                 leaf scheduler-drop-profile-ht-index {
                   type uint32;
                   description
                     "Class-of-service scheduler drop profile index high, 
                     TCP";
                 }
                 leaf scheduler-drop-profile-ht {
                   type string;
                   description
                     "Class-of-service scheduler drop profile high, TCP";
                 }
                 leaf scheduler-drop-profile-la-index {
                   type uint32;
                   description
                     "Class-of-service scheduler drop profile index low";
                 }
                 leaf scheduler-drop-profile-la {
                   type string;
                   description
                     "Class-of-service scheduler drop profile low";
                 }
                 leaf scheduler-drop-profile-ma-index {
                   type uint32;
                   description
                     "Class-of-service scheduler drop profile index medium";
                 }
                 leaf scheduler-drop-profile-ma {
                   type string;
                   description
                     "Class-of-service scheduler drop profile medium";
                 }
                 leaf scheduler-drop-profile-mla-index {
                   type uint32;
                   description
                     "Class-of-service scheduler drop profile index 
                     medium-low";
                 }
                 leaf scheduler-drop-profile-mla {
                   type string;
                   description
                     "Class-of-service scheduler drop profile medium-low";
                 }
                 leaf scheduler-drop-profile-mha-index {
                   type uint32;
                   description
                     "Class-of-service scheduler drop profile index 
                     medium-high";
                 }
                 leaf scheduler-drop-profile-mha {
                   type string;
                   description
                     "Class-of-service scheduler drop profile medium-high";
                 }
                 leaf scheduler-drop-profile-ha-index {
                   type uint32;
                   description
                     "Class-of-service scheduler drop profile index high";
                 }
                 leaf scheduler-drop-profile-ha {
                   type string;
                   description
                     "Class-of-service scheduler drop profile high";
                 }
               }
             }
           }
           container cos-traffic-control-profile-information {
             list traffic-control-profile {
               description
                 "Information about one or more traffic control profiles";
               leaf traffic-control-profile-name {
                 type string;
                 description
                   "Class-of-service traffic control profile name";
               }
               leaf traffic-control-profile-index {
                 type uint64;
                 description
                   "Index number for Class-of-service traffic control 
                   profile";
               }
               leaf user-plane-name {
                 type string;
                 description
                   "Class-of-service user-plane name for XDA";
               }
               leaf scheduler-map-name {
                 type string;
                 description
                   "Class-of-service scheduler map name";
               }
               leaf atm-service {
                 type string;
                 description
                   "Class-of-service traffic control profile atm service";
               }
               leaf shaping-rate {
                 type uint64;
                 description
                   "Class-of-service shaping rate";
               }
               leaf shaping-rate-burst {
                 type uint32;
                 description
                   "Class-of-service shaping rate burst, in bytes";
               }
               leaf low-granularity {
                 type uint32;
                 description
                   "Class-of-service low-granularity mode support";
               }
               leaf queue-mode-4q {
                 type uint32;
                 description
                   "Class-of-service tcp-voq-mode(4Q) mode support";
               }
               leaf shaping-rate-priority-strict-high {
                 type uint64;
                 description
                   "Class-of-service shaping rate for priority strict high";
               }
               leaf shaping-rate-priority-strict-high-burst {
                 type uint32;
                 description
                   "Class-of-service shaping rate burst for priority 
                   strict-high";
               }
               leaf shaping-rate-priority-high {
                 type uint64;
                 description
                   "Class-of-service shaping rate for priority high";
               }
               leaf shaping-rate-priority-high-burst {
                 type uint32;
                 description
                   "Class-of-service shaping rate for priority high burst";
               }
               leaf shaping-rate-priority-medium {
                 type uint64;
                 description
                   "Class-of-service shaping rate for priority medium";
               }
               leaf shaping-rate-priority-medium-burst {
                 type uint32;
                 description
                   "Class-of-service shaping rate for priority medium burst";
               }
               leaf shaping-rate-priority-medium-low {
                 type uint64;
                 description
                   "Class-of-service shaping rate for priority medium-low";
               }
               leaf shaping-rate-priority-medium-low-burst {
                 type uint32;
                 description
                   "Class-of-service shaping rate burst for priority 
                   medium-low";
               }
               leaf shaping-rate-priority-low {
                 type uint64;
                 description
                   "Class-of-service shaping rate for priority low";
               }
               leaf shaping-rate-priority-low-burst {
                 type uint32;
                 description
                   "Class-of-service shaping rate for priority low burst";
               }
               leaf shaping-rate-excess-high {
                 type uint64;
                 description
                   "Class-of-service shaping rate for excess high";
               }
               leaf shaping-rate-excess-high-burst {
                 type uint32;
                 description
                   "Class-of-service shaping rate for excess high burst";
               }
               leaf shaping-rate-excess-medium-high {
                 type uint64;
                 description
                   "Class-of-service shaping rate for excess medium-high";
               }
               leaf shaping-rate-excess-medium-high-burst {
                 type uint32;
                 description
                   "Class-of-service shaping rate burst for excess 
                   medium-high";
               }
               leaf shaping-rate-excess-medium-low {
                 type uint64;
                 description
                   "Class-of-service shaping rate for excess medium-low";
               }
               leaf shaping-rate-excess-medium-low-burst {
                 type uint32;
                 description
                   "Class-of-service shaping rate burst for excess 
                   medium-low";
               }
               leaf shaping-rate-excess-low {
                 type uint64;
                 description
                   "Class-of-service shaping rate for excess low";
               }
               leaf shaping-rate-excess-low-burst {
                 type uint32;
                 description
                   "Class-of-service shaping rate for excess low burst";
               }
               leaf guaranteed-rate {
                 type uint64;
                 description
                   "Class-of-service guaranteed rate";
               }
               leaf guaranteed-rate-burst {
                 type uint32;
                 description
                   "Class-of-service guaranteed rate burst, in bytes";
               }
               leaf delay-buffer-rate {
                 type uint64;
                 description
                   "Class-of-service delay buffer rate";
               }
               leaf excess-rate {
                 type uint32;
                 description
                   "Class-of-service excess rate";
               }
               leaf excess-rate-high {
                 type uint32;
                 description
                   "Class-of-service excess rate for excess-high priority 
                   traffic";
               }
               leaf excess-rate-medium-high {
                 type uint32;
                 description
                   "Class-of-service excess rate for excess-medium-high 
                   priority traffic";
               }
               leaf excess-rate-medium-low {
                 type uint32;
                 description
                   "Class-of-service excess rate for excess-medium-low 
                   priority traffic";
               }
               leaf excess-rate-low {
                 type uint32;
                 description
                   "Class-of-service excess rate for excess-low priority 
                   traffic";
               }
               leaf adjust-minimum {
                 type uint64;
                 description
                   "Class-of-service adjustment minimum rate";
               }
               leaf overhead-bytes {
                 type int32;
                 description
                   "Class-of-service Overhead bytes";
               }
               leaf frame-mode-bytes {
                 type int32;
                 description
                   "Class-of-service overhead bytes when in frame-mode";
               }
               leaf cell-mode-bytes {
                 type int32;
                 description
                   "Class-of-service overhead bytes when in cell-mode";
               }
               leaf overhead-accounting-mode {
                 type string;
                 description
                   "Class-of-service Overhead Accounting Mode";
               }
               list traffic-control-profile-instance {
                 description
                   "Class-of-service traffic control profile instance";
                 leaf traffic-control-profile-instance-name {
                   type string;
                   description
                     "Class-of-service traffic control profile instance";
                 }
                 leaf traffic-control-profile-instance-index {
                   type uint32;
                   description
                     "Index number for Class-of-service traffic control 
                     profile instance";
                 }
                 leaf instance-reference-count {
                   type uint32;
                   description
                     "Instance reference count";
                 }
               }
             }
           }
           container cos-routing-instance-information {
             list routing-instance-map {
               description
                 "Mapping between class-of-service objects and routing 
                 instances";
               leaf routing-instance-name {
                 type string;
                 description
                   "Name of class-of-service routing instance";
               }
               list i-logical-map {
                 leaf i-logical-name {
                   type string;
                   description
                     "Class-of-service logical interface name";
                 }
                 leaf i-logical-index {
                   type uint32;
                   description
                     "Class-of-service logical interface index";
                 }
                 leaf monitoring-profile-map-name {
                   type string;
                   description
                     "Monitoring Profile Name";
                 }
                 list cos-objects {
                   description
                     "Class-of-service object  mappings";
                   leaf cos-object-type {
                     type string;
                     description
                       "Class-of-service object type";
                   }
                   leaf cos-object-name {
                     type string;
                     description
                       "Class-of-service object name";
                   }
                   leaf cos-object-subtype {
                     type string;
                     description
                       "Class-of-service object subtype";
                   }
                   leaf cos-object-index {
                     type uint64;
                     description
                       "Class-of-service object index";
                   }
                 }
               }
             }
           }
           container cos-fabric-scheduler-map-information {
             container fabric-scheduler-map {
               list fabric-scheduler {
                 leaf fabric-scheduler-name {
                   type string;
                   description
                     "Class-of-service scheduler name";
                 }
                 leaf fabric-scheduler-index {
                   type uint32;
                   description
                     "Class of service scheduler index";
                 }
                 leaf fabric-scheduler-drop-profile-ln-index {
                   type uint32;
                   description
                     "Class-of-service scheduler drop profile index low, 
                     non-TCP";
                 }
                 leaf fabric-scheduler-drop-profile-ln {
                   type string;
                   description
                     "Class-of-service scheduler drop profile low, non-TCP";
                 }
                 leaf fabric-scheduler-drop-profile-lt-index {
                   type uint32;
                   description
                     "Class-of-service scheduler drop profile index low, TCP";
                 }
                 leaf fabric-scheduler-drop-profile-lt {
                   type string;
                   description
                     "Class-of-service scheduler drop profile low, TCP";
                 }
                 leaf fabric-scheduler-drop-profile-hn-index {
                   type uint32;
                   description
                     "Class-of-service scheduler drop profile index high, 
                     non-TCP";
                 }
                 leaf fabric-scheduler-drop-profile-hn {
                   type string;
                   description
                     "Class-of-service scheduler drop profile high, non-TCP";
                 }
                 leaf fabric-scheduler-drop-profile-ht-index {
                   type uint32;
                   description
                     "Class-of-service scheduler drop profile index high, 
                     TCP";
                 }
                 leaf fabric-scheduler-drop-profile-ht {
                   type string;
                   description
                     "Class-of-service scheduler drop profile high, TCP";
                 }
                 leaf fabric-scheduler-priority {
                   type string;
                 }
               }
             }
           }
           container cos-tcm-information {
             list tcm {
               description
                 "Class-of-service traffic-class-map";
               leaf tcm-name {
                 type string;
                 description
                   "Class-of-service traffic-class-map name";
               }
               leaf tcm-type {
                 type string;
                 description
                   "Class-of-service traffic-class-map type";
               }
               leaf table-index {
                 type uint32;
                 description
                   "Table index";
               }
               container tcm-map {
                 list tcm-map-item {
                   leaf code-point {
                     type string;
                     description
                       "Class-of-service code point alias name or bits";
                   }
                   leaf tc-name {
                     type string;
                     description
                       "Class-of-service traffic-class-map traffic-class 
                       name";
                   }
                 }
               }
             }
           }
           container cos-lecn-profile-information {
             list lecn-profile {
               description
                 "Class-of-service lecn profile";
               leaf lecn-profile-name {
                 type string;
                 description
                   "Class-of-service lecn profile name";
               }
               leaf lecn-profile-index {
                 type uint64;
                 description
                   "Class-of-service lecn profile index";
               }
               list lecn-profile-queue {
                 description
                   "Class-of-service lecn profile queue";
                 leaf latency-explicit-congestion-notification-queue {
                   type uint32;
                   description
                     "Class-of-service LECN queue";
                 }
                 leaf latency-explicit-congestion-notification-latency {
                   type uint32;
                   description
                     "Class-of-service LECN latency";
                 }
               }
             }
           }
         }
         container physical-interface-cos-information {
           description
             "Physical interface class-of-service parameters";
         }
         container precl-statistics {
           description
             "Preclassifier Statistics ";
           container precl-information {
             description
               "Preclassifier Statistics";
           }
         }
         container mlfr-uni-nni-traffic-statistics {
           container bundle {
           }
         }
       }
       list logical-interface {
         key "name";
         description
           "Information about a single logical interface";
         leaf name {
           type string;
           description
             "Name of this item";
         }
         leaf admin-status {
           type string;
           description
             "Desired state of the interface";
         }
         leaf oper-status {
           type string;
           description
             "Current operational state of the interface";
         }
         leaf vrfname {
           type string;
           description
             "Routing instance name";
         }
         leaf zonename {
           type string;
           description
             "Zone name";
         }
         leaf subunit {
           type int32;
           description
             "Subunit for this interface";
         }
         leaf dialer-time-to-disconnect {
           type string;
           description
             "Time for dialer to disconnect due to idle timeout";
         }
         leaf lcp-state {
           type string;
           description
             "State of the Line Control Protocol";
         }
         leaf chap-state {
           type string;
           description
             "State of the Challenge Handshake Authentication Protocol";
         }
         leaf pap-state {
           type string;
           description
             "State of the Password Authentication Protocol";
         }
         container pppoe-information {
           description
             "PPPoE information";
           list pppoe-interface {
             leaf state {
               type string;
               description
                 "State";
             }
             leaf session-id {
               type string;
               description
                 "Session ID";
             }
             leaf ac-name-session {
               type string;
               description
                 "Session AC name";
             }
             leaf remote-mac {
               type string;
               description
                 "Remote MAC address";
             }
             leaf ac-name-config {
               type string;
               description
                 "Configured AC name";
             }
             leaf service-name {
               type string;
               description
                 "Service name";
             }
             leaf auto-reconnect {
               type string;
               description
                 "Autoreconnect timeout";
             }
             leaf idle-timeout {
               type string;
               description
                 "Idle timeout";
             }
             leaf underlying-interface-name {
               type string;
               description
                 "Underlying interface name";
             }
             leaf underlying-interface-index {
               type string;
               description
                 "Underlying interface index";
             }
             leaf padg-credits {
               type int32;
               description
                 "PADG transmit credits";
             }
             leaf pppoe-credit-scale-factor {
               type string;
               description
                 "Scaling factor";
             }
             leaf ignore-eol-tag {
               type string;
               description
                 "Ignore End-of-List TAG";
             }
             leaf ppp-max-payload-tag {
               type int32;
               description
                 "PPP-Max-Payload TAG";
             }
             leaf interface-name {
               type string;
               description
                 "Class-of-service interface name";
             }
             leaf interface-index {
               type uint32;
               description
                 "Class-of-service interface index";
             }
             leaf aci-iflset-name {
               type string;
               description
                 "ACI Interface Set name";
             }
             leaf aci-iflset-index {
               type string;
               description
                 "ACI Interface Set index";
             }
             leaf ifl-type {
               type string;
               description
                 "Type";
             }
             leaf session-uptime {
               type string;
               description
                 "Duration for which the session has been up";
             }
             leaf dynamic-profile {
               type string;
               description
                 "Dynamic Profile name";
             }
             leaf pppoe-credits {
               type string;
               description
                 "Forwarding credit balances";
             }
             leaf dynamic-interface-bandwidth {
               type string;
               description
                 "Dynamic interface bandwidth";
             }
             leaf agent-circuit-id {
               type string;
               description
                 "Agent Circuit ID";
             }
             leaf agent-remote-id {
               type string;
               description
                 "Agent Remote ID";
             }
             leaf padm-motm {
               type string;
               description
                 "PADM Message of the Moment tag";
             }
             leaf padm-hurl {
               type string;
               description
                 "PADM HTTP URL tag";
             }
           }
         }
         container pppoe-underlying-information {
           description
             "PPPoE Underlying information";
           list pppoe-underlying-interface {
             leaf dynamic-profile {
               type string;
               description
                 "Dynamic Profile name";
             }
             leaf service-name-table {
               type string;
               description
                 "Name of Service Name Table";
             }
             leaf max-sessions {
               type int32;
               description
                 "Maximum number of PPPoE sessions";
             }
             leaf max-sessions-vsa-ignore {
               type string;
               description
                 "Ignore max-sessions VSA";
             }
             leaf duplicate-protection {
               type string;
               description
                 "Duplicate protection mode";
             }
             leaf short-cycle-protection {
               type string;
               description
                 "Short cycle protection mode";
             }
             leaf direct-connect {
               type string;
               description
                 "Direct connect mode";
             }
             leaf ac-name {
               type string;
               description
                 "Access Concentrator name";
             }
             leaf underlying-interface-name {
               type string;
               description
                 "Underlying interface name";
             }
             leaf underlying-interface-index {
               type string;
               description
                 "Underlying interface index";
             }
             leaf encapsulation-type-identifier {
               type string;
               description
                 "Encapsulation type identifier";
             }
             leaf state {
               type string;
               description
                 "State";
             }
             leaf active-sessions {
               type int32;
               description
                 "Number of active PPPoE sessions";
             }
             leaf aci-autosensing {
               type string;
               description
                 "ACI VLAN Autosensing mode";
             }
             leaf line-identity-autosensing {
               type string;
               description
                 "Line Identity Autosensing mode";
             }
           }
         }
         container aci-vlan-information {
           leaf dynamic-profile {
             type string;
             description
               "Dynamic Profile name";
           }
         }
         container line-identity-information {
           leaf dynamic-profile {
             type string;
             description
               "Dynamic Profile name";
           }
           leaf circuit-id {
             type string;
             description
               "Aci vlan attribute";
           }
           leaf remote-id {
             type string;
             description
               "Aci vlan attribute";
           }
           leaf accept-no-ids {
             type string;
             description
               "Aci vlan attribute";
           }
         }
         container demux-information {
           description
             "Demux information";
           container demux-interface {
             leaf demux-underlying-interface-name {
               type string;
               description
                 "Underlying interface name";
             }
             leaf demux-underlying-interface-index {
               type string;
               description
                 "Underlying interface index";
             }
             leaf demux-inet-prefix-type {
               type string;
               description
                 "Prefix type";
             }
             leaf demux-inet-prefix-count {
               type string;
               description
                 "IPv4 Prefix count";
             }
             leaf demux-inet-prefix {
               type string;
               description
                 "IPv4 Prefix";
             }
             leaf demux-inet6-prefix-type {
               type string;
               description
                 "Prefix type";
             }
             leaf demux-inet6-prefix-count {
               type string;
               description
                 "IPv6 Prefix count";
             }
             leaf demux-inet6-prefix {
               type string;
               description
                 "IPv6 Prefix";
             }
           }
         }
         container dual-ad-icl-color-information {
           container dual-ad-icl-color-info {
             description
               "Dual-AD ICL Color Information";
             leaf dual-ad-icl-color-type {
               type uint32;
               description
                 "Dual-AD ICL Color Type";
             }
             leaf dual-ad-icl-color {
               type uint32;
               description
                 "Dual-AD ICL Color";
             }
           }
         }
         container dialer-information {
           description
             "Dialer information";
           leaf dialer-time-to-disconnect {
             type string;
             description
               "Time for dialer to disconnect due to idle timeout";
           }
           container dialer-interface {
             leaf dialer-interface-name {
               type string;
               description
                 "Interface name";
             }
             leaf dialer-interface-state {
               type string;
               description
                 "Dialer interface state";
             }
             leaf pool-id {
               type string;
               description
                 "Pool identifier";
             }
             leaf primary-interface {
               type string;
               description
                 "Primary interface";
             }
             leaf activation-delay {
               type string;
               description
                 "Activation delay";
             }
             leaf deactivation-delay {
               type string;
               description
                 "Deactivation delay";
             }
             leaf activation-delay-elapsed {
               type string;
               description
                 "Activation delay elapsed";
             }
             leaf deactivation-delay-elapsed {
               type string;
               description
                 "Deactivation delay elapsed";
             }
             leaf call-idle-timeout {
               type string;
               description
                 "Call idle timeout";
             }
             leaf initial-route-check {
               type string;
               description
                 "Initial route check delay";
             }
             leaf redial-delay {
               type string;
               description
                 "Delay before dialer dials out again (seconds)";
             }
             leaf callback-wait-period {
               type string;
               description
                 "Delay before dialer attempts callback (seconds)";
             }
             leaf callback-wait-period-elapsed {
               type string;
               description
                 "Number of seconds in callback wait period that have 
                 elapsed";
             }
             leaf load-threshold {
               type string;
               description
                 "Load threshold that determines when interfaces are added 
                 to bundle";
             }
             leaf load-interval {
               type string;
               description
                 "Interval over which average load is calculated";
             }
             container dialer-interface-flags {
               description
                 "Flags indicating interface configuration";
               leaf backup {
                 type empty;
                 description
                   "Dialer backup";
               }
               leaf multilink {
                 type empty;
                 description
                   "Dialer multilink";
               }
               leaf watchlist {
                 type empty;
                 description
                   "Dialer watchlist";
               }
               leaf interesting-detected {
                 type empty;
                 description
                   "Interesting packet detected";
               }
             }
           }
         }
         container shared-interface-information {
           description
             "Shared interface information";
           container shared-interface-logical-interface {
             description
               "Shared interface logical interface";
             leaf peer-interface-name {
               type string;
               description
                 "Peer interface name";
             }
             leaf interface-shared-with {
               type string;
               description
                 "Logical interface owner";
             }
             leaf rx-fe {
               type string;
               description
                 "Rx tunnel token forwarding element";
             }
             leaf rx-nhid {
               type string;
               description
                 "Rx tunnel token next hop index";
             }
             leaf tx-fe {
               type string;
               description
                 "Tx tunnel token forwarding element";
             }
             leaf tx-nhid {
               type string;
               description
                 "Tx tunnel token next hop index";
             }
           }
         }
         container mac-database {
         }
         container queue-counters {
           description
             "Queue counter statistics";
           leaf queue-counters-error-message {
             type string;
             description
               "Queue statistics not available for this interface";
           }
           list queue {
             description
               "Counters for a single queue";
             leaf queue-number {
               type int32;
               description
                 "Queue number";
             }
             leaf queue-counters-queued-packets {
               type uint64;
               description
                 "Queued packet count";
             }
             leaf queue-counters-trans-packets {
               type uint64;
               description
                 "Total number of transmitted packets";
             }
             leaf queue-counters-total-drop-packets {
               type uint64;
               description
                 "Number of total packets dropped at the queue";
             }
             leaf forwarding-class-name {
               type string;
               description
                 "Forwarding class name associated with queue";
             }
             leaf queue-counters-queued-packets-rate {
               type uint64;
               description
                 "Rate at which packets are queued";
             }
             leaf queue-counters-queued-bytes {
               type uint64;
               description
                 "Queued bytes count";
             }
             leaf queue-counters-queued-bytes-rate {
               type uint64;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets-rate {
               type uint64;
               description
                 "Rate at which packets are transmitted";
             }
             leaf queue-counters-trans-bytes {
               type uint64;
               description
                 "Total number of transmitted bytes";
             }
             leaf queue-counters-trans-bytes-rate {
               type uint64;
               description
                 "Rate at which bytes are transmitted";
             }
             leaf queue-counters-tail-drop-packets-na {
               type string;
               description
                 "Number of packets dropped due to tail drop not available";
             }
             leaf queue-counters-tail-drop-packets {
               type uint64;
               description
                 "Number of packets dropped at the tail of the queue";
             }
             leaf queue-counters-tail-drop-packets-rate {
               type uint64;
               description
                 "Rate at which packets are dropped at tail of queue";
             }
             leaf queue-counters-tail-drop-bytes {
               type uint64;
               description
                 "Number of packets dropped at tail drop of the queue";
             }
             leaf queue-counters-tail-drop-bytes-rate {
               type uint64;
               description
                 "Number of packets dropped at tail drop of the queue";
             }
             leaf queue-counters-rate-limit-drop-packets-na {
               type string;
               description
                 "Number of packets dropped due to rate-limit drop not 
                 available";
             }
             leaf queue-counters-rate-limit-drop-packets {
               type uint64;
               description
                 "Number of packets dropped by rate-limit for the queue";
             }
             leaf queue-counters-rate-limit-drop-packets-rate {
               type uint64;
               description
                 "Rate at which packets are dropped by rate-limit for the 
                 queue";
             }
             leaf queue-counters-rate-limit-drop-bytes-na {
               type string;
               description
                 "Number of bytes dropped due to tail drop not available";
             }
             leaf queue-counters-rate-limit-drop-bytes {
               type uint64;
               description
                 "Number of bytes dropped at the tail of the queue";
             }
             leaf queue-counters-rate-limit-drop-bytes-rate {
               type uint64;
               description
                 "Rate at which bytes are dropped at the tail of the queue";
             }
             leaf queue-counters-red-packets-na {
               type string;
               description
                 "Number of packets dropped due to RED not available";
             }
             leaf queue-counters-red-packets {
               type uint64;
               description
                 "Number of packets dropped due to RED";
             }
             leaf queue-counters-red-packets-rate {
               type uint64;
               description
                 "Rate at which packets are dropped due to RED";
             }
             leaf queue-counters-red-packets-ln {
               type uint64;
               description
                 "Number of RED dropped low-loss, non-TCP packets";
             }
             leaf queue-counters-red-packets-rate-ln {
               type uint64;
               description
                 "RED drop rate for low-loss, non-TCP packets";
             }
             leaf queue-counters-red-packets-lt {
               type uint64;
               description
                 "Number of RED dropped of low-loss, TCP packets";
             }
             leaf queue-counters-red-packets-rate-lt {
               type uint64;
               description
                 "RED drop rate for low-loss, TCP packets";
             }
             leaf queue-counters-red-packets-hn {
               type uint64;
               description
                 "Number of RED dropped high-loss, non-TCP packets";
             }
             leaf queue-counters-red-packets-rate-hn {
               type uint64;
               description
                 "RED drop rate for high-loss, non-TCP packets";
             }
             leaf queue-counters-red-packets-ht {
               type uint64;
               description
                 "Number of RED dropped high-loss, TCP packets";
             }
             leaf queue-counters-red-packets-rate-ht {
               type uint64;
               description
                 "RED drop rate for high-loss, TCP packets";
             }
             leaf queue-counters-red-packets-low {
               type uint64;
               description
                 "Number of RED dropped low-loss packets";
             }
             leaf queue-counters-red-packets-rate-low {
               type uint64;
               description
                 "RED drop rate for low-loss packets";
             }
             leaf queue-counters-red-packets-medium-low {
               type uint64;
               description
                 "Number of RED dropped medium-low-loss packets";
             }
             leaf queue-counters-red-packets-rate-medium-low {
               type uint64;
               description
                 "RED drop rate for medium-low-loss packets";
             }
             leaf queue-counters-red-packets-medium-high {
               type uint64;
               description
                 "Number of RED dropped medium-high-loss packets";
             }
             leaf queue-counters-red-packets-rate-medium-high {
               type uint64;
               description
                 "RED drop rate for medium-high-loss packets";
             }
             leaf queue-counters-red-packets-medium {
               type uint64;
               description
                 "Number of RED dropped medium-loss packets";
             }
             leaf queue-counters-red-packets-rate-medium {
               type uint64;
               description
                 "RED drop rate for medium-loss packets";
             }
             leaf queue-counters-red-packets-high {
               type uint64;
               description
                 "Number of RED dropped high-loss packets";
             }
             leaf queue-counters-red-packets-rate-high {
               type uint64;
               description
                 "RED drop rate for high-loss packets";
             }
             leaf queue-counters-red-bytes-na {
               type string;
               description
                 "Number of bytes dropped due to RED not available";
             }
             leaf queue-counters-red-bytes {
               type uint64;
               description
                 "Number of bytes dropped due to RED";
             }
             leaf queue-counters-red-bytes-rate {
               type uint64;
               description
                 "Rate at which bytes are dropped due to RED";
             }
             leaf queue-counters-red-bytes-ln {
               type uint64;
               description
                 "Number of RED dropped low-loss, non-TCP bytes";
             }
             leaf queue-counters-red-bytes-rate-ln {
               type uint64;
               description
                 "RED drop rate for low-loss, non-TCP bytes";
             }
             leaf queue-counters-red-bytes-lt {
               type uint64;
               description
                 "Number of RED dropped low-loss, TCP bytes";
             }
             leaf queue-counters-red-bytes-rate-lt {
               type uint64;
               description
                 "RED drop rate for low-loss, TCP bytes";
             }
             leaf queue-counters-red-bytes-hn {
               type uint64;
               description
                 "Number of RED dropped high-loss, non-TCP bytes";
             }
             leaf queue-counters-red-bytes-rate-hn {
               type uint64;
               description
                 "RED drop rate for high-loss, non-TCP bytes";
             }
             leaf queue-counters-red-bytes-ht {
               type uint64;
               description
                 "Number of RED dropped high-loss, TCP bytes";
             }
             leaf queue-counters-red-bytes-rate-ht {
               type uint64;
               description
                 "RED drop rate for high-loss, TCP bytes";
             }
             leaf queue-counters-red-bytes-low {
               type uint64;
               description
                 "Number of RED dropped low-loss bytes";
             }
             leaf queue-counters-red-bytes-rate-low {
               type uint64;
               description
                 "RED drop rate for low-loss bytes";
             }
             leaf queue-counters-red-bytes-medium-low {
               type uint64;
               description
                 "Number of RED dropped medium-low-loss bytes";
             }
             leaf queue-counters-red-bytes-rate-medium-low {
               type uint64;
               description
                 "RED drop rate for medium-low-loss bytes";
             }
             leaf queue-counters-red-bytes-medium-high {
               type uint64;
               description
                 "Number of RED dropped medium-high-loss bytes";
             }
             leaf queue-counters-red-bytes-rate-medium-high {
               type uint64;
               description
                 "RED drop rate for medium-high-loss bytes";
             }
             leaf queue-counters-red-bytes-medium {
               type uint64;
               description
                 "Number of RED dropped medium-loss bytes";
             }
             leaf queue-counters-red-bytes-rate-medium {
               type uint64;
               description
                 "RED drop rate for medium-loss bytes";
             }
             leaf queue-counters-red-bytes-high {
               type uint64;
               description
                 "Number of RED dropped high-loss bytes";
             }
             leaf queue-counters-red-bytes-rate-high {
               type uint64;
               description
                 "RED drop rate for high-loss bytes";
             }
             leaf queue-counters-timestamp {
               type uint64;
               description
                 "Last packet enqueued timestamp";
             }
             leaf queue-counters-total-drop-packets-rate {
               type uint64;
               description
                 "Number of total packets dropped at the queue";
             }
             leaf queue-counters-total-drop-bytes {
               type uint64;
               description
                 "Number of total packets dropped at the queue";
             }
             leaf queue-counters-total-drop-bytes-rate {
               type uint64;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-short-summary {
             description
               "Summary of queue information on an interface";
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
         }
         container ingress-queue-counters {
           description
             "Ingress queue counter statistics";
           list queue {
             description
               "Counters for a single queue";
             leaf queue-number {
               type int32;
               description
                 "Queue number";
             }
             leaf forwarding-class-name {
               type string;
               description
                 "Forwarding class name associated with queue";
             }
             leaf queue-counters-queued-packets {
               type uint64;
               description
                 "Queued packet count";
             }
             leaf queue-counters-queued-packets-rate {
               type uint64;
               description
                 "Rate at which packets are queued";
             }
             leaf queue-counters-queued-bytes {
               type uint64;
               description
                 "Queued bytes count";
             }
             leaf queue-counters-queued-bytes-rate {
               type uint64;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets {
               type uint64;
               description
                 "Total number of transmitted packets";
             }
             leaf queue-counters-trans-packets-rate {
               type uint64;
               description
                 "Rate at which packets are transmitted";
             }
             leaf queue-counters-trans-bytes {
               type uint64;
               description
                 "Total number of transmitted bytes";
             }
             leaf queue-counters-trans-bytes-rate {
               type uint64;
               description
                 "Rate at which bytes are transmitted";
             }
             leaf queue-counters-tail-drop-packets-na {
               type string;
               description
                 "Number of packets dropped due to tail drop not available";
             }
             leaf queue-counters-tail-drop-packets {
               type uint64;
               description
                 "Number of packets dropped at the tail of the queue";
             }
             leaf queue-counters-tail-drop-packets-rate {
               type uint64;
               description
                 "Rate at which packets are dropped at tail of queue";
             }
             leaf queue-counters-tail-drop-bytes {
               type uint64;
               description
                 "Number of packets dropped at tail drop of the queue";
             }
             leaf queue-counters-tail-drop-bytes-rate {
               type uint64;
               description
                 "Number of packets dropped at tail drop of the queue";
             }
             leaf queue-counters-rate-limit-drop-packets-na {
               type string;
               description
                 "Number of packets dropped due to rate-limit drop not 
                 available";
             }
             leaf queue-counters-rate-limit-drop-packets {
               type uint64;
               description
                 "Number of packets dropped by rate-limit for the queue";
             }
             leaf queue-counters-rate-limit-drop-packets-rate {
               type uint64;
               description
                 "Rate at which packets are dropped by rate-limit for the 
                 queue";
             }
             leaf queue-counters-rate-limit-drop-bytes-na {
               type string;
               description
                 "Number of bytes dropped due to tail drop not available";
             }
             leaf queue-counters-rate-limit-drop-bytes {
               type uint64;
               description
                 "Number of bytes dropped at the tail of the queue";
             }
             leaf queue-counters-rate-limit-drop-bytes-rate {
               type uint64;
               description
                 "Rate at which bytes are dropped at the tail of the queue";
             }
             leaf queue-counters-red-packets-na {
               type string;
               description
                 "Number of packets dropped due to RED not available";
             }
             leaf queue-counters-red-packets {
               type uint64;
               description
                 "Number of packets dropped due to RED";
             }
             leaf queue-counters-red-packets-rate {
               type uint64;
               description
                 "Rate at which packets are dropped due to RED";
             }
             leaf queue-counters-red-packets-ln {
               type uint64;
               description
                 "Number of RED dropped low-loss, non-TCP packets";
             }
             leaf queue-counters-red-packets-rate-ln {
               type uint64;
               description
                 "RED drop rate for low-loss, non-TCP packets";
             }
             leaf queue-counters-red-packets-lt {
               type uint64;
               description
                 "Number of RED dropped of low-loss, TCP packets";
             }
             leaf queue-counters-red-packets-rate-lt {
               type uint64;
               description
                 "RED drop rate for low-loss, TCP packets";
             }
             leaf queue-counters-red-packets-hn {
               type uint64;
               description
                 "Number of RED dropped high-loss, non-TCP packets";
             }
             leaf queue-counters-red-packets-rate-hn {
               type uint64;
               description
                 "RED drop rate for high-loss, non-TCP packets";
             }
             leaf queue-counters-red-packets-ht {
               type uint64;
               description
                 "Number of RED dropped high-loss, TCP packets";
             }
             leaf queue-counters-red-packets-rate-ht {
               type uint64;
               description
                 "RED drop rate for high-loss, TCP packets";
             }
             leaf queue-counters-red-packets-low {
               type uint64;
               description
                 "Number of RED dropped low-loss packets";
             }
             leaf queue-counters-red-packets-rate-low {
               type uint64;
               description
                 "RED drop rate for low-loss packets";
             }
             leaf queue-counters-red-packets-medium-low {
               type uint64;
               description
                 "Number of RED dropped medium-low-loss packets";
             }
             leaf queue-counters-red-packets-rate-medium-low {
               type uint64;
               description
                 "RED drop rate for medium-low-loss packets";
             }
             leaf queue-counters-red-packets-medium-high {
               type uint64;
               description
                 "Number of RED dropped medium-high-loss packets";
             }
             leaf queue-counters-red-packets-rate-medium-high {
               type uint64;
               description
                 "RED drop rate for medium-high-loss packets";
             }
             leaf queue-counters-red-packets-medium {
               type uint64;
               description
                 "Number of RED dropped medium-loss packets";
             }
             leaf queue-counters-red-packets-rate-medium {
               type uint64;
               description
                 "RED drop rate for medium-loss packets";
             }
             leaf queue-counters-red-packets-high {
               type uint64;
               description
                 "Number of RED dropped high-loss packets";
             }
             leaf queue-counters-red-packets-rate-high {
               type uint64;
               description
                 "RED drop rate for high-loss packets";
             }
             leaf queue-counters-red-bytes-na {
               type string;
               description
                 "Number of bytes dropped due to RED not available";
             }
             leaf queue-counters-red-bytes {
               type uint64;
               description
                 "Number of bytes dropped due to RED";
             }
             leaf queue-counters-red-bytes-rate {
               type uint64;
               description
                 "Rate at which bytes are dropped due to RED";
             }
             leaf queue-counters-red-bytes-ln {
               type uint64;
               description
                 "Number of RED dropped low-loss, non-TCP bytes";
             }
             leaf queue-counters-red-bytes-rate-ln {
               type uint64;
               description
                 "RED drop rate for low-loss, non-TCP bytes";
             }
             leaf queue-counters-red-bytes-lt {
               type uint64;
               description
                 "Number of RED dropped low-loss, TCP bytes";
             }
             leaf queue-counters-red-bytes-rate-lt {
               type uint64;
               description
                 "RED drop rate for low-loss, TCP bytes";
             }
             leaf queue-counters-red-bytes-hn {
               type uint64;
               description
                 "Number of RED dropped high-loss, non-TCP bytes";
             }
             leaf queue-counters-red-bytes-rate-hn {
               type uint64;
               description
                 "RED drop rate for high-loss, non-TCP bytes";
             }
             leaf queue-counters-red-bytes-ht {
               type uint64;
               description
                 "Number of RED dropped high-loss, TCP bytes";
             }
             leaf queue-counters-red-bytes-rate-ht {
               type uint64;
               description
                 "RED drop rate for high-loss, TCP bytes";
             }
             leaf queue-counters-red-bytes-low {
               type uint64;
               description
                 "Number of RED dropped low-loss bytes";
             }
             leaf queue-counters-red-bytes-rate-low {
               type uint64;
               description
                 "RED drop rate for low-loss bytes";
             }
             leaf queue-counters-red-bytes-medium-low {
               type uint64;
               description
                 "Number of RED dropped medium-low-loss bytes";
             }
             leaf queue-counters-red-bytes-rate-medium-low {
               type uint64;
               description
                 "RED drop rate for medium-low-loss bytes";
             }
             leaf queue-counters-red-bytes-medium-high {
               type uint64;
               description
                 "Number of RED dropped medium-high-loss bytes";
             }
             leaf queue-counters-red-bytes-rate-medium-high {
               type uint64;
               description
                 "RED drop rate for medium-high-loss bytes";
             }
             leaf queue-counters-red-bytes-medium {
               type uint64;
               description
                 "Number of RED dropped medium-loss bytes";
             }
             leaf queue-counters-red-bytes-rate-medium {
               type uint64;
               description
                 "RED drop rate for medium-loss bytes";
             }
             leaf queue-counters-red-bytes-high {
               type uint64;
               description
                 "Number of RED dropped high-loss bytes";
             }
             leaf queue-counters-red-bytes-rate-high {
               type uint64;
               description
                 "RED drop rate for high-loss bytes";
             }
             leaf queue-counters-timestamp {
               type uint64;
               description
                 "Last packet enqueued timestamp";
             }
             leaf queue-counters-total-drop-packets {
               type uint64;
               description
                 "Number of total packets dropped at the queue";
             }
             leaf queue-counters-total-drop-packets-rate {
               type uint64;
               description
                 "Number of total packets dropped at the queue";
             }
             leaf queue-counters-total-drop-bytes {
               type uint64;
               description
                 "Number of total packets dropped at the queue";
             }
             leaf queue-counters-total-drop-bytes-rate {
               type uint64;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
           container interface-cos-short-summary {
             description
               "Summary of queue information on an interface";
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           container queue-num-forwarding-class-name-map {
             leaf queue-number {
               type int32;
               description
                 "Queue number";
             }
             leaf forwarding-class-name {
               type string;
               description
                 "Forwarding class name associated with queue";
             }
           }
         }
         container forwarding-class-counters {
           description
             "Forwarding-class counter statistics";
           leaf forwarding-class-counters-error-message {
             type string;
             description
               "Forwarding-class statistics not available for this interface";
           }
           container ipv4-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container ipv6-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container mpls-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container layer2-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container other-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container protocol-aggregate-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container forwarding-class-statistics {
             container protocol-aggregate-forwarding-class-counters {
             }
             container ipv4-forwarding-class-counters {
             }
             container ipv6-forwarding-class-counters {
             }
             container mpls-forwarding-class-counters {
             }
             container layer2-forwarding-class-counters {
             }
             container other-forwarding-class-counters {
             }
           }
           container forwarding-class-accounting-parameters {
             leaf forwarding-class-accounting-for-protocol {
               type string;
             }
             leaf forwarding-class-accounting-for-traffic-direction {
               type string;
             }
             leaf forwarding-class-accounting-for-traffic-type {
               type string;
             }
             leaf forwarding-class-accounting-overhead-bytes {
               type uint32;
             }
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container multilink-bundle-options {
           leaf filler-packet-interval {
             type int32;
           }
         }
         container multilink-traffic-statistics {
           container bundle {
           }
           container class {
             description
               "Multilink class traffic statistics";
           }
           container multilink-detail-statistics {
             container bundle-detail {
             }
             container class-detail {
             }
           }
           container crtp {
             container crtp-sessions {
               leaf input-frames {
                 type int32;
               }
               leaf output-frames {
                 type int32;
               }
             }
             list crtp-statistics {
               key "name";
               leaf name {
                 type string;
                 description
                   "Name of this item";
               }
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
           }
         }
         container traffic-statistics {
           leaf input-bps {
             type int32;
           }
           leaf input-pps {
             type int32;
           }
           leaf output-bps {
             type int32;
           }
           leaf output-pps {
             type int32;
           }
           leaf input-packets {
             type int32;
           }
           leaf output-packets {
             type int32;
           }
           leaf input-bytes {
             type int32;
           }
           leaf output-bytes {
             type int32;
           }
           container ipv6-transit-statistics {
             leaf input-bytes {
               type int32;
             }
             leaf output-bytes {
               type int32;
             }
             leaf input-packets {
               type int32;
             }
             leaf output-packets {
               type int32;
             }
           }
           container ipv6-total-statistics {
             leaf input-bytes {
               type int32;
             }
             leaf output-bytes {
               type int32;
             }
             leaf input-packets {
               type int32;
             }
             leaf output-packets {
               type int32;
             }
           }
         }
         container multicast-statistics {
           description
             "Multicast statistics for interface";
           leaf multicast-statistics-header {
             type empty;
           }
           container ipv4-multicast-statistics {
             description
               "IPV4 multicast statistics for interface";
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
           container ipv6-multicast-statistics {
             description
               "IPV6 multicast statistics for interface";
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
         }
         container ingress-traffic-statistics {
           description
             "Traffic statistics at ingress before entering Packet 
             Forwarding Engine";
           leaf input-bps {
             type int32;
           }
           leaf input-pps {
             type int32;
           }
           leaf input-drop-bps {
             type int32;
             description
               "Drop rate at ingress in bits per second ";
           }
           leaf input-drop-pps {
             type int32;
             description
               "Drop rate at ingress in packets per second ";
           }
           leaf input-bytes {
             type int32;
           }
           leaf input-packets {
             type int32;
           }
           leaf input-drop-bytes {
             type int32;
             description
               "Drop statistics at ingress in bytes";
           }
           leaf input-drop-packets {
             type int32;
             description
               "Drop statistics at ingress in packets";
           }
         }
         container transit-traffic-statistics {
           description
             "Statistics for traffic passing through the Packet Forwarding 
             Engine";
         }
         container keepalive-statistics {
           description
             "Keepalive statistics for this interface";
           leaf keepalive-lmi-descriptor {
             type string;
           }
           leaf keepalive-input-count {
             type int32;
           }
           leaf keepalive-input-time {
             type string;
           }
           leaf keepalive-output-count {
             type int32;
           }
           leaf keepalive-output-time {
             type string;
           }
         }
         container virtual-circuit-information {
           description
             "Operational information and statistics for a virtual circuit";
           container traffic-statistics {
             leaf input-bps {
               type int32;
             }
             leaf input-pps {
               type int32;
             }
             leaf output-bps {
               type int32;
             }
             leaf output-pps {
               type int32;
             }
             leaf input-packets {
               type int32;
             }
             leaf output-packets {
               type int32;
             }
             leaf input-bytes {
               type int32;
             }
             leaf output-bytes {
               type int32;
             }
             container ipv6-transit-statistics {
               leaf input-bytes {
                 type int32;
               }
               leaf output-bytes {
                 type int32;
               }
               leaf input-packets {
                 type int32;
               }
               leaf output-packets {
                 type int32;
               }
             }
             container ipv6-total-statistics {
               leaf input-bytes {
                 type int32;
               }
               leaf output-bytes {
                 type int32;
               }
               leaf input-packets {
                 type int32;
               }
               leaf output-packets {
                 type int32;
               }
             }
           }
           container atm-cos-information {
             leaf vc-cos-mode {
               type string;
               description
                 "Virtual circuit CoS scheduling mode";
             }
             list atm-cos-queue {
               container atm-cos-queue-parameters {
                 leaf cos-forwarding-class-name {
                   type string;
                   description
                     "Forwarding class name associated with queue";
                 }
                 leaf cos-queue-number {
                   type int32;
                   description
                     "Queue number";
                 }
                 leaf scheduling-priority {
                   type string;
                   description
                     "Scheduling priority";
                 }
                 leaf transmit-weight-cells {
                   type int32;
                   description
                     "Weight to apply to scheduling as number of cells";
                 }
                 leaf transmit-weight-percent {
                   type int32;
                   description
                     "Weight to apply to scheduling as fill percentage";
                 }
                 leaf epd-threshold {
                   type int32;
                   description
                     "Early packet drop threshold";
                 }
                 leaf epd-threshold-plp0 {
                   type int32;
                   description
                     "Early packet drop threshold for PLP 0";
                 }
                 leaf epd-threshold-plp1 {
                   type int32;
                   description
                     "Early packet drop threshold for PLP 1";
                 }
                 container linear-red-drop-profile {
                   leaf queue-depth {
                     type uint32;
                     description
                       "Instantaneous queue depth";
                   }
                   leaf low-red {
                     type int32;
                     description
                       "Fill level percentage when linear RED is applied for
                       low PLP";
                   }
                   leaf high-red {
                     type int32;
                     description
                       "Fill level percentage when linear RED is applied for
                       high PLP";
                   }
                   leaf max-low-red {
                     type int32;
                     description
                       "Fill level percentage with 100% packet drop for low 
                       PLP";
                   }
                   leaf max-high-red {
                     type int32;
                     description
                       "Fill level percentage with 100% packet drop for high
                       PLP";
                   }
                 }
               }
               container atm-cos-queue-statistics {
                 leaf atm-output-bytes {
                   type int32;
                 }
                 leaf atm-output-packets {
                   type int32;
                 }
                 leaf atm-packet-drops {
                   type int32;
                 }
               }
               container atm-cos-plp-statistics {
                 leaf atm-plp0-output-bytes {
                   type int32;
                 }
                 leaf atm-plp1-output-bytes {
                   type int32;
                 }
                 leaf atm-plp0-output-packets {
                   type int32;
                 }
                 leaf atm-plp1-output-packets {
                   type int32;
                 }
                 leaf atm-plp0-byte-drops {
                   type int32;
                 }
                 leaf atm-plp1-byte-drops {
                   type int32;
                 }
                 leaf atm-plp0-packet-drops {
                   type int32;
                 }
                 leaf atm-plp1-packet-drops {
                   type int32;
                 }
               }
             }
           }
         }
         list filter-information {
           leaf filter-family {
             type string;
             description
               "Protocol family of the filter";
           }
           leaf-list filter-input {
             type string;
             description
               "Name of the input filter";
           }
           leaf-list filter-output {
             type string;
             description
               "Name of the output filter";
           }
         }
         list address-family {
           leaf local-bias-information {
             type string;
           }
           leaf ft-iff-dest-port {
             type uint32;
             description
               "Destination UDP port to be used for this family";
           }
           container pppoe-underlying-information {
             description
               "PPPoE Underlying information";
             list pppoe-underlying-interface {
               leaf dynamic-profile {
                 type string;
                 description
                   "Dynamic Profile name";
               }
               leaf service-name-table {
                 type string;
                 description
                   "Name of Service Name Table";
               }
               leaf max-sessions {
                 type int32;
                 description
                   "Maximum number of PPPoE sessions";
               }
               leaf max-sessions-vsa-ignore {
                 type string;
                 description
                   "Ignore max-sessions VSA";
               }
               leaf duplicate-protection {
                 type string;
                 description
                   "Duplicate protection mode";
               }
               leaf short-cycle-protection {
                 type string;
                 description
                   "Short cycle protection mode";
               }
               leaf direct-connect {
                 type string;
                 description
                   "Direct connect mode";
               }
               leaf ac-name {
                 type string;
                 description
                   "Access Concentrator name";
               }
               leaf underlying-interface-name {
                 type string;
                 description
                   "Underlying interface name";
               }
               leaf underlying-interface-index {
                 type string;
                 description
                   "Underlying interface index";
               }
               leaf encapsulation-type-identifier {
                 type string;
                 description
                   "Encapsulation type identifier";
               }
               leaf state {
                 type string;
                 description
                   "State";
               }
               leaf active-sessions {
                 type int32;
                 description
                   "Number of active PPPoE sessions";
               }
               leaf aci-autosensing {
                 type string;
                 description
                   "ACI VLAN Autosensing mode";
               }
               leaf line-identity-autosensing {
                 type string;
                 description
                   "Line Identity Autosensing mode";
               }
             }
           }
           list interface-address {
           }
           container destination-class-statistics {
             description
               "Destination class usage (DCU) statistics";
           }
           container source-class-statistics {
             description
               "Source class usage (SCU) statistics";
           }
         }
         list bridge-iff-properties {
           description
             "Information about Ethernet-switching address family";
         }
         container l2circuit-info {
           leaf out-of-sequence {
             type int32;
           }
           leaf denied-packets {
             type int32;
           }
           leaf cell-bundle-size {
             type int32;
           }
           leaf cell-bundle-timeout {
             type int32;
           }
           leaf cell-timeout-count {
             type int32;
           }
         }
         container media-information {
           description
             "Information about media alarms";
           leaf media-type {
             type string;
             description
               "Type of media this information is for";
           }
           list media-alarm {
             leaf media-alarm-name {
               type string;
             }
             leaf media-alarm-count {
               type int32;
             }
             leaf media-alarm-seconds {
               type int32;
             }
             leaf media-alarm-state {
               type string;
             }
             leaf ce-counter-name {
               type string;
               description
                 "Circuit Emulation counter information";
             }
             leaf ce-counter-packets {
               type int32;
               description
                 "Circuit Emulation number of packets";
             }
             leaf ce-counter-bytes {
               type int32;
               description
                 "Circuit Emulation number of bytes";
             }
             leaf ce-counter-count {
               type int32;
               description
                 "Circuit Emulation number of event occurrences";
             }
           }
           leaf ds1-timeslots {
             type string;
           }
           leaf ds1-line-encoding {
             type string;
           }
           leaf ds1-byte-encoding {
             type string;
           }
           leaf ds1-data-inversion {
             type string;
           }
           leaf idle-cycle-flag {
             type string;
           }
           leaf start-end-flag {
             type string;
           }
           leaf ds0-byte-encoding {
             type string;
           }
           leaf ds0-data-inversion {
             type string;
           }
           leaf e3-data-inversion {
             type string;
           }
           leaf ds1-buildout {
             type string;
             description
               "Number of feet";
           }
         }
         list macsec-statistics {
           description
             "Information about MAC Security statistics details";
           leaf interface-name {
             type string;
             description
               "Class-of-service interface name";
           }
           leaf encrypted-packets {
             type uint64;
             description
               "Macsec encrypted packets sent";
           }
           leaf encrypted-bytes {
             type uint64;
             description
               "Macsec encrypted bytes sent";
           }
           leaf protected-packets {
             type uint64;
             description
               "Macsec packets sent with only integrity protection";
           }
           leaf protected-bytes {
             type uint64;
             description
               "Macsec bytes sent with only integrity protection";
           }
           leaf ok-packets {
             type uint64;
             description
               "Macsec packets accepted";
           }
           leaf decrypted-bytes {
             type uint64;
             description
               "Macsec received bytes decrypted";
           }
           leaf decrypted-packets {
             type uint64;
             description
               "Macsec received packets decrypted";
           }
           leaf validated-packets {
             type uint64;
             description
               "Macsec received packets validated";
           }
           leaf validated-bytes {
             type uint64;
             description
               "Macsec received bytes validated";
           }
           leaf untagged-packets {
             type uint64;
             description
               "Macsec untagged packets";
           }
           leaf toolong-packets {
             type uint64;
             description
               "Macsec too long packets transmitted on a secure channel";
           }
           leaf control-packets {
             type uint64;
             description
               "Macsec control packets received on a secure channel";
           }
           leaf tagged-miss-packets {
             type uint64;
             description
               "Macsec tagged miss packets received on a secure channel";
           }
           leaf untagged-hit-packets {
             type uint64;
             description
               "Macsec untagged hit packets received on a secure channel";
           }
           leaf notag-packets {
             type uint64;
             description
               "Macsec no tag packets received on a secure channel";
           }
           leaf badtag-packets {
             type uint64;
             description
               "Macsec bad tag packets received on a secure channel";
           }
           leaf unknown-sci-packets {
             type uint64;
             description
               "Macsec unknown sci packets received on a secure channel";
           }
           leaf no-sci-packets {
             type uint64;
             description
               "Macsec no sci packets received on a secure channel";
           }
           leaf control-pass-packets {
             type uint64;
             description
               "Macsec allowed control packets received on a secure channel";
           }
           leaf uncontrol-pass-packets {
             type uint64;
             description
               "Macsec allowed uncontrol packets received on a secure 
               channel";
           }
           leaf control-fail-packets {
             type uint64;
             description
               "Macsec dropped control packets received on a secure channel";
           }
           leaf uncontrol-fail-packets {
             type uint64;
             description
               "Macsec dropped uncontrol packets received on a secure 
               channel";
           }
           leaf hit-dropped-packets {
             type uint64;
             description
               "Macsec hit dropped packets received on a security channel";
           }
           leaf notusing-sa-packets {
             type uint64;
             description
               "Macsec not using sa packets received on a security channel";
           }
           leaf unused-sa-packets {
             type uint64;
             description
               "Macsec unused sa packets received on a security channel";
           }
           leaf late-packets {
             type uint64;
             description
               "Macsec late packets dropped on a security channel";
           }
           leaf delayed-packets {
             type uint64;
             description
               "Macsec delayed packets accepted on a security channel";
           }
           leaf unchecked-packets {
             type uint64;
             description
               "Macsec unchecked packets accepted on a security channel";
           }
           leaf notvalid-packets {
             type uint64;
             description
               "Macsec not valid packets dropped on a security channel";
           }
           leaf invalid-packets {
             type uint64;
             description
               "Macsec invalid packets accepted on a security channel";
           }
           list secure-channel-sent {
             leaf encrypted-packets {
               type uint64;
               description
                 "Macsec encrypted packets sent";
             }
             leaf encrypted-bytes {
               type uint64;
               description
                 "Macsec encrypted bytes sent";
             }
             leaf protected-packets {
               type uint64;
               description
                 "Macsec packets sent with only integrity protection";
             }
             leaf protected-bytes {
               type uint64;
               description
                 "Macsec bytes sent with only integrity protection";
             }
           }
           list secure-association-sent {
             leaf encrypted-packets {
               type uint64;
               description
                 "Macsec encrypted packets sent";
             }
             leaf encrypted-bytes {
               type uint64;
               description
                 "Macsec encrypted bytes sent";
             }
             leaf protected-packets {
               type uint64;
               description
                 "Macsec packets sent with only integrity protection";
             }
             leaf protected-bytes {
               type uint64;
               description
                 "Macsec bytes sent with only integrity protection";
             }
           }
           list secure-channel-received {
             leaf ok-packets {
               type uint64;
               description
                 "Macsec packets accepted";
             }
             leaf decrypted-packets {
               type uint64;
               description
                 "Macsec received packets decrypted";
             }
             leaf decrypted-bytes {
               type uint64;
               description
                 "Macsec received bytes decrypted";
             }
             leaf validated-packets {
               type uint64;
               description
                 "Macsec received packets validated";
             }
             leaf validated-bytes {
               type uint64;
               description
                 "Macsec received bytes validated";
             }
           }
           list secure-association-received {
             leaf ok-packets {
               type uint64;
               description
                 "Macsec packets accepted";
             }
             leaf decrypted-packets {
               type uint64;
               description
                 "Macsec received packets decrypted";
             }
             leaf decrypted-bytes {
               type uint64;
               description
                 "Macsec received bytes decrypted";
             }
             leaf validated-packets {
               type uint64;
               description
                 "Macsec received packets validated";
             }
             leaf validated-bytes {
               type uint64;
               description
                 "Macsec received bytes validated";
             }
           }
           list macsec-error-information {
             list secure-channel-sent-errors {
               leaf untagged-packets {
                 type uint64;
                 description
                   "Macsec untagged packets";
               }
               leaf toolong-packets {
                 type uint64;
                 description
                   "Macsec too long packets transmitted on a secure channel";
               }
             }
             list secure-channel-received-errors {
               leaf control-packets {
                 type uint64;
                 description
                   "Macsec control packets received on a secure channel";
               }
               leaf tagged-miss-packets {
                 type uint64;
                 description
                   "Macsec tagged miss packets received on a secure channel";
               }
               leaf untagged-hit-packets {
                 type uint64;
                 description
                   "Macsec untagged hit packets received on a secure channel";
               }
               leaf untagged-packets {
                 type uint64;
                 description
                   "Macsec untagged packets";
               }
               leaf notag-packets {
                 type uint64;
                 description
                   "Macsec no tag packets received on a secure channel";
               }
               leaf badtag-packets {
                 type uint64;
                 description
                   "Macsec bad tag packets received on a secure channel";
               }
               leaf unknown-sci-packets {
                 type uint64;
                 description
                   "Macsec unknown sci packets received on a secure channel";
               }
               leaf no-sci-packets {
                 type uint64;
                 description
                   "Macsec no sci packets received on a secure channel";
               }
               leaf control-pass-packets {
                 type uint64;
                 description
                   "Macsec allowed control packets received on a secure 
                   channel";
               }
               leaf control-fail-packets {
                 type uint64;
                 description
                   "Macsec dropped control packets received on a secure 
                   channel";
               }
               leaf uncontrol-pass-packets {
                 type uint64;
                 description
                   "Macsec allowed uncontrol packets received on a secure 
                   channel";
               }
               leaf uncontrol-fail-packets {
                 type uint64;
                 description
                   "Macsec dropped uncontrol packets received on a secure 
                   channel";
               }
             }
             list secure-channel-received-extended {
               leaf hit-dropped-packets {
                 type uint64;
                 description
                   "Macsec hit dropped packets received on a security 
                   channel";
               }
               leaf invalid-packets {
                 type uint64;
                 description
                   "Macsec invalid packets accepted on a security channel";
               }
               leaf late-packets {
                 type uint64;
                 description
                   "Macsec late packets dropped on a security channel";
               }
               leaf delayed-packets {
                 type uint64;
                 description
                   "Macsec delayed packets accepted on a security channel";
               }
               leaf unchecked-packets {
                 type uint64;
                 description
                   "Macsec unchecked packets accepted on a security channel";
               }
               leaf notvalid-packets {
                 type uint64;
                 description
                   "Macsec not valid packets dropped on a security channel";
               }
               leaf notusing-sa-packets {
                 type uint64;
                 description
                   "Macsec not using sa packets received on a security 
                   channel";
               }
               leaf unused-sa-packets {
                 type uint64;
                 description
                   "Macsec unused sa packets received on a security channel";
               }
               leaf untagged-hit-packets {
                 type uint64;
                 description
                   "Macsec untagged hit packets received on a secure channel";
               }
             }
           }
         }
         container lag-traffic-statistics {
           container lag-multicast-statistics {
             leaf lag-multicast-statistics-header {
               type empty;
             }
             container lag-ipv4-multicast-statistics {
               leaf input-packets {
                 type int32;
               }
               leaf input-pps {
                 type int32;
               }
               leaf input-bytes {
                 type int32;
               }
               leaf input-bps {
                 type int32;
               }
               leaf output-packets {
                 type int32;
               }
               leaf output-pps {
                 type int32;
               }
               leaf output-bytes {
                 type int32;
               }
               leaf output-bps {
                 type int32;
               }
             }
             container lag-ipv6-multicast-statistics {
               leaf input-packets {
                 type int32;
               }
               leaf input-pps {
                 type int32;
               }
               leaf input-bytes {
                 type int32;
               }
               leaf input-bps {
                 type int32;
               }
               leaf output-packets {
                 type int32;
               }
               leaf output-pps {
                 type int32;
               }
               leaf output-bytes {
                 type int32;
               }
               leaf output-bps {
                 type int32;
               }
             }
           }
           list if-distribution-list-information {
           }
         }
         container layer2-input-policer-statistics {
           description
             "Layer 2 input policer statistics for interface";
           leaf policer-medium-low-frames {
             type int32;
             description
               "Number of loss priority medium low frames";
           }
           leaf policer-medium-low-bytes {
             type int32;
             description
               "Number of loss priority medium low bytes";
           }
           leaf policer-medium-low-rate {
             type int32;
             description
               "Rate of loss priority medium low pkts";
           }
         }
         container layer2-output-policer-statistics {
           description
             "Layer 2 output policer statistics for interface";
           leaf policer-medium-low-frames {
             type int32;
             description
               "Number of loss priority medium low frames";
           }
           leaf policer-medium-low-bytes {
             type int32;
             description
               "Number of loss priority medium low bytes";
           }
           leaf policer-medium-low-rate {
             type int32;
             description
               "Rate of loss priority medium low pkts";
           }
         }
         container mac-policer-information {
           container ether-policer-list {
           }
         }
       }
     }
     container interface-policer-information {
       list physical-interface {
         key "name";
         description
           "Information about a single physical interface";
         leaf name {
           type string;
           description
             "Name of this item";
         }
         leaf admin-status {
           type string;
           description
             "Desired state of the interface";
         }
         leaf oper-status {
           type string;
           description
             "Current operational state of the interface";
         }
         leaf esi-source-bmac {
           type jt:mac-addr;
           description
             "Ethernet segment source B-MAC for this interface";
         }
         leaf sonet-payload-pointer-curptr {
           type string;
           description
             "Value of the SONET/SDH payload pointer, derived from the H1 
             and H2 overhead bytes";
         }
         leaf sonet-payload-pointer-ptrinc-count {
           type string;
           description
             "Number of times the value of the SONET/SDH payload pointer had
             positive justification";
         }
         leaf sonet-payload-pointer-ptrdec-count {
           type string;
           description
             "Number of times the value of the SONET/SDH payload pointer had
             negative justification";
         }
         leaf sonet-payload-pointer-newptr-ndf-count {
           type string;
           description
             "Number of times a new payload pointer was created with the New
             Data Found flag set";
         }
         leaf link-partner-status {
           type string;
           description
             "Auto-negotiation status of link partner";
         }
         container optics-properties {
           description
             "Optics properties";
           leaf wavelength {
             type string;
             description
               "Wavelength of optics in nanometers";
           }
           leaf frequency {
             type string;
             description
               "Frequency of optics in terahertz";
           }
         }
         container queue-counters {
           description
             "Queue counter statistics";
           leaf queue-counters-error-message {
             type string;
             description
               "Queue statistics not available for this interface";
           }
           list queue {
             description
               "Counters for a single queue";
             leaf queue-number {
               type int32;
               description
                 "Queue number";
             }
             leaf queue-counters-queued-packets {
               type uint64;
               description
                 "Queued packet count";
             }
             leaf queue-counters-trans-packets {
               type uint64;
               description
                 "Total number of transmitted packets";
             }
             leaf queue-counters-total-drop-packets {
               type uint64;
               description
                 "Number of total packets dropped at the queue";
             }
             leaf forwarding-class-name {
               type string;
               description
                 "Forwarding class name associated with queue";
             }
             leaf queue-counters-queued-packets-rate {
               type uint64;
               description
                 "Rate at which packets are queued";
             }
             leaf queue-counters-queued-bytes {
               type uint64;
               description
                 "Queued bytes count";
             }
             leaf queue-counters-queued-bytes-rate {
               type uint64;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets-rate {
               type uint64;
               description
                 "Rate at which packets are transmitted";
             }
             leaf queue-counters-trans-bytes {
               type uint64;
               description
                 "Total number of transmitted bytes";
             }
             leaf queue-counters-trans-bytes-rate {
               type uint64;
               description
                 "Rate at which bytes are transmitted";
             }
             leaf queue-counters-tail-drop-packets-na {
               type string;
               description
                 "Number of packets dropped due to tail drop not available";
             }
             leaf queue-counters-tail-drop-packets {
               type uint64;
               description
                 "Number of packets dropped at the tail of the queue";
             }
             leaf queue-counters-tail-drop-packets-rate {
               type uint64;
               description
                 "Rate at which packets are dropped at tail of queue";
             }
             leaf queue-counters-tail-drop-bytes {
               type uint64;
               description
                 "Number of packets dropped at tail drop of the queue";
             }
             leaf queue-counters-tail-drop-bytes-rate {
               type uint64;
               description
                 "Number of packets dropped at tail drop of the queue";
             }
             leaf queue-counters-rate-limit-drop-packets-na {
               type string;
               description
                 "Number of packets dropped due to rate-limit drop not 
                 available";
             }
             leaf queue-counters-rate-limit-drop-packets {
               type uint64;
               description
                 "Number of packets dropped by rate-limit for the queue";
             }
             leaf queue-counters-rate-limit-drop-packets-rate {
               type uint64;
               description
                 "Rate at which packets are dropped by rate-limit for the 
                 queue";
             }
             leaf queue-counters-rate-limit-drop-bytes-na {
               type string;
               description
                 "Number of bytes dropped due to tail drop not available";
             }
             leaf queue-counters-rate-limit-drop-bytes {
               type uint64;
               description
                 "Number of bytes dropped at the tail of the queue";
             }
             leaf queue-counters-rate-limit-drop-bytes-rate {
               type uint64;
               description
                 "Rate at which bytes are dropped at the tail of the queue";
             }
             leaf queue-counters-red-packets-na {
               type string;
               description
                 "Number of packets dropped due to RED not available";
             }
             leaf queue-counters-red-packets {
               type uint64;
               description
                 "Number of packets dropped due to RED";
             }
             leaf queue-counters-red-packets-rate {
               type uint64;
               description
                 "Rate at which packets are dropped due to RED";
             }
             leaf queue-counters-red-packets-ln {
               type uint64;
               description
                 "Number of RED dropped low-loss, non-TCP packets";
             }
             leaf queue-counters-red-packets-rate-ln {
               type uint64;
               description
                 "RED drop rate for low-loss, non-TCP packets";
             }
             leaf queue-counters-red-packets-lt {
               type uint64;
               description
                 "Number of RED dropped of low-loss, TCP packets";
             }
             leaf queue-counters-red-packets-rate-lt {
               type uint64;
               description
                 "RED drop rate for low-loss, TCP packets";
             }
             leaf queue-counters-red-packets-hn {
               type uint64;
               description
                 "Number of RED dropped high-loss, non-TCP packets";
             }
             leaf queue-counters-red-packets-rate-hn {
               type uint64;
               description
                 "RED drop rate for high-loss, non-TCP packets";
             }
             leaf queue-counters-red-packets-ht {
               type uint64;
               description
                 "Number of RED dropped high-loss, TCP packets";
             }
             leaf queue-counters-red-packets-rate-ht {
               type uint64;
               description
                 "RED drop rate for high-loss, TCP packets";
             }
             leaf queue-counters-red-packets-low {
               type uint64;
               description
                 "Number of RED dropped low-loss packets";
             }
             leaf queue-counters-red-packets-rate-low {
               type uint64;
               description
                 "RED drop rate for low-loss packets";
             }
             leaf queue-counters-red-packets-medium-low {
               type uint64;
               description
                 "Number of RED dropped medium-low-loss packets";
             }
             leaf queue-counters-red-packets-rate-medium-low {
               type uint64;
               description
                 "RED drop rate for medium-low-loss packets";
             }
             leaf queue-counters-red-packets-medium-high {
               type uint64;
               description
                 "Number of RED dropped medium-high-loss packets";
             }
             leaf queue-counters-red-packets-rate-medium-high {
               type uint64;
               description
                 "RED drop rate for medium-high-loss packets";
             }
             leaf queue-counters-red-packets-medium {
               type uint64;
               description
                 "Number of RED dropped medium-loss packets";
             }
             leaf queue-counters-red-packets-rate-medium {
               type uint64;
               description
                 "RED drop rate for medium-loss packets";
             }
             leaf queue-counters-red-packets-high {
               type uint64;
               description
                 "Number of RED dropped high-loss packets";
             }
             leaf queue-counters-red-packets-rate-high {
               type uint64;
               description
                 "RED drop rate for high-loss packets";
             }
             leaf queue-counters-red-bytes-na {
               type string;
               description
                 "Number of bytes dropped due to RED not available";
             }
             leaf queue-counters-red-bytes {
               type uint64;
               description
                 "Number of bytes dropped due to RED";
             }
             leaf queue-counters-red-bytes-rate {
               type uint64;
               description
                 "Rate at which bytes are dropped due to RED";
             }
             leaf queue-counters-red-bytes-ln {
               type uint64;
               description
                 "Number of RED dropped low-loss, non-TCP bytes";
             }
             leaf queue-counters-red-bytes-rate-ln {
               type uint64;
               description
                 "RED drop rate for low-loss, non-TCP bytes";
             }
             leaf queue-counters-red-bytes-lt {
               type uint64;
               description
                 "Number of RED dropped low-loss, TCP bytes";
             }
             leaf queue-counters-red-bytes-rate-lt {
               type uint64;
               description
                 "RED drop rate for low-loss, TCP bytes";
             }
             leaf queue-counters-red-bytes-hn {
               type uint64;
               description
                 "Number of RED dropped high-loss, non-TCP bytes";
             }
             leaf queue-counters-red-bytes-rate-hn {
               type uint64;
               description
                 "RED drop rate for high-loss, non-TCP bytes";
             }
             leaf queue-counters-red-bytes-ht {
               type uint64;
               description
                 "Number of RED dropped high-loss, TCP bytes";
             }
             leaf queue-counters-red-bytes-rate-ht {
               type uint64;
               description
                 "RED drop rate for high-loss, TCP bytes";
             }
             leaf queue-counters-red-bytes-low {
               type uint64;
               description
                 "Number of RED dropped low-loss bytes";
             }
             leaf queue-counters-red-bytes-rate-low {
               type uint64;
               description
                 "RED drop rate for low-loss bytes";
             }
             leaf queue-counters-red-bytes-medium-low {
               type uint64;
               description
                 "Number of RED dropped medium-low-loss bytes";
             }
             leaf queue-counters-red-bytes-rate-medium-low {
               type uint64;
               description
                 "RED drop rate for medium-low-loss bytes";
             }
             leaf queue-counters-red-bytes-medium-high {
               type uint64;
               description
                 "Number of RED dropped medium-high-loss bytes";
             }
             leaf queue-counters-red-bytes-rate-medium-high {
               type uint64;
               description
                 "RED drop rate for medium-high-loss bytes";
             }
             leaf queue-counters-red-bytes-medium {
               type uint64;
               description
                 "Number of RED dropped medium-loss bytes";
             }
             leaf queue-counters-red-bytes-rate-medium {
               type uint64;
               description
                 "RED drop rate for medium-loss bytes";
             }
             leaf queue-counters-red-bytes-high {
               type uint64;
               description
                 "Number of RED dropped high-loss bytes";
             }
             leaf queue-counters-red-bytes-rate-high {
               type uint64;
               description
                 "RED drop rate for high-loss bytes";
             }
             leaf queue-counters-timestamp {
               type uint64;
               description
                 "Last packet enqueued timestamp";
             }
             leaf queue-counters-total-drop-packets-rate {
               type uint64;
               description
                 "Number of total packets dropped at the queue";
             }
             leaf queue-counters-total-drop-bytes {
               type uint64;
               description
                 "Number of total packets dropped at the queue";
             }
             leaf queue-counters-total-drop-bytes-rate {
               type uint64;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-short-summary {
             description
               "Summary of queue information on an interface";
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
         }
         container voq-counters {
           description
             "VOQ counter statistics";
           leaf voq-counters-error-message {
             type string;
             description
               "VOQ statistics not available for this interface";
           }
           container voq {
             description
               "Counters for a single voq";
             container fpc {
               description
                 "Counters for a single FPC";
               leaf fpc-no {
                 type int32;
                 description
                   "FPC number";
               }
               container pfe {
                 description
                   "Counters for a single PFE";
                 leaf-list pfe-no {
                   type int32;
                   description
                     "PFE number";
                 }
                 leaf voq-counters-tail-drop-packets {
                   type int32;
                   description
                     "Tail DROP packet count";
                 }
                 leaf voq-counters-tail-drop-packets-rate {
                   type int32;
                   description
                     "Rate at which tail packets are dropped";
                 }
                 leaf voq-counters-tail-drop-bytes {
                   type int32;
                   description
                     "Tail DROP bytes count";
                 }
                 leaf voq-counters-tail-drop-bytes-rate {
                   type int32;
                   description
                     "Rate at which tail bytes are dropped";
                 }
                 leaf voq-counters-drop-packets {
                   type int32;
                   description
                     "DROP packet count";
                 }
                 leaf voq-counters-drop-packets-rate {
                   type int32;
                   description
                     "Rate at which packets are dropped";
                 }
                 leaf voq-counters-drop-bytes {
                   type int32;
                   description
                     "DROP bytes count";
                 }
                 leaf voq-counters-drop-bytes-rate {
                   type int32;
                   description
                     "Rate at which bytes are dropped";
                 }
               }
             }
             leaf queue-number {
               type int32;
               description
                 "Queue number";
             }
             leaf forwarding-class-name {
               type string;
               description
                 "Forwarding class name associated with queue";
             }
           }
         }
         container smart-sfp-av-titan-statistics {
           description
             "AimValley Smart SFP statistics";
           leaf smart-sfp-av-titan-error-message {
             type string;
             description
               "AV Smart SFP un-available";
           }
           container smart-sfp-av-titan-eth-port-statistics {
             leaf rx-crct-frames {
               type uint32;
             }
             leaf rx-crct-bytes {
               type uint32;
             }
             leaf rx-fragments {
               type uint32;
             }
             leaf rx-crct-unicast-frames {
               type uint32;
             }
             leaf rx-crct-multicast-frames {
               type uint32;
             }
             leaf rx-crct-broadcast-frames {
               type uint32;
             }
             leaf rx-err-fcs-frames {
               type uint32;
             }
             leaf rx-len-err-frames {
               type uint32;
             }
             leaf rx-undersize-frames {
               type uint32;
             }
             leaf rx-oversize-frames {
               type uint32;
             }
             leaf rx-inv-vlan-mismatch-frames {
               type uint32;
             }
             leaf rx-discarded-frames {
               type uint32;
             }
             leaf rx-dropped-q-overflow-frames {
               type uint32;
             }
             leaf tx-frames {
               type uint32;
             }
             leaf tx-bytes {
               type uint32;
             }
             leaf tx-unicast-frames {
               type uint32;
             }
             leaf tx-multicast-frames {
               type uint32;
             }
             leaf tx-broadcast-frames {
               type uint32;
             }
           }
           container smart-sfp-av-titan-iwf-statistics {
             leaf rx-packets {
               type uint32;
             }
             leaf tx-packets {
               type uint32;
             }
             leaf malformed-packets {
               type uint32;
             }
             leaf reordered-packets {
               type uint32;
             }
             leaf misordered-dropped-packets {
               type uint32;
             }
             leaf missing-packets {
               type uint32;
             }
             leaf played-out-packets {
               type uint32;
             }
             leaf jb-overrun {
               type uint32;
             }
             leaf jb-underrun {
               type uint32;
             }
           }
           container smart-sfp-av-titan-ds3-statistics {
             leaf rx-bpvexzerrors {
               type uint32;
             }
             leaf rx-cvperrors {
               type uint32;
             }
             leaf b3-errors {
               type uint32;
             }
           }
           container smart-sfp-av-titan-stm-statistics {
             leaf rx-b1-errors {
               type uint32;
             }
             leaf tx-b1-errors {
               type uint32;
             }
           }
         }
         container smart-sfp-av-titan-defects {
           description
             "AimValley Smart SFP defects";
           container smart-sfp-av-titan-defect-list {
             leaf sfp-tdm-defects {
               type string;
             }
             leaf sfp-system-defects {
               type string;
             }
           }
         }
         container forwarding-class-counters {
           description
             "Forwarding-class counter statistics";
           leaf forwarding-class-counters-error-message {
             type string;
             description
               "Forwarding-class statistics not available for this interface";
           }
           container ipv4-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container ipv6-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container mpls-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container layer2-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container other-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container protocol-aggregate-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container forwarding-class-statistics {
             container protocol-aggregate-forwarding-class-counters {
             }
             container ipv4-forwarding-class-counters {
             }
             container ipv6-forwarding-class-counters {
             }
             container mpls-forwarding-class-counters {
             }
             container layer2-forwarding-class-counters {
             }
             container other-forwarding-class-counters {
             }
           }
           container forwarding-class-accounting-parameters {
             leaf forwarding-class-accounting-for-protocol {
               type string;
             }
             leaf forwarding-class-accounting-for-traffic-direction {
               type string;
             }
             leaf forwarding-class-accounting-for-traffic-type {
               type string;
             }
             leaf forwarding-class-accounting-overhead-bytes {
               type uint32;
             }
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container keepalive-statistics {
           description
             "Keepalive statistics for this interface";
           leaf keepalive-lmi-descriptor {
             type string;
           }
           leaf keepalive-input-count {
             type int32;
           }
           leaf keepalive-input-time {
             type string;
           }
           leaf keepalive-output-count {
             type int32;
           }
           leaf keepalive-output-time {
             type string;
           }
         }
         container optics-bit-rate {
           leaf bit-rate {
             type string;
             description
               " Optics Bit Rate";
           }
         }
         container optics-fec-statistics {
           leaf fec-corrected-errors {
             type int32;
           }
           leaf fec-valid-time {
             type int32;
           }
           leaf fec-corrected-error-ratio {
             type int32;
           }
           leaf fec-uncorrected-words {
             type int32;
           }
         }
         container traffic-statistics {
           leaf input-bps {
             type int32;
           }
           leaf input-pps {
             type int32;
           }
           leaf output-bps {
             type int32;
           }
           leaf output-pps {
             type int32;
           }
           leaf input-packets {
             type int32;
           }
           leaf output-packets {
             type int32;
           }
           leaf input-bytes {
             type int32;
           }
           leaf output-bytes {
             type int32;
           }
           container ipv6-transit-statistics {
             leaf input-bytes {
               type int32;
             }
             leaf output-bytes {
               type int32;
             }
             leaf input-packets {
               type int32;
             }
             leaf output-packets {
               type int32;
             }
           }
           container ipv6-total-statistics {
             leaf input-bytes {
               type int32;
             }
             leaf output-bytes {
               type int32;
             }
             leaf input-packets {
               type int32;
             }
             leaf output-packets {
               type int32;
             }
           }
         }
         container multicast-statistics {
           description
             "Multicast statistics for interface";
           leaf multicast-statistics-header {
             type empty;
           }
           container ipv4-multicast-statistics {
             description
               "IPV4 multicast statistics for interface";
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
           container ipv6-multicast-statistics {
             description
               "IPV6 multicast statistics for interface";
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
         }
         container ingress-traffic-statistics {
           description
             "Traffic statistics at ingress before entering Packet 
             Forwarding Engine";
           leaf input-bps {
             type int32;
           }
           leaf input-pps {
             type int32;
           }
           leaf input-drop-bps {
             type int32;
             description
               "Drop rate at ingress in bits per second ";
           }
           leaf input-drop-pps {
             type int32;
             description
               "Drop rate at ingress in packets per second ";
           }
           leaf input-bytes {
             type int32;
           }
           leaf input-packets {
             type int32;
           }
           leaf input-drop-bytes {
             type int32;
             description
               "Drop statistics at ingress in bytes";
           }
           leaf input-drop-packets {
             type int32;
             description
               "Drop statistics at ingress in packets";
           }
         }
         container active-alarms {
         }
         container active-defects {
         }
         container media-state-information {
         }
         container sonet-errors {
           list media-alarm {
             leaf media-alarm-name {
               type string;
             }
             leaf media-alarm-count {
               type int32;
             }
           }
         }
         container sonet-physical-information {
           list media-alarm {
             leaf media-alarm-name {
               type string;
             }
             leaf media-alarm-seconds {
               type int32;
             }
             leaf media-alarm-count {
               type int32;
             }
             leaf media-alarm-state {
               type string;
             }
           }
         }
         container sonet-section-information {
           list media-alarm {
             leaf media-alarm-name {
               type string;
             }
             leaf media-alarm-seconds {
               type int32;
             }
             leaf media-alarm-count {
               type int32;
             }
             leaf media-alarm-state {
               type string;
             }
           }
         }
         container sonet-line-information {
           list media-alarm {
             leaf media-alarm-name {
               type string;
             }
             leaf media-alarm-seconds {
               type int32;
             }
             leaf media-alarm-count {
               type int32;
             }
             leaf media-alarm-state {
               type string;
             }
           }
         }
         container sonet-path-information {
           list media-alarm {
             leaf media-alarm-name {
               type string;
             }
             leaf media-alarm-seconds {
               type int32;
             }
             leaf media-alarm-count {
               type int32;
             }
             leaf media-alarm-state {
               type string;
             }
           }
         }
         container sonet-vt-information {
           list media-alarm {
             leaf media-alarm-name {
               type string;
             }
             leaf media-alarm-seconds {
               type int32;
             }
             leaf media-alarm-count {
               type int32;
             }
             leaf media-alarm-state {
               type string;
             }
           }
         }
         container otn-errors {
           list media-alarm {
             leaf media-alarm-name {
               type string;
             }
             leaf media-alarm-count {
               type int32;
             }
           }
         }
         container otn-fec-statistics {
           leaf fec-corrected-errors {
             type int32;
           }
           leaf fec-valid-time {
             type int32;
           }
           leaf fec-corrected-error-ratio {
             type int32;
           }
           leaf fec-uncorrected-words {
             type int32;
           }
         }
         container otn-fec-alarms {
           description
             "OTN degraded and excessive FEC error rates";
           list media-alarm {
             leaf media-alarm-name {
               type string;
             }
             leaf media-alarm-seconds {
               type int32;
             }
             leaf media-alarm-count {
               type int32;
             }
             leaf media-alarm-state {
               type string;
             }
           }
         }
         container otn-fec-mode {
           leaf fec-mode {
             type string;
             description
               "Optics FEC mode";
           }
         }
         container otn-otn-mode {
           leaf otn-mode {
             type string;
           }
         }
         container otn-otn-rate {
           leaf otn-rate {
             type string;
           }
         }
         container otn-otn-loopback {
           leaf otn-loopback {
             type string;
           }
         }
         container otn-local-loopback {
           leaf local-loopback {
             type string;
           }
         }
         container otn-payload-prbs {
           leaf payload-prbs {
             type string;
           }
         }
         container otn-laser-enable {
           leaf laser-enable {
             type string;
             description
               "Optics laser status";
           }
         }
         container media-information {
           description
             "Information about media alarms";
           leaf media-type {
             type string;
             description
               "Type of media this information is for";
           }
           list media-alarm {
             leaf media-alarm-name {
               type string;
             }
             leaf media-alarm-count {
               type int32;
             }
             leaf media-alarm-seconds {
               type int32;
             }
             leaf media-alarm-state {
               type string;
             }
             leaf ce-counter-name {
               type string;
               description
                 "Circuit Emulation counter information";
             }
             leaf ce-counter-packets {
               type int32;
               description
                 "Circuit Emulation number of packets";
             }
             leaf ce-counter-bytes {
               type int32;
               description
                 "Circuit Emulation number of bytes";
             }
             leaf ce-counter-count {
               type int32;
               description
                 "Circuit Emulation number of event occurrences";
             }
           }
           leaf ds1-timeslots {
             type string;
           }
           leaf ds1-line-encoding {
             type string;
           }
           leaf ds1-byte-encoding {
             type string;
           }
           leaf ds1-data-inversion {
             type string;
           }
           leaf idle-cycle-flag {
             type string;
           }
           leaf start-end-flag {
             type string;
           }
           leaf ds0-byte-encoding {
             type string;
           }
           leaf ds0-data-inversion {
             type string;
           }
           leaf e3-data-inversion {
             type string;
           }
           leaf ds1-buildout {
             type string;
             description
               "Number of feet";
           }
         }
         container ethernet-pcs-statistics {
           description
             "Ethernet PCS statistics";
           leaf bit-error-seconds {
             type int32;
             description
               "Bit error duration";
           }
           leaf errored-blocks-seconds {
             type int32;
             description
               "Errored blocks duration";
           }
         }
         container ethernet-fec-mode {
           description
             "Ethernet FEC Mode";
           leaf enabled_fec_mode {
             type string;
             description
               "Enabled FEC mode: <NONE/FEC74/FEC91/FEC108>";
           }
         }
         container ethernet-fec-statistics {
           description
             "Ethernet FEC statistics";
           leaf fec_ccw_count {
             type int32;
             description
               "FEC Corrected Error Count";
           }
           leaf fec_nccw_count {
             type int32;
             description
               "FEC Uncorrected Error Count";
           }
           leaf fec_ccw_error_rate {
             type int32;
             description
               "FEC Corrected Error Rate (errors/sec)";
           }
           leaf fec_nccw_error_rate {
             type int32;
             description
               "FEC Uncorrected Error Rate (errors/sec)";
           }
         }
         container ctle {
           description
             "Ctle ";
           leaf ctle_value {
             type int32;
             description
               "Ctle value";
           }
         }
         container pre-emphasis {
           description
             "Pre-emphasis ";
           leaf pre_emphasis_value {
             type int32;
             description
               "Pre-emphasis value";
           }
         }
         container differential-amplitude {
           description
             "Differential-amplitude ";
           leaf differential_amplitude_value {
             type int32;
             description
               "Differential-amplitude value";
           }
         }
         container ethernet-mac-statistics {
           description
             "Ethernet MAC statistics";
           leaf input-bytes {
             type int32;
           }
           leaf input-packets {
             type int32;
           }
           leaf output-bytes {
             type int32;
           }
           leaf output-packets {
             type int32;
           }
           leaf input-undersized-frames {
             type int32;
           }
           leaf input-unicasts {
             type int32;
           }
           leaf output-unicasts {
             type int32;
           }
           leaf input-broadcasts {
             type int32;
           }
           leaf output-broadcasts {
             type int32;
           }
           leaf input-multicasts {
             type int32;
           }
           leaf output-multicasts {
             type int32;
           }
           leaf input-crc-errors {
             type int32;
           }
           leaf output-crc-errors {
             type int32;
           }
           leaf input-fifo-errors {
             type int32;
           }
           leaf output-fifo-errors {
             type int32;
           }
           leaf input-dma-errors {
             type int32;
           }
           leaf output-dma-errors {
             type int32;
           }
           leaf input-mac-control-frames {
             type int32;
           }
           leaf output-mac-control-frames {
             type int32;
           }
           leaf input-mac-pause-frames {
             type int32;
           }
           leaf output-mac-pause-frames {
             type int32;
           }
           leaf input-oversized-frames {
             type int32;
           }
           leaf input-jabber-frames {
             type int32;
           }
           leaf input-fragment-frames {
             type int32;
           }
           leaf input-vlan-tagged-frames {
             type int32;
           }
           leaf input-code-violations {
             type int32;
           }
           leaf input-total-errors {
             type int32;
           }
           leaf output-total-errors {
             type int32;
           }
           leaf input-policer-frame-drops {
             type int32;
           }
           leaf input-policer-byte-drops {
             type int32;
           }
         }
         container ethernet-prbs-mode {
           description
             "PRBS Mode";
           leaf prbs-mode {
             type string;
             description
               "PRBS Mode: <Enabled/Disabled>";
           }
         }
         container ethernet-prbs-statistics {
           description
             "Ethernet PRBS statistics";
           leaf prbs-lane {
             type int32;
             description
               "PRBS Lane";
           }
           leaf prbs-state {
             type string;
             description
               "PRBS State";
           }
           leaf prbs-error-count {
             type int32;
             description
               "PRBS Error Count";
           }
         }
         container smart-sfp-configurable-type {
           leaf smart-sfp-tdm-management {
             type string;
           }
         }
         container smart-sfp-type {
           leaf smart-sfp-module-type {
             type string;
           }
           leaf smart-sfp-present {
             type string;
           }
         }
         container smart-sfp-config {
           leaf tdm-loopback {
             type string;
           }
           leaf dmac-check-enable {
             type string;
           }
           leaf encap-ecid {
             type int32;
           }
           leaf decap-ecid {
             type int32;
           }
           leaf vlan-id-1 {
             type int32;
           }
           leaf vlan-id-2 {
             type int32;
           }
           leaf mode {
             type string;
           }
           leaf chan-dmac {
             type jt:mac-addr;
           }
         }
         container smart-sfp-oc3-statistics {
           leaf fcs-error-count {
             type uint32;
           }
           leaf sec-sefs {
             type uint32;
           }
           leaf sec-es {
             type uint32;
           }
           leaf sec-es-min15 {
             type uint32;
           }
           leaf sec-ses {
             type uint32;
           }
           leaf sec-ses-min15 {
             type uint32;
           }
           leaf sec-cv {
             type uint32;
           }
           leaf sec-cv-min15 {
             type uint32;
           }
           leaf line-es {
             type uint32;
           }
           leaf line-es-min15 {
             type uint32;
           }
           leaf line-ses {
             type uint32;
           }
           leaf line-ses-min15 {
             type uint32;
           }
           leaf line-cv {
             type uint32;
           }
           leaf line-cv-min15 {
             type uint32;
           }
           leaf line-uas {
             type uint32;
           }
           leaf line-uas-min15 {
             type uint32;
           }
           leaf path-es {
             type uint32;
           }
           leaf path-es-min15 {
             type uint32;
           }
           leaf path-ses {
             type uint32;
           }
           leaf path-ses-min15 {
             type uint32;
           }
           leaf path-cv {
             type uint32;
           }
           leaf path-cv-min15 {
             type uint32;
           }
           leaf path-uas {
             type uint32;
           }
           leaf path-uas-min15 {
             type uint32;
           }
         }
         container smart-sfp-e1t1-statistics {
           leaf e1t1-es {
             type uint32;
           }
           leaf e1t1-es-min15 {
             type uint32;
           }
           leaf e1t1-ses {
             type uint32;
           }
           leaf e1t1-ses-min15 {
             type uint32;
           }
           leaf e1t1-uas {
             type uint32;
           }
           leaf e1t1-uas-min15 {
             type uint32;
           }
           leaf e1t1-bes {
             type uint32;
           }
           leaf e1t1-bes-min15 {
             type uint32;
           }
           leaf e1t1-les {
             type uint32;
           }
           leaf e1t1-les-min15 {
             type uint32;
           }
           leaf e1t1-pes {
             type uint32;
           }
           leaf e1t1-pes-min15 {
             type uint32;
           }
           leaf e1t1-psess {
             type uint32;
           }
           leaf e1t1-psess-min15 {
             type uint32;
           }
           leaf e1t1-ces {
             type uint32;
           }
           leaf e1t1-ces-min15 {
             type uint32;
           }
           leaf e1t1-cses {
             type uint32;
           }
           leaf e1t1-cses-min15 {
             type uint32;
           }
           leaf e1t1-sefs {
             type uint32;
           }
           leaf e1t1-sefs-min15 {
             type uint32;
           }
         }
         container smart-sfp-e3t3-statistics {
           leaf e3t3-les {
             type uint32;
           }
           leaf e3t3-les-min15 {
             type uint32;
           }
           leaf e3t3-pes {
             type uint32;
           }
           leaf e3t3-pes-min15 {
             type uint32;
           }
           leaf e3t3-psess {
             type uint32;
           }
           leaf e3t3-psess-min15 {
             type uint32;
           }
           leaf e3t3-ces {
             type uint32;
           }
           leaf e3t3-ces-min15 {
             type uint32;
           }
           leaf e3t3-cses {
             type uint32;
           }
           leaf e3t3-cses-min15 {
             type uint32;
           }
           leaf e3t3-sefs {
             type uint32;
           }
           leaf e3t3-sefs-min15 {
             type uint32;
           }
           leaf e3t3-uas {
             type uint32;
           }
           leaf e3t3-uas-min15 {
             type uint32;
           }
         }
         container fibrechannel-port-flow-control {
           description
             "Fibre Channel interface flow control";
           leaf fibrechannel-port-flow-control-mode {
             type string;
           }
           list fibrechannel-port-flow-control-credits {
             description
               "Generic flow control credits";
             leaf fibrechannel-port-flow-control-credits-subject {
               type string;
             }
             leaf fibrechannel-port-flow-control-credits-assigned {
               type uint64;
             }
             leaf fibrechannel-port-flow-control-credits-available {
               type uint64;
             }
           }
         }
         container fibrechannel-mac-statistics {
           description
             "Fibre Channel MAC statistics";
           container fibrechannel-mac-statistics-generic {
             leaf link-failures {
               type uint64;
             }
             leaf loss-of-sync {
               type uint64;
             }
             leaf loss-of-signal {
               type uint64;
             }
             leaf sw-link-resets {
               type uint64;
             }
             leaf buffer-to-buffer-credit-recovery-lost-frames {
               type uint64;
             }
             leaf buffer-to-buffer-credit-recovery-lost-rrdys {
               type uint64;
             }
           }
           container fibrechannel-mac-statistics-received {
             leaf rx-class-2-frames {
               type uint64;
             }
             leaf rx-class-2-octets {
               type uint64;
             }
             leaf rx-class-3-frames {
               type uint64;
             }
             leaf rx-class-3-octets {
               type uint64;
             }
             leaf rx-class-f-frames {
               type uint64;
             }
             leaf rx-class-f-octets {
               type uint64;
             }
             leaf class-2-discards {
               type uint64;
             }
             leaf class-3-discards {
               type uint64;
             }
             leaf class-f-discards {
               type uint64;
             }
             leaf rx-frames-too-long {
               type uint64;
             }
             leaf rx-frames-too-short {
               type uint64;
             }
             leaf rx-missing-eof {
               type uint64;
             }
             leaf rx-invalid-crcs {
               type uint64;
             }
             leaf rx-link-resets {
               type uint64;
             }
             leaf rx-link-reset-responses {
               type uint64;
             }
             leaf rx-offlines {
               type uint64;
             }
             leaf rx-not-operationals {
               type uint64;
             }
             leaf rx-invalid-tx-words {
               type uint64;
             }
             leaf rx-encoding-disparity-errors {
               type uint64;
             }
             leaf rx-delimiter-errors {
               type uint64;
             }
             leaf rx-input-buffers-full {
               type uint64;
             }
             leaf rx-invalid-ordered-sets {
               type uint64;
             }
             leaf rx-prim-seq-protocol-errors {
               type uint64;
             }
             leaf rx-other-errors {
               type uint64;
             }
           }
           container fibrechannel-mac-statistics-transmitted {
             leaf tx-class-2-frames {
               type uint64;
             }
             leaf tx-class-2-octets {
               type uint64;
             }
             leaf tx-class-3-frames {
               type uint64;
             }
             leaf tx-class-3-octets {
               type uint64;
             }
             leaf tx-class-f-frames {
               type uint64;
             }
             leaf tx-class-f-octets {
               type uint64;
             }
             leaf tx-link-resets {
               type uint64;
             }
             leaf tx-link-reset-responses {
               type uint64;
             }
             leaf tx-offlines {
               type uint64;
             }
             leaf tx-not-operationals {
               type uint64;
             }
             leaf tx-bb-credit-zeroes {
               type uint64;
             }
             leaf tx-other-errors {
               type uint64;
             }
           }
         }
         container ethernet-filter-statistics {
           description
             "Ethernet filter statistics";
           leaf input-reject-count {
             type int32;
           }
           leaf output-packet-pad-count {
             type int32;
           }
           leaf output-packet-error-count {
             type int32;
           }
           leaf input-packets {
             type int32;
           }
           leaf input-reject-destination-address-count {
             type int32;
           }
           leaf input-reject-source-address-count {
             type int32;
           }
           leaf output-packets {
             type int32;
           }
           leaf cam-destination-filter-count {
             type int32;
           }
           leaf cam-source-filter-count {
             type int32;
           }
         }
         container ethernet-autonegotiation {
           description
             "Ethernet autonegotiation information";
         }
         container mac-database {
         }
         container dsl-information {
           description
             "Operational information and statistics for ADSL interfaces";
           container dsl-statistics {
             leaf interleaved-rx-cells {
               type int32;
               description
                 "Interleaved receiver cells";
             }
             leaf fast-rx-cells {
               type int32;
               description
                 "Fast receiver cells";
             }
             leaf interleaved-tx-cells {
               type int32;
               description
                 "Interleaved transmitter cells";
             }
             leaf fast-tx-cells {
               type int32;
               description
                 "Fast transmitter cells";
             }
           }
         }
         container vdsl-information {
           description
             "Operational information and statistics for VDSL interfaces";
         }
         container shdsl-information {
           description
             "Operational information and statistics for SHDSL interfaces";
         }
         container efm-information {
           description
             "Operational information and statistics for EFM interfaces";
           container efm-line-statistics {
             container active-alarms-efm {
             }
             container active-defects-efm {
             }
             container media-information {
               description
                 "Information about media alarms";
               leaf media-type {
                 type string;
                 description
                   "Type of media this information is for";
               }
               list media-alarm {
                 leaf media-alarm-name {
                   type string;
                 }
                 leaf media-alarm-count {
                   type int32;
                 }
                 leaf media-alarm-seconds {
                   type int32;
                 }
                 leaf media-alarm-state {
                   type string;
                 }
                 leaf ce-counter-name {
                   type string;
                   description
                     "Circuit Emulation counter information";
                 }
                 leaf ce-counter-packets {
                   type int32;
                   description
                     "Circuit Emulation number of packets";
                 }
                 leaf ce-counter-bytes {
                   type int32;
                   description
                     "Circuit Emulation number of bytes";
                 }
                 leaf ce-counter-count {
                   type int32;
                   description
                     "Circuit Emulation number of event occurrences";
                 }
               }
               leaf ds1-timeslots {
                 type string;
               }
               leaf ds1-line-encoding {
                 type string;
               }
               leaf ds1-byte-encoding {
                 type string;
               }
               leaf ds1-data-inversion {
                 type string;
               }
               leaf idle-cycle-flag {
                 type string;
               }
               leaf start-end-flag {
                 type string;
               }
               leaf ds0-byte-encoding {
                 type string;
               }
               leaf ds0-data-inversion {
                 type string;
               }
               leaf e3-data-inversion {
                 type string;
               }
               leaf ds1-buildout {
                 type string;
                 description
                   "Number of feet";
               }
             }
             container shdsl-information {
               description
                 "Operational information and statistics for SHDSL 
                 interfaces";
             }
           }
         }
         container atm-information {
           description
             "Operational information and statistics for ATM interfaces";
           container plcp-defects {
           }
           container atm-defects {
           }
         }
         container serial-information {
           description
             "Serial interfaces information and statistics";
           leaf dce-loopback-override {
             type string;
           }
           container eia530-control-signal {
           }
         }
         container virtual-path-information {
           description
             "Operational information and statistics for a virtual path";
           leaf cdvt {
             type int32;
           }
           container traffic-statistics {
             leaf input-bps {
               type int32;
             }
             leaf input-pps {
               type int32;
             }
             leaf output-bps {
               type int32;
             }
             leaf output-pps {
               type int32;
             }
             leaf input-packets {
               type int32;
             }
             leaf output-packets {
               type int32;
             }
             leaf input-bytes {
               type int32;
             }
             leaf output-bytes {
               type int32;
             }
             container ipv6-transit-statistics {
               leaf input-bytes {
                 type int32;
               }
               leaf output-bytes {
                 type int32;
               }
               leaf input-packets {
                 type int32;
               }
               leaf output-packets {
                 type int32;
               }
             }
             container ipv6-total-statistics {
               leaf input-bytes {
                 type int32;
               }
               leaf output-bytes {
                 type int32;
               }
               leaf input-packets {
                 type int32;
               }
               leaf output-packets {
                 type int32;
               }
             }
           }
         }
         container ct3-information {
           list interface-tx-queue {
             leaf output-drops-bytes {
               type int32;
             }
           }
         }
         container cds1-information {
           list interface-tx-queue {
             leaf output-drops-bytes {
               type int32;
             }
           }
         }
         container nxds0-information {
           list interface-tx-queue {
             leaf output-drops-bytes {
               type int32;
             }
           }
         }
         list logical-interface {
           key "name";
           description
             "Information about a single logical interface";
           leaf name {
             type string;
             description
               "Name of this item";
           }
           leaf admin-status {
             type string;
             description
               "Desired state of the interface";
           }
           leaf oper-status {
             type string;
             description
               "Current operational state of the interface";
           }
           leaf vrfname {
             type string;
             description
               "Routing instance name";
           }
           leaf zonename {
             type string;
             description
               "Zone name";
           }
           leaf subunit {
             type int32;
             description
               "Subunit for this interface";
           }
           leaf dialer-time-to-disconnect {
             type string;
             description
               "Time for dialer to disconnect due to idle timeout";
           }
           leaf lcp-state {
             type string;
             description
               "State of the Line Control Protocol";
           }
           leaf chap-state {
             type string;
             description
               "State of the Challenge Handshake Authentication Protocol";
           }
           leaf pap-state {
             type string;
             description
               "State of the Password Authentication Protocol";
           }
           container layer2-input-policer-information {
             description
               "Information about Layer 2 input policer for interface";
             leaf layer2-input-policer {
               type string;
               description
                 "Name of the Layer 2 input policer";
             }
           }
           container layer2-output-policer-information {
             description
               "Information about Layer 2 output policer for interface";
             leaf layer2-output-policer {
               type string;
               description
                 "Name of the Layer 2 output policer";
             }
           }
           container pppoe-information {
             description
               "PPPoE information";
             list pppoe-interface {
               leaf state {
                 type string;
                 description
                   "State";
               }
               leaf session-id {
                 type string;
                 description
                   "Session ID";
               }
               leaf ac-name-session {
                 type string;
                 description
                   "Session AC name";
               }
               leaf remote-mac {
                 type string;
                 description
                   "Remote MAC address";
               }
               leaf ac-name-config {
                 type string;
                 description
                   "Configured AC name";
               }
               leaf service-name {
                 type string;
                 description
                   "Service name";
               }
               leaf auto-reconnect {
                 type string;
                 description
                   "Autoreconnect timeout";
               }
               leaf idle-timeout {
                 type string;
                 description
                   "Idle timeout";
               }
               leaf underlying-interface-name {
                 type string;
                 description
                   "Underlying interface name";
               }
               leaf underlying-interface-index {
                 type string;
                 description
                   "Underlying interface index";
               }
               leaf padg-credits {
                 type int32;
                 description
                   "PADG transmit credits";
               }
               leaf pppoe-credit-scale-factor {
                 type string;
                 description
                   "Scaling factor";
               }
               leaf ignore-eol-tag {
                 type string;
                 description
                   "Ignore End-of-List TAG";
               }
               leaf ppp-max-payload-tag {
                 type int32;
                 description
                   "PPP-Max-Payload TAG";
               }
               leaf interface-name {
                 type string;
                 description
                   "Class-of-service interface name";
               }
               leaf interface-index {
                 type uint32;
                 description
                   "Class-of-service interface index";
               }
               leaf aci-iflset-name {
                 type string;
                 description
                   "ACI Interface Set name";
               }
               leaf aci-iflset-index {
                 type string;
                 description
                   "ACI Interface Set index";
               }
               leaf ifl-type {
                 type string;
                 description
                   "Type";
               }
               leaf session-uptime {
                 type string;
                 description
                   "Duration for which the session has been up";
               }
               leaf dynamic-profile {
                 type string;
                 description
                   "Dynamic Profile name";
               }
               leaf pppoe-credits {
                 type string;
                 description
                   "Forwarding credit balances";
               }
               leaf dynamic-interface-bandwidth {
                 type string;
                 description
                   "Dynamic interface bandwidth";
               }
               leaf agent-circuit-id {
                 type string;
                 description
                   "Agent Circuit ID";
               }
               leaf agent-remote-id {
                 type string;
                 description
                   "Agent Remote ID";
               }
               leaf padm-motm {
                 type string;
                 description
                   "PADM Message of the Moment tag";
               }
               leaf padm-hurl {
                 type string;
                 description
                   "PADM HTTP URL tag";
               }
             }
           }
           container pppoe-underlying-information {
             description
               "PPPoE Underlying information";
             list pppoe-underlying-interface {
               leaf dynamic-profile {
                 type string;
                 description
                   "Dynamic Profile name";
               }
               leaf service-name-table {
                 type string;
                 description
                   "Name of Service Name Table";
               }
               leaf max-sessions {
                 type int32;
                 description
                   "Maximum number of PPPoE sessions";
               }
               leaf max-sessions-vsa-ignore {
                 type string;
                 description
                   "Ignore max-sessions VSA";
               }
               leaf duplicate-protection {
                 type string;
                 description
                   "Duplicate protection mode";
               }
               leaf short-cycle-protection {
                 type string;
                 description
                   "Short cycle protection mode";
               }
               leaf direct-connect {
                 type string;
                 description
                   "Direct connect mode";
               }
               leaf ac-name {
                 type string;
                 description
                   "Access Concentrator name";
               }
               leaf underlying-interface-name {
                 type string;
                 description
                   "Underlying interface name";
               }
               leaf underlying-interface-index {
                 type string;
                 description
                   "Underlying interface index";
               }
               leaf encapsulation-type-identifier {
                 type string;
                 description
                   "Encapsulation type identifier";
               }
               leaf state {
                 type string;
                 description
                   "State";
               }
               leaf active-sessions {
                 type int32;
                 description
                   "Number of active PPPoE sessions";
               }
               leaf aci-autosensing {
                 type string;
                 description
                   "ACI VLAN Autosensing mode";
               }
               leaf line-identity-autosensing {
                 type string;
                 description
                   "Line Identity Autosensing mode";
               }
             }
           }
           container aci-vlan-information {
             leaf dynamic-profile {
               type string;
               description
                 "Dynamic Profile name";
             }
           }
           container line-identity-information {
             leaf dynamic-profile {
               type string;
               description
                 "Dynamic Profile name";
             }
             leaf circuit-id {
               type string;
               description
                 "Aci vlan attribute";
             }
             leaf remote-id {
               type string;
               description
                 "Aci vlan attribute";
             }
             leaf accept-no-ids {
               type string;
               description
                 "Aci vlan attribute";
             }
           }
           container demux-information {
             description
               "Demux information";
             container demux-interface {
               leaf demux-underlying-interface-name {
                 type string;
                 description
                   "Underlying interface name";
               }
               leaf demux-underlying-interface-index {
                 type string;
                 description
                   "Underlying interface index";
               }
               leaf demux-inet-prefix-type {
                 type string;
                 description
                   "Prefix type";
               }
               leaf demux-inet-prefix-count {
                 type string;
                 description
                   "IPv4 Prefix count";
               }
               leaf demux-inet-prefix {
                 type string;
                 description
                   "IPv4 Prefix";
               }
               leaf demux-inet6-prefix-type {
                 type string;
                 description
                   "Prefix type";
               }
               leaf demux-inet6-prefix-count {
                 type string;
                 description
                   "IPv6 Prefix count";
               }
               leaf demux-inet6-prefix {
                 type string;
                 description
                   "IPv6 Prefix";
               }
             }
           }
           container dual-ad-icl-color-information {
             container dual-ad-icl-color-info {
               description
                 "Dual-AD ICL Color Information";
               leaf dual-ad-icl-color-type {
                 type uint32;
                 description
                   "Dual-AD ICL Color Type";
               }
               leaf dual-ad-icl-color {
                 type uint32;
                 description
                   "Dual-AD ICL Color";
               }
             }
           }
           container dialer-information {
             description
               "Dialer information";
             leaf dialer-time-to-disconnect {
               type string;
               description
                 "Time for dialer to disconnect due to idle timeout";
             }
             container dialer-interface {
               leaf dialer-interface-name {
                 type string;
                 description
                   "Interface name";
               }
               leaf dialer-interface-state {
                 type string;
                 description
                   "Dialer interface state";
               }
               leaf pool-id {
                 type string;
                 description
                   "Pool identifier";
               }
               leaf primary-interface {
                 type string;
                 description
                   "Primary interface";
               }
               leaf activation-delay {
                 type string;
                 description
                   "Activation delay";
               }
               leaf deactivation-delay {
                 type string;
                 description
                   "Deactivation delay";
               }
               leaf activation-delay-elapsed {
                 type string;
                 description
                   "Activation delay elapsed";
               }
               leaf deactivation-delay-elapsed {
                 type string;
                 description
                   "Deactivation delay elapsed";
               }
               leaf call-idle-timeout {
                 type string;
                 description
                   "Call idle timeout";
               }
               leaf initial-route-check {
                 type string;
                 description
                   "Initial route check delay";
               }
               leaf redial-delay {
                 type string;
                 description
                   "Delay before dialer dials out again (seconds)";
               }
               leaf callback-wait-period {
                 type string;
                 description
                   "Delay before dialer attempts callback (seconds)";
               }
               leaf callback-wait-period-elapsed {
                 type string;
                 description
                   "Number of seconds in callback wait period that have 
                   elapsed";
               }
               leaf load-threshold {
                 type string;
                 description
                   "Load threshold that determines when interfaces are added
                   to bundle";
               }
               leaf load-interval {
                 type string;
                 description
                   "Interval over which average load is calculated";
               }
               container dialer-interface-flags {
                 description
                   "Flags indicating interface configuration";
                 leaf backup {
                   type empty;
                   description
                     "Dialer backup";
                 }
                 leaf multilink {
                   type empty;
                   description
                     "Dialer multilink";
                 }
                 leaf watchlist {
                   type empty;
                   description
                     "Dialer watchlist";
                 }
                 leaf interesting-detected {
                   type empty;
                   description
                     "Interesting packet detected";
                 }
               }
             }
           }
           container shared-interface-information {
             description
               "Shared interface information";
             container shared-interface-logical-interface {
               description
                 "Shared interface logical interface";
               leaf peer-interface-name {
                 type string;
                 description
                   "Peer interface name";
               }
               leaf interface-shared-with {
                 type string;
                 description
                   "Logical interface owner";
               }
               leaf rx-fe {
                 type string;
                 description
                   "Rx tunnel token forwarding element";
               }
               leaf rx-nhid {
                 type string;
                 description
                   "Rx tunnel token next hop index";
               }
               leaf tx-fe {
                 type string;
                 description
                   "Tx tunnel token forwarding element";
               }
               leaf tx-nhid {
                 type string;
                 description
                   "Tx tunnel token next hop index";
               }
             }
           }
           container mac-database {
           }
           container queue-counters {
             description
               "Queue counter statistics";
             leaf queue-counters-error-message {
               type string;
               description
                 "Queue statistics not available for this interface";
             }
             list queue {
               description
                 "Counters for a single queue";
               leaf queue-number {
                 type int32;
                 description
                   "Queue number";
               }
               leaf queue-counters-queued-packets {
                 type uint64;
                 description
                   "Queued packet count";
               }
               leaf queue-counters-trans-packets {
                 type uint64;
                 description
                   "Total number of transmitted packets";
               }
               leaf queue-counters-total-drop-packets {
                 type uint64;
                 description
                   "Number of total packets dropped at the queue";
               }
               leaf forwarding-class-name {
                 type string;
                 description
                   "Forwarding class name associated with queue";
               }
               leaf queue-counters-queued-packets-rate {
                 type uint64;
                 description
                   "Rate at which packets are queued";
               }
               leaf queue-counters-queued-bytes {
                 type uint64;
                 description
                   "Queued bytes count";
               }
               leaf queue-counters-queued-bytes-rate {
                 type uint64;
                 description
                   "Rate at which bytes are queued";
               }
               leaf queue-counters-queued-packets-na {
                 type string;
                 description
                   "Queued packets not available";
               }
               leaf queue-counters-queued-bytes-na {
                 type string;
                 description
                   "Queued bytes not available";
               }
               leaf queue-counters-trans-packets-rate {
                 type uint64;
                 description
                   "Rate at which packets are transmitted";
               }
               leaf queue-counters-trans-bytes {
                 type uint64;
                 description
                   "Total number of transmitted bytes";
               }
               leaf queue-counters-trans-bytes-rate {
                 type uint64;
                 description
                   "Rate at which bytes are transmitted";
               }
               leaf queue-counters-tail-drop-packets-na {
                 type string;
                 description
                   "Number of packets dropped due to tail drop not available";
               }
               leaf queue-counters-tail-drop-packets {
                 type uint64;
                 description
                   "Number of packets dropped at the tail of the queue";
               }
               leaf queue-counters-tail-drop-packets-rate {
                 type uint64;
                 description
                   "Rate at which packets are dropped at tail of queue";
               }
               leaf queue-counters-tail-drop-bytes {
                 type uint64;
                 description
                   "Number of packets dropped at tail drop of the queue";
               }
               leaf queue-counters-tail-drop-bytes-rate {
                 type uint64;
                 description
                   "Number of packets dropped at tail drop of the queue";
               }
               leaf queue-counters-rate-limit-drop-packets-na {
                 type string;
                 description
                   "Number of packets dropped due to rate-limit drop not 
                   available";
               }
               leaf queue-counters-rate-limit-drop-packets {
                 type uint64;
                 description
                   "Number of packets dropped by rate-limit for the queue";
               }
               leaf queue-counters-rate-limit-drop-packets-rate {
                 type uint64;
                 description
                   "Rate at which packets are dropped by rate-limit for the 
                   queue";
               }
               leaf queue-counters-rate-limit-drop-bytes-na {
                 type string;
                 description
                   "Number of bytes dropped due to tail drop not available";
               }
               leaf queue-counters-rate-limit-drop-bytes {
                 type uint64;
                 description
                   "Number of bytes dropped at the tail of the queue";
               }
               leaf queue-counters-rate-limit-drop-bytes-rate {
                 type uint64;
                 description
                   "Rate at which bytes are dropped at the tail of the queue";
               }
               leaf queue-counters-red-packets-na {
                 type string;
                 description
                   "Number of packets dropped due to RED not available";
               }
               leaf queue-counters-red-packets {
                 type uint64;
                 description
                   "Number of packets dropped due to RED";
               }
               leaf queue-counters-red-packets-rate {
                 type uint64;
                 description
                   "Rate at which packets are dropped due to RED";
               }
               leaf queue-counters-red-packets-ln {
                 type uint64;
                 description
                   "Number of RED dropped low-loss, non-TCP packets";
               }
               leaf queue-counters-red-packets-rate-ln {
                 type uint64;
                 description
                   "RED drop rate for low-loss, non-TCP packets";
               }
               leaf queue-counters-red-packets-lt {
                 type uint64;
                 description
                   "Number of RED dropped of low-loss, TCP packets";
               }
               leaf queue-counters-red-packets-rate-lt {
                 type uint64;
                 description
                   "RED drop rate for low-loss, TCP packets";
               }
               leaf queue-counters-red-packets-hn {
                 type uint64;
                 description
                   "Number of RED dropped high-loss, non-TCP packets";
               }
               leaf queue-counters-red-packets-rate-hn {
                 type uint64;
                 description
                   "RED drop rate for high-loss, non-TCP packets";
               }
               leaf queue-counters-red-packets-ht {
                 type uint64;
                 description
                   "Number of RED dropped high-loss, TCP packets";
               }
               leaf queue-counters-red-packets-rate-ht {
                 type uint64;
                 description
                   "RED drop rate for high-loss, TCP packets";
               }
               leaf queue-counters-red-packets-low {
                 type uint64;
                 description
                   "Number of RED dropped low-loss packets";
               }
               leaf queue-counters-red-packets-rate-low {
                 type uint64;
                 description
                   "RED drop rate for low-loss packets";
               }
               leaf queue-counters-red-packets-medium-low {
                 type uint64;
                 description
                   "Number of RED dropped medium-low-loss packets";
               }
               leaf queue-counters-red-packets-rate-medium-low {
                 type uint64;
                 description
                   "RED drop rate for medium-low-loss packets";
               }
               leaf queue-counters-red-packets-medium-high {
                 type uint64;
                 description
                   "Number of RED dropped medium-high-loss packets";
               }
               leaf queue-counters-red-packets-rate-medium-high {
                 type uint64;
                 description
                   "RED drop rate for medium-high-loss packets";
               }
               leaf queue-counters-red-packets-medium {
                 type uint64;
                 description
                   "Number of RED dropped medium-loss packets";
               }
               leaf queue-counters-red-packets-rate-medium {
                 type uint64;
                 description
                   "RED drop rate for medium-loss packets";
               }
               leaf queue-counters-red-packets-high {
                 type uint64;
                 description
                   "Number of RED dropped high-loss packets";
               }
               leaf queue-counters-red-packets-rate-high {
                 type uint64;
                 description
                   "RED drop rate for high-loss packets";
               }
               leaf queue-counters-red-bytes-na {
                 type string;
                 description
                   "Number of bytes dropped due to RED not available";
               }
               leaf queue-counters-red-bytes {
                 type uint64;
                 description
                   "Number of bytes dropped due to RED";
               }
               leaf queue-counters-red-bytes-rate {
                 type uint64;
                 description
                   "Rate at which bytes are dropped due to RED";
               }
               leaf queue-counters-red-bytes-ln {
                 type uint64;
                 description
                   "Number of RED dropped low-loss, non-TCP bytes";
               }
               leaf queue-counters-red-bytes-rate-ln {
                 type uint64;
                 description
                   "RED drop rate for low-loss, non-TCP bytes";
               }
               leaf queue-counters-red-bytes-lt {
                 type uint64;
                 description
                   "Number of RED dropped low-loss, TCP bytes";
               }
               leaf queue-counters-red-bytes-rate-lt {
                 type uint64;
                 description
                   "RED drop rate for low-loss, TCP bytes";
               }
               leaf queue-counters-red-bytes-hn {
                 type uint64;
                 description
                   "Number of RED dropped high-loss, non-TCP bytes";
               }
               leaf queue-counters-red-bytes-rate-hn {
                 type uint64;
                 description
                   "RED drop rate for high-loss, non-TCP bytes";
               }
               leaf queue-counters-red-bytes-ht {
                 type uint64;
                 description
                   "Number of RED dropped high-loss, TCP bytes";
               }
               leaf queue-counters-red-bytes-rate-ht {
                 type uint64;
                 description
                   "RED drop rate for high-loss, TCP bytes";
               }
               leaf queue-counters-red-bytes-low {
                 type uint64;
                 description
                   "Number of RED dropped low-loss bytes";
               }
               leaf queue-counters-red-bytes-rate-low {
                 type uint64;
                 description
                   "RED drop rate for low-loss bytes";
               }
               leaf queue-counters-red-bytes-medium-low {
                 type uint64;
                 description
                   "Number of RED dropped medium-low-loss bytes";
               }
               leaf queue-counters-red-bytes-rate-medium-low {
                 type uint64;
                 description
                   "RED drop rate for medium-low-loss bytes";
               }
               leaf queue-counters-red-bytes-medium-high {
                 type uint64;
                 description
                   "Number of RED dropped medium-high-loss bytes";
               }
               leaf queue-counters-red-bytes-rate-medium-high {
                 type uint64;
                 description
                   "RED drop rate for medium-high-loss bytes";
               }
               leaf queue-counters-red-bytes-medium {
                 type uint64;
                 description
                   "Number of RED dropped medium-loss bytes";
               }
               leaf queue-counters-red-bytes-rate-medium {
                 type uint64;
                 description
                   "RED drop rate for medium-loss bytes";
               }
               leaf queue-counters-red-bytes-high {
                 type uint64;
                 description
                   "Number of RED dropped high-loss bytes";
               }
               leaf queue-counters-red-bytes-rate-high {
                 type uint64;
                 description
                   "RED drop rate for high-loss bytes";
               }
               leaf queue-counters-timestamp {
                 type uint64;
                 description
                   "Last packet enqueued timestamp";
               }
               leaf queue-counters-total-drop-packets-rate {
                 type uint64;
                 description
                   "Number of total packets dropped at the queue";
               }
               leaf queue-counters-total-drop-bytes {
                 type uint64;
                 description
                   "Number of total packets dropped at the queue";
               }
               leaf queue-counters-total-drop-bytes-rate {
                 type uint64;
                 description
                   "Number of total packets dropped at the queue";
               }
               leaf queue-counters-reserved-buffer-packets {
                 type int32;
                 description
                   "Queues's usage of reserved buffer pool in pkts";
               }
               leaf queue-counters-reserved-buffer-bytes {
                 type int32;
                 description
                   "Queues's usage of reserved buffer pool in bytes";
               }
               leaf queue-counters-shared-buffer-packets {
                 type int32;
                 description
                   "Queues's usage of shared buffer pool in pkts";
               }
               leaf queue-counters-shared-buffer-bytes {
                 type int32;
                 description
                   "Queues's usage of shared buffer pool in bytes";
               }
               leaf queue-counters-depth-average {
                 type int32;
                 description
                   "Time averaged queue depth";
               }
               leaf queue-counters-depth-current {
                 type int32;
                 description
                   "Current instantaneous queue depth";
               }
               leaf queue-counters-depth-peak {
                 type int32;
                 description
                   "Peak queue depth";
               }
               leaf queue-counters-depth-max {
                 type int32;
                 description
                   "Maximum queue depth attained";
               }
               leaf queue-counters-srx-reserved-buffer-bytes {
                 type int32;
                 description
                   "Queues's usage of reserved buffer pool in bytes";
               }
               leaf queue-counters-srx-depth-current {
                 type int32;
                 description
                   "Current instantaneous queue depth";
               }
             }
             container interface-cos-short-summary {
               description
                 "Summary of queue information on an interface";
               leaf intf-cos-queue-type {
                 type string;
                 description
                   "Interface queue type";
               }
               leaf intf-cos-num-queues-supported {
                 type int32;
                 description
                   "Number of queues supported on this interface";
               }
               leaf intf-cos-num-queues-in-use {
                 type int32;
                 description
                   "Number of queues currently in use on this interface";
               }
               leaf intf-cos-queue-dedicated-or-shared {
                 type string;
                 description
                   "Interface has dedicated or shared queues";
               }
               leaf intf-cos-sched-resource-type {
                 type string;
                 description
                   "Interface scheduling resource type";
               }
               leaf intf-cos-sched-resource-usage-mic-limit {
                 type int32;
                 description
                   "MIC/PIC scheduling resource usage limit";
               }
               leaf intf-cos-sched-resource-usage-mic-count {
                 type int32;
                 description
                   "MIC/PIC scheduling resource usage count";
               }
               leaf intf-cos-sched-resource-usage-port-limit {
                 type int32;
                 description
                   "Interface scheduling resource limit";
               }
               leaf intf-cos-sched-resource-usage-port-count {
                 type int32;
                 description
                   "Interface scheduling resource usage";
               }
             }
             container interface-cos-summary {
               description
                 "Summary of forwarding class and queue information on an 
                 interface";
               leaf intf-cos-forwarding-classes-supported {
                 type int32;
                 description
                   "Number of forwarding classes supported on this interface";
               }
               leaf intf-cos-forwarding-classes-in-use {
                 type int32;
                 description
                   "Number of forwarding classes currently in use on this 
                   interface";
               }
               leaf intf-cos-queue-type {
                 type string;
                 description
                   "Interface queue type";
               }
               leaf intf-cos-num-queues-supported {
                 type int32;
                 description
                   "Number of queues supported on this interface";
               }
               leaf intf-cos-num-queues-in-use {
                 type int32;
                 description
                   "Number of queues currently in use on this interface";
               }
               leaf intf-cos-queue-dedicated-or-shared {
                 type string;
                 description
                   "Interface has dedicated or shared queues";
               }
               leaf intf-cos-sched-resource-type {
                 type string;
                 description
                   "Interface scheduling resource type";
               }
               leaf intf-cos-sched-resource-usage-mic-limit {
                 type int32;
                 description
                   "MIC/PIC scheduling resource usage limit";
               }
               leaf intf-cos-sched-resource-usage-mic-count {
                 type int32;
                 description
                   "MIC/PIC scheduling resource usage count";
               }
               leaf intf-cos-sched-resource-usage-port-limit {
                 type int32;
                 description
                   "Interface scheduling resource limit";
               }
               leaf intf-cos-sched-resource-usage-port-count {
                 type int32;
                 description
                   "Interface scheduling resource usage";
               }
               leaf intf-cos-burst-size-for-ifl {
                 type int32;
                 description
                   "Burst size for the logical interface";
               }
             }
           }
           container ingress-queue-counters {
             description
               "Ingress queue counter statistics";
             list queue {
               description
                 "Counters for a single queue";
               leaf queue-number {
                 type int32;
                 description
                   "Queue number";
               }
               leaf forwarding-class-name {
                 type string;
                 description
                   "Forwarding class name associated with queue";
               }
               leaf queue-counters-queued-packets {
                 type uint64;
                 description
                   "Queued packet count";
               }
               leaf queue-counters-queued-packets-rate {
                 type uint64;
                 description
                   "Rate at which packets are queued";
               }
               leaf queue-counters-queued-bytes {
                 type uint64;
                 description
                   "Queued bytes count";
               }
               leaf queue-counters-queued-bytes-rate {
                 type uint64;
                 description
                   "Rate at which bytes are queued";
               }
               leaf queue-counters-queued-packets-na {
                 type string;
                 description
                   "Queued packets not available";
               }
               leaf queue-counters-queued-bytes-na {
                 type string;
                 description
                   "Queued bytes not available";
               }
               leaf queue-counters-trans-packets {
                 type uint64;
                 description
                   "Total number of transmitted packets";
               }
               leaf queue-counters-trans-packets-rate {
                 type uint64;
                 description
                   "Rate at which packets are transmitted";
               }
               leaf queue-counters-trans-bytes {
                 type uint64;
                 description
                   "Total number of transmitted bytes";
               }
               leaf queue-counters-trans-bytes-rate {
                 type uint64;
                 description
                   "Rate at which bytes are transmitted";
               }
               leaf queue-counters-tail-drop-packets-na {
                 type string;
                 description
                   "Number of packets dropped due to tail drop not available";
               }
               leaf queue-counters-tail-drop-packets {
                 type uint64;
                 description
                   "Number of packets dropped at the tail of the queue";
               }
               leaf queue-counters-tail-drop-packets-rate {
                 type uint64;
                 description
                   "Rate at which packets are dropped at tail of queue";
               }
               leaf queue-counters-tail-drop-bytes {
                 type uint64;
                 description
                   "Number of packets dropped at tail drop of the queue";
               }
               leaf queue-counters-tail-drop-bytes-rate {
                 type uint64;
                 description
                   "Number of packets dropped at tail drop of the queue";
               }
               leaf queue-counters-rate-limit-drop-packets-na {
                 type string;
                 description
                   "Number of packets dropped due to rate-limit drop not 
                   available";
               }
               leaf queue-counters-rate-limit-drop-packets {
                 type uint64;
                 description
                   "Number of packets dropped by rate-limit for the queue";
               }
               leaf queue-counters-rate-limit-drop-packets-rate {
                 type uint64;
                 description
                   "Rate at which packets are dropped by rate-limit for the 
                   queue";
               }
               leaf queue-counters-rate-limit-drop-bytes-na {
                 type string;
                 description
                   "Number of bytes dropped due to tail drop not available";
               }
               leaf queue-counters-rate-limit-drop-bytes {
                 type uint64;
                 description
                   "Number of bytes dropped at the tail of the queue";
               }
               leaf queue-counters-rate-limit-drop-bytes-rate {
                 type uint64;
                 description
                   "Rate at which bytes are dropped at the tail of the queue";
               }
               leaf queue-counters-red-packets-na {
                 type string;
                 description
                   "Number of packets dropped due to RED not available";
               }
               leaf queue-counters-red-packets {
                 type uint64;
                 description
                   "Number of packets dropped due to RED";
               }
               leaf queue-counters-red-packets-rate {
                 type uint64;
                 description
                   "Rate at which packets are dropped due to RED";
               }
               leaf queue-counters-red-packets-ln {
                 type uint64;
                 description
                   "Number of RED dropped low-loss, non-TCP packets";
               }
               leaf queue-counters-red-packets-rate-ln {
                 type uint64;
                 description
                   "RED drop rate for low-loss, non-TCP packets";
               }
               leaf queue-counters-red-packets-lt {
                 type uint64;
                 description
                   "Number of RED dropped of low-loss, TCP packets";
               }
               leaf queue-counters-red-packets-rate-lt {
                 type uint64;
                 description
                   "RED drop rate for low-loss, TCP packets";
               }
               leaf queue-counters-red-packets-hn {
                 type uint64;
                 description
                   "Number of RED dropped high-loss, non-TCP packets";
               }
               leaf queue-counters-red-packets-rate-hn {
                 type uint64;
                 description
                   "RED drop rate for high-loss, non-TCP packets";
               }
               leaf queue-counters-red-packets-ht {
                 type uint64;
                 description
                   "Number of RED dropped high-loss, TCP packets";
               }
               leaf queue-counters-red-packets-rate-ht {
                 type uint64;
                 description
                   "RED drop rate for high-loss, TCP packets";
               }
               leaf queue-counters-red-packets-low {
                 type uint64;
                 description
                   "Number of RED dropped low-loss packets";
               }
               leaf queue-counters-red-packets-rate-low {
                 type uint64;
                 description
                   "RED drop rate for low-loss packets";
               }
               leaf queue-counters-red-packets-medium-low {
                 type uint64;
                 description
                   "Number of RED dropped medium-low-loss packets";
               }
               leaf queue-counters-red-packets-rate-medium-low {
                 type uint64;
                 description
                   "RED drop rate for medium-low-loss packets";
               }
               leaf queue-counters-red-packets-medium-high {
                 type uint64;
                 description
                   "Number of RED dropped medium-high-loss packets";
               }
               leaf queue-counters-red-packets-rate-medium-high {
                 type uint64;
                 description
                   "RED drop rate for medium-high-loss packets";
               }
               leaf queue-counters-red-packets-medium {
                 type uint64;
                 description
                   "Number of RED dropped medium-loss packets";
               }
               leaf queue-counters-red-packets-rate-medium {
                 type uint64;
                 description
                   "RED drop rate for medium-loss packets";
               }
               leaf queue-counters-red-packets-high {
                 type uint64;
                 description
                   "Number of RED dropped high-loss packets";
               }
               leaf queue-counters-red-packets-rate-high {
                 type uint64;
                 description
                   "RED drop rate for high-loss packets";
               }
               leaf queue-counters-red-bytes-na {
                 type string;
                 description
                   "Number of bytes dropped due to RED not available";
               }
               leaf queue-counters-red-bytes {
                 type uint64;
                 description
                   "Number of bytes dropped due to RED";
               }
               leaf queue-counters-red-bytes-rate {
                 type uint64;
                 description
                   "Rate at which bytes are dropped due to RED";
               }
               leaf queue-counters-red-bytes-ln {
                 type uint64;
                 description
                   "Number of RED dropped low-loss, non-TCP bytes";
               }
               leaf queue-counters-red-bytes-rate-ln {
                 type uint64;
                 description
                   "RED drop rate for low-loss, non-TCP bytes";
               }
               leaf queue-counters-red-bytes-lt {
                 type uint64;
                 description
                   "Number of RED dropped low-loss, TCP bytes";
               }
               leaf queue-counters-red-bytes-rate-lt {
                 type uint64;
                 description
                   "RED drop rate for low-loss, TCP bytes";
               }
               leaf queue-counters-red-bytes-hn {
                 type uint64;
                 description
                   "Number of RED dropped high-loss, non-TCP bytes";
               }
               leaf queue-counters-red-bytes-rate-hn {
                 type uint64;
                 description
                   "RED drop rate for high-loss, non-TCP bytes";
               }
               leaf queue-counters-red-bytes-ht {
                 type uint64;
                 description
                   "Number of RED dropped high-loss, TCP bytes";
               }
               leaf queue-counters-red-bytes-rate-ht {
                 type uint64;
                 description
                   "RED drop rate for high-loss, TCP bytes";
               }
               leaf queue-counters-red-bytes-low {
                 type uint64;
                 description
                   "Number of RED dropped low-loss bytes";
               }
               leaf queue-counters-red-bytes-rate-low {
                 type uint64;
                 description
                   "RED drop rate for low-loss bytes";
               }
               leaf queue-counters-red-bytes-medium-low {
                 type uint64;
                 description
                   "Number of RED dropped medium-low-loss bytes";
               }
               leaf queue-counters-red-bytes-rate-medium-low {
                 type uint64;
                 description
                   "RED drop rate for medium-low-loss bytes";
               }
               leaf queue-counters-red-bytes-medium-high {
                 type uint64;
                 description
                   "Number of RED dropped medium-high-loss bytes";
               }
               leaf queue-counters-red-bytes-rate-medium-high {
                 type uint64;
                 description
                   "RED drop rate for medium-high-loss bytes";
               }
               leaf queue-counters-red-bytes-medium {
                 type uint64;
                 description
                   "Number of RED dropped medium-loss bytes";
               }
               leaf queue-counters-red-bytes-rate-medium {
                 type uint64;
                 description
                   "RED drop rate for medium-loss bytes";
               }
               leaf queue-counters-red-bytes-high {
                 type uint64;
                 description
                   "Number of RED dropped high-loss bytes";
               }
               leaf queue-counters-red-bytes-rate-high {
                 type uint64;
                 description
                   "RED drop rate for high-loss bytes";
               }
               leaf queue-counters-timestamp {
                 type uint64;
                 description
                   "Last packet enqueued timestamp";
               }
               leaf queue-counters-total-drop-packets {
                 type uint64;
                 description
                   "Number of total packets dropped at the queue";
               }
               leaf queue-counters-total-drop-packets-rate {
                 type uint64;
                 description
                   "Number of total packets dropped at the queue";
               }
               leaf queue-counters-total-drop-bytes {
                 type uint64;
                 description
                   "Number of total packets dropped at the queue";
               }
               leaf queue-counters-total-drop-bytes-rate {
                 type uint64;
                 description
                   "Number of total packets dropped at the queue";
               }
               leaf queue-counters-reserved-buffer-packets {
                 type int32;
                 description
                   "Queues's usage of reserved buffer pool in pkts";
               }
               leaf queue-counters-reserved-buffer-bytes {
                 type int32;
                 description
                   "Queues's usage of reserved buffer pool in bytes";
               }
               leaf queue-counters-shared-buffer-packets {
                 type int32;
                 description
                   "Queues's usage of shared buffer pool in pkts";
               }
               leaf queue-counters-shared-buffer-bytes {
                 type int32;
                 description
                   "Queues's usage of shared buffer pool in bytes";
               }
               leaf queue-counters-depth-average {
                 type int32;
                 description
                   "Time averaged queue depth";
               }
               leaf queue-counters-depth-current {
                 type int32;
                 description
                   "Current instantaneous queue depth";
               }
               leaf queue-counters-depth-peak {
                 type int32;
                 description
                   "Peak queue depth";
               }
               leaf queue-counters-depth-max {
                 type int32;
                 description
                   "Maximum queue depth attained";
               }
               leaf queue-counters-srx-reserved-buffer-bytes {
                 type int32;
                 description
                   "Queues's usage of reserved buffer pool in bytes";
               }
               leaf queue-counters-srx-depth-current {
                 type int32;
                 description
                   "Current instantaneous queue depth";
               }
             }
             container interface-cos-summary {
               description
                 "Summary of forwarding class and queue information on an 
                 interface";
               leaf intf-cos-forwarding-classes-supported {
                 type int32;
                 description
                   "Number of forwarding classes supported on this interface";
               }
               leaf intf-cos-forwarding-classes-in-use {
                 type int32;
                 description
                   "Number of forwarding classes currently in use on this 
                   interface";
               }
               leaf intf-cos-queue-type {
                 type string;
                 description
                   "Interface queue type";
               }
               leaf intf-cos-num-queues-supported {
                 type int32;
                 description
                   "Number of queues supported on this interface";
               }
               leaf intf-cos-num-queues-in-use {
                 type int32;
                 description
                   "Number of queues currently in use on this interface";
               }
               leaf intf-cos-queue-dedicated-or-shared {
                 type string;
                 description
                   "Interface has dedicated or shared queues";
               }
               leaf intf-cos-sched-resource-type {
                 type string;
                 description
                   "Interface scheduling resource type";
               }
               leaf intf-cos-sched-resource-usage-mic-limit {
                 type int32;
                 description
                   "MIC/PIC scheduling resource usage limit";
               }
               leaf intf-cos-sched-resource-usage-mic-count {
                 type int32;
                 description
                   "MIC/PIC scheduling resource usage count";
               }
               leaf intf-cos-sched-resource-usage-port-limit {
                 type int32;
                 description
                   "Interface scheduling resource limit";
               }
               leaf intf-cos-sched-resource-usage-port-count {
                 type int32;
                 description
                   "Interface scheduling resource usage";
               }
               leaf intf-cos-burst-size-for-ifl {
                 type int32;
                 description
                   "Burst size for the logical interface";
               }
             }
             container interface-cos-short-summary {
               description
                 "Summary of queue information on an interface";
               leaf intf-cos-queue-type {
                 type string;
                 description
                   "Interface queue type";
               }
               leaf intf-cos-num-queues-supported {
                 type int32;
                 description
                   "Number of queues supported on this interface";
               }
               leaf intf-cos-num-queues-in-use {
                 type int32;
                 description
                   "Number of queues currently in use on this interface";
               }
               leaf intf-cos-queue-dedicated-or-shared {
                 type string;
                 description
                   "Interface has dedicated or shared queues";
               }
               leaf intf-cos-sched-resource-type {
                 type string;
                 description
                   "Interface scheduling resource type";
               }
               leaf intf-cos-sched-resource-usage-mic-limit {
                 type int32;
                 description
                   "MIC/PIC scheduling resource usage limit";
               }
               leaf intf-cos-sched-resource-usage-mic-count {
                 type int32;
                 description
                   "MIC/PIC scheduling resource usage count";
               }
               leaf intf-cos-sched-resource-usage-port-limit {
                 type int32;
                 description
                   "Interface scheduling resource limit";
               }
               leaf intf-cos-sched-resource-usage-port-count {
                 type int32;
                 description
                   "Interface scheduling resource usage";
               }
             }
             container queue-num-forwarding-class-name-map {
               leaf queue-number {
                 type int32;
                 description
                   "Queue number";
               }
               leaf forwarding-class-name {
                 type string;
                 description
                   "Forwarding class name associated with queue";
               }
             }
           }
           container forwarding-class-counters {
             description
               "Forwarding-class counter statistics";
             leaf forwarding-class-counters-error-message {
               type string;
               description
                 "Forwarding-class statistics not available for this 
                 interface";
             }
             container ipv4-forwarding-class-counters {
               leaf forwarding-class-stats-type {
                 type string;
               }
               container per-forwarding-class-counters {
                 leaf fc_name_header {
                   type string;
                 }
                 leaf forwarding-class-name {
                   type string;
                   description
                     "Forwarding class name associated with queue";
                 }
                 leaf fc-input-bytes {
                   type int32;
                 }
                 leaf fc-input-bytes-rate {
                   type int32;
                   description
                     "Input bytes rate";
                 }
                 leaf fc-output-bytes {
                   type int32;
                 }
                 leaf fc-output-bytes-rate {
                   type int32;
                   description
                     "Output bytes rate";
                 }
                 leaf fc-input-packets {
                   type int32;
                 }
                 leaf fc-input-packets-rate {
                   type int32;
                   description
                     "Input packets rate";
                 }
                 leaf fc-output-packets {
                   type int32;
                 }
                 leaf fc-output-packets-rate {
                   type int32;
                   description
                     "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container ipv6-forwarding-class-counters {
               leaf forwarding-class-stats-type {
                 type string;
               }
               container per-forwarding-class-counters {
                 leaf fc_name_header {
                   type string;
                 }
                 leaf forwarding-class-name {
                   type string;
                   description
                     "Forwarding class name associated with queue";
                 }
                 leaf fc-input-bytes {
                   type int32;
                 }
                 leaf fc-input-bytes-rate {
                   type int32;
                   description
                     "Input bytes rate";
                 }
                 leaf fc-output-bytes {
                   type int32;
                 }
                 leaf fc-output-bytes-rate {
                   type int32;
                   description
                     "Output bytes rate";
                 }
                 leaf fc-input-packets {
                   type int32;
                 }
                 leaf fc-input-packets-rate {
                   type int32;
                   description
                     "Input packets rate";
                 }
                 leaf fc-output-packets {
                   type int32;
                 }
                 leaf fc-output-packets-rate {
                   type int32;
                   description
                     "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container mpls-forwarding-class-counters {
               leaf forwarding-class-stats-type {
                 type string;
               }
               container per-forwarding-class-counters {
                 leaf fc_name_header {
                   type string;
                 }
                 leaf forwarding-class-name {
                   type string;
                   description
                     "Forwarding class name associated with queue";
                 }
                 leaf fc-input-bytes {
                   type int32;
                 }
                 leaf fc-input-bytes-rate {
                   type int32;
                   description
                     "Input bytes rate";
                 }
                 leaf fc-output-bytes {
                   type int32;
                 }
                 leaf fc-output-bytes-rate {
                   type int32;
                   description
                     "Output bytes rate";
                 }
                 leaf fc-input-packets {
                   type int32;
                 }
                 leaf fc-input-packets-rate {
                   type int32;
                   description
                     "Input packets rate";
                 }
                 leaf fc-output-packets {
                   type int32;
                 }
                 leaf fc-output-packets-rate {
                   type int32;
                   description
                     "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container layer2-forwarding-class-counters {
               leaf forwarding-class-stats-type {
                 type string;
               }
               container per-forwarding-class-counters {
                 leaf fc_name_header {
                   type string;
                 }
                 leaf forwarding-class-name {
                   type string;
                   description
                     "Forwarding class name associated with queue";
                 }
                 leaf fc-input-bytes {
                   type int32;
                 }
                 leaf fc-input-bytes-rate {
                   type int32;
                   description
                     "Input bytes rate";
                 }
                 leaf fc-output-bytes {
                   type int32;
                 }
                 leaf fc-output-bytes-rate {
                   type int32;
                   description
                     "Output bytes rate";
                 }
                 leaf fc-input-packets {
                   type int32;
                 }
                 leaf fc-input-packets-rate {
                   type int32;
                   description
                     "Input packets rate";
                 }
                 leaf fc-output-packets {
                   type int32;
                 }
                 leaf fc-output-packets-rate {
                   type int32;
                   description
                     "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container other-forwarding-class-counters {
               leaf forwarding-class-stats-type {
                 type string;
               }
               container per-forwarding-class-counters {
                 leaf fc_name_header {
                   type string;
                 }
                 leaf forwarding-class-name {
                   type string;
                   description
                     "Forwarding class name associated with queue";
                 }
                 leaf fc-input-bytes {
                   type int32;
                 }
                 leaf fc-input-bytes-rate {
                   type int32;
                   description
                     "Input bytes rate";
                 }
                 leaf fc-output-bytes {
                   type int32;
                 }
                 leaf fc-output-bytes-rate {
                   type int32;
                   description
                     "Output bytes rate";
                 }
                 leaf fc-input-packets {
                   type int32;
                 }
                 leaf fc-input-packets-rate {
                   type int32;
                   description
                     "Input packets rate";
                 }
                 leaf fc-output-packets {
                   type int32;
                 }
                 leaf fc-output-packets-rate {
                   type int32;
                   description
                     "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container protocol-aggregate-forwarding-class-counters {
               leaf forwarding-class-stats-type {
                 type string;
               }
               container per-forwarding-class-counters {
                 leaf fc_name_header {
                   type string;
                 }
                 leaf forwarding-class-name {
                   type string;
                   description
                     "Forwarding class name associated with queue";
                 }
                 leaf fc-input-bytes {
                   type int32;
                 }
                 leaf fc-input-bytes-rate {
                   type int32;
                   description
                     "Input bytes rate";
                 }
                 leaf fc-output-bytes {
                   type int32;
                 }
                 leaf fc-output-bytes-rate {
                   type int32;
                   description
                     "Output bytes rate";
                 }
                 leaf fc-input-packets {
                   type int32;
                 }
                 leaf fc-input-packets-rate {
                   type int32;
                   description
                     "Input packets rate";
                 }
                 leaf fc-output-packets {
                   type int32;
                 }
                 leaf fc-output-packets-rate {
                   type int32;
                   description
                     "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container forwarding-class-statistics {
               container protocol-aggregate-forwarding-class-counters {
               }
               container ipv4-forwarding-class-counters {
               }
               container ipv6-forwarding-class-counters {
               }
               container mpls-forwarding-class-counters {
               }
               container layer2-forwarding-class-counters {
               }
               container other-forwarding-class-counters {
               }
             }
             container forwarding-class-accounting-parameters {
               leaf forwarding-class-accounting-for-protocol {
                 type string;
               }
               leaf forwarding-class-accounting-for-traffic-direction {
                 type string;
               }
               leaf forwarding-class-accounting-for-traffic-type {
                 type string;
               }
               leaf forwarding-class-accounting-overhead-bytes {
                 type uint32;
               }
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container multilink-bundle-options {
             leaf filler-packet-interval {
               type int32;
             }
           }
           container multilink-traffic-statistics {
             container bundle {
             }
             container class {
               description
                 "Multilink class traffic statistics";
             }
             container multilink-detail-statistics {
               container bundle-detail {
               }
               container class-detail {
               }
             }
             container crtp {
               container crtp-sessions {
                 leaf input-frames {
                   type int32;
                 }
                 leaf output-frames {
                   type int32;
                 }
               }
               list crtp-statistics {
                 key "name";
                 leaf name {
                   type string;
                   description
                     "Name of this item";
                 }
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
             }
           }
           container traffic-statistics {
             leaf input-bps {
               type int32;
             }
             leaf input-pps {
               type int32;
             }
             leaf output-bps {
               type int32;
             }
             leaf output-pps {
               type int32;
             }
             leaf input-packets {
               type int32;
             }
             leaf output-packets {
               type int32;
             }
             leaf input-bytes {
               type int32;
             }
             leaf output-bytes {
               type int32;
             }
             container ipv6-transit-statistics {
               leaf input-bytes {
                 type int32;
               }
               leaf output-bytes {
                 type int32;
               }
               leaf input-packets {
                 type int32;
               }
               leaf output-packets {
                 type int32;
               }
             }
             container ipv6-total-statistics {
               leaf input-bytes {
                 type int32;
               }
               leaf output-bytes {
                 type int32;
               }
               leaf input-packets {
                 type int32;
               }
               leaf output-packets {
                 type int32;
               }
             }
           }
           container multicast-statistics {
             description
               "Multicast statistics for interface";
             leaf multicast-statistics-header {
               type empty;
             }
             container ipv4-multicast-statistics {
               description
                 "IPV4 multicast statistics for interface";
               leaf input-bytes {
                 type int32;
               }
               leaf input-bps {
                 type int32;
               }
               leaf output-bytes {
                 type int32;
               }
               leaf output-bps {
                 type int32;
               }
               leaf input-packets {
                 type int32;
               }
               leaf input-pps {
                 type int32;
               }
               leaf output-packets {
                 type int32;
               }
               leaf output-pps {
                 type int32;
               }
             }
             container ipv6-multicast-statistics {
               description
                 "IPV6 multicast statistics for interface";
               leaf input-bytes {
                 type int32;
               }
               leaf input-bps {
                 type int32;
               }
               leaf output-bytes {
                 type int32;
               }
               leaf output-bps {
                 type int32;
               }
               leaf input-packets {
                 type int32;
               }
               leaf input-pps {
                 type int32;
               }
               leaf output-packets {
                 type int32;
               }
               leaf output-pps {
                 type int32;
               }
             }
           }
           container ingress-traffic-statistics {
             description
               "Traffic statistics at ingress before entering Packet 
               Forwarding Engine";
             leaf input-bps {
               type int32;
             }
             leaf input-pps {
               type int32;
             }
             leaf input-drop-bps {
               type int32;
               description
                 "Drop rate at ingress in bits per second ";
             }
             leaf input-drop-pps {
               type int32;
               description
                 "Drop rate at ingress in packets per second ";
             }
             leaf input-bytes {
               type int32;
             }
             leaf input-packets {
               type int32;
             }
             leaf input-drop-bytes {
               type int32;
               description
                 "Drop statistics at ingress in bytes";
             }
             leaf input-drop-packets {
               type int32;
               description
                 "Drop statistics at ingress in packets";
             }
           }
           container transit-traffic-statistics {
             description
               "Statistics for traffic passing through the Packet Forwarding
               Engine";
           }
           container keepalive-statistics {
             description
               "Keepalive statistics for this interface";
             leaf keepalive-lmi-descriptor {
               type string;
             }
             leaf keepalive-input-count {
               type int32;
             }
             leaf keepalive-input-time {
               type string;
             }
             leaf keepalive-output-count {
               type int32;
             }
             leaf keepalive-output-time {
               type string;
             }
           }
           container virtual-circuit-information {
             description
               "Operational information and statistics for a virtual circuit";
             container traffic-statistics {
               leaf input-bps {
                 type int32;
               }
               leaf input-pps {
                 type int32;
               }
               leaf output-bps {
                 type int32;
               }
               leaf output-pps {
                 type int32;
               }
               leaf input-packets {
                 type int32;
               }
               leaf output-packets {
                 type int32;
               }
               leaf input-bytes {
                 type int32;
               }
               leaf output-bytes {
                 type int32;
               }
               container ipv6-transit-statistics {
                 leaf input-bytes {
                   type int32;
                 }
                 leaf output-bytes {
                   type int32;
                 }
                 leaf input-packets {
                   type int32;
                 }
                 leaf output-packets {
                   type int32;
                 }
               }
               container ipv6-total-statistics {
                 leaf input-bytes {
                   type int32;
                 }
                 leaf output-bytes {
                   type int32;
                 }
                 leaf input-packets {
                   type int32;
                 }
                 leaf output-packets {
                   type int32;
                 }
               }
             }
             container atm-cos-information {
               leaf vc-cos-mode {
                 type string;
                 description
                   "Virtual circuit CoS scheduling mode";
               }
               list atm-cos-queue {
                 container atm-cos-queue-parameters {
                   leaf cos-forwarding-class-name {
                     type string;
                     description
                       "Forwarding class name associated with queue";
                   }
                   leaf cos-queue-number {
                     type int32;
                     description
                       "Queue number";
                   }
                   leaf scheduling-priority {
                     type string;
                     description
                       "Scheduling priority";
                   }
                   leaf transmit-weight-cells {
                     type int32;
                     description
                       "Weight to apply to scheduling as number of cells";
                   }
                   leaf transmit-weight-percent {
                     type int32;
                     description
                       "Weight to apply to scheduling as fill percentage";
                   }
                   leaf epd-threshold {
                     type int32;
                     description
                       "Early packet drop threshold";
                   }
                   leaf epd-threshold-plp0 {
                     type int32;
                     description
                       "Early packet drop threshold for PLP 0";
                   }
                   leaf epd-threshold-plp1 {
                     type int32;
                     description
                       "Early packet drop threshold for PLP 1";
                   }
                   container linear-red-drop-profile {
                     leaf queue-depth {
                       type uint32;
                       description
                         "Instantaneous queue depth";
                     }
                     leaf low-red {
                       type int32;
                       description
                         "Fill level percentage when linear RED is applied 
                         for low PLP";
                     }
                     leaf high-red {
                       type int32;
                       description
                         "Fill level percentage when linear RED is applied 
                         for high PLP";
                     }
                     leaf max-low-red {
                       type int32;
                       description
                         "Fill level percentage with 100% packet drop for 
                         low PLP";
                     }
                     leaf max-high-red {
                       type int32;
                       description
                         "Fill level percentage with 100% packet drop for 
                         high PLP";
                     }
                   }
                 }
                 container atm-cos-queue-statistics {
                   leaf atm-output-bytes {
                     type int32;
                   }
                   leaf atm-output-packets {
                     type int32;
                   }
                   leaf atm-packet-drops {
                     type int32;
                   }
                 }
                 container atm-cos-plp-statistics {
                   leaf atm-plp0-output-bytes {
                     type int32;
                   }
                   leaf atm-plp1-output-bytes {
                     type int32;
                   }
                   leaf atm-plp0-output-packets {
                     type int32;
                   }
                   leaf atm-plp1-output-packets {
                     type int32;
                   }
                   leaf atm-plp0-byte-drops {
                     type int32;
                   }
                   leaf atm-plp1-byte-drops {
                     type int32;
                   }
                   leaf atm-plp0-packet-drops {
                     type int32;
                   }
                   leaf atm-plp1-packet-drops {
                     type int32;
                   }
                 }
               }
             }
           }
           list policer-information {
             description
               "Interface policer information";
             leaf policer-family {
               type string;
               description
                 "Protocol family of the policer";
             }
             leaf policer-input {
               type string;
               description
                 "Name of the input policer";
             }
             leaf policer-output {
               type string;
               description
                 "Name of the output policer";
             }
           }
           list address-family {
             leaf local-bias-information {
               type string;
             }
             leaf ft-iff-dest-port {
               type uint32;
               description
                 "Destination UDP port to be used for this family";
             }
             container pppoe-underlying-information {
               description
                 "PPPoE Underlying information";
               list pppoe-underlying-interface {
                 leaf dynamic-profile {
                   type string;
                   description
                     "Dynamic Profile name";
                 }
                 leaf service-name-table {
                   type string;
                   description
                     "Name of Service Name Table";
                 }
                 leaf max-sessions {
                   type int32;
                   description
                     "Maximum number of PPPoE sessions";
                 }
                 leaf max-sessions-vsa-ignore {
                   type string;
                   description
                     "Ignore max-sessions VSA";
                 }
                 leaf duplicate-protection {
                   type string;
                   description
                     "Duplicate protection mode";
                 }
                 leaf short-cycle-protection {
                   type string;
                   description
                     "Short cycle protection mode";
                 }
                 leaf direct-connect {
                   type string;
                   description
                     "Direct connect mode";
                 }
                 leaf ac-name {
                   type string;
                   description
                     "Access Concentrator name";
                 }
                 leaf underlying-interface-name {
                   type string;
                   description
                     "Underlying interface name";
                 }
                 leaf underlying-interface-index {
                   type string;
                   description
                     "Underlying interface index";
                 }
                 leaf encapsulation-type-identifier {
                   type string;
                   description
                     "Encapsulation type identifier";
                 }
                 leaf state {
                   type string;
                   description
                     "State";
                 }
                 leaf active-sessions {
                   type int32;
                   description
                     "Number of active PPPoE sessions";
                 }
                 leaf aci-autosensing {
                   type string;
                   description
                     "ACI VLAN Autosensing mode";
                 }
                 leaf line-identity-autosensing {
                   type string;
                   description
                     "Line Identity Autosensing mode";
                 }
               }
             }
             list interface-address {
             }
             container destination-class-statistics {
               description
                 "Destination class usage (DCU) statistics";
             }
             container source-class-statistics {
               description
                 "Source class usage (SCU) statistics";
             }
           }
           list bridge-iff-properties {
             description
               "Information about Ethernet-switching address family";
           }
           container l2circuit-info {
             leaf out-of-sequence {
               type int32;
             }
             leaf denied-packets {
               type int32;
             }
             leaf cell-bundle-size {
               type int32;
             }
             leaf cell-bundle-timeout {
               type int32;
             }
             leaf cell-timeout-count {
               type int32;
             }
           }
           container media-information {
             description
               "Information about media alarms";
             leaf media-type {
               type string;
               description
                 "Type of media this information is for";
             }
             list media-alarm {
               leaf media-alarm-name {
                 type string;
               }
               leaf media-alarm-count {
                 type int32;
               }
               leaf media-alarm-seconds {
                 type int32;
               }
               leaf media-alarm-state {
                 type string;
               }
               leaf ce-counter-name {
                 type string;
                 description
                   "Circuit Emulation counter information";
               }
               leaf ce-counter-packets {
                 type int32;
                 description
                   "Circuit Emulation number of packets";
               }
               leaf ce-counter-bytes {
                 type int32;
                 description
                   "Circuit Emulation number of bytes";
               }
               leaf ce-counter-count {
                 type int32;
                 description
                   "Circuit Emulation number of event occurrences";
               }
             }
             leaf ds1-timeslots {
               type string;
             }
             leaf ds1-line-encoding {
               type string;
             }
             leaf ds1-byte-encoding {
               type string;
             }
             leaf ds1-data-inversion {
               type string;
             }
             leaf idle-cycle-flag {
               type string;
             }
             leaf start-end-flag {
               type string;
             }
             leaf ds0-byte-encoding {
               type string;
             }
             leaf ds0-data-inversion {
               type string;
             }
             leaf e3-data-inversion {
               type string;
             }
             leaf ds1-buildout {
               type string;
               description
                 "Number of feet";
             }
           }
           list macsec-statistics {
             description
               "Information about MAC Security statistics details";
             leaf interface-name {
               type string;
               description
                 "Class-of-service interface name";
             }
             leaf encrypted-packets {
               type uint64;
               description
                 "Macsec encrypted packets sent";
             }
             leaf encrypted-bytes {
               type uint64;
               description
                 "Macsec encrypted bytes sent";
             }
             leaf protected-packets {
               type uint64;
               description
                 "Macsec packets sent with only integrity protection";
             }
             leaf protected-bytes {
               type uint64;
               description
                 "Macsec bytes sent with only integrity protection";
             }
             leaf ok-packets {
               type uint64;
               description
                 "Macsec packets accepted";
             }
             leaf decrypted-bytes {
               type uint64;
               description
                 "Macsec received bytes decrypted";
             }
             leaf decrypted-packets {
               type uint64;
               description
                 "Macsec received packets decrypted";
             }
             leaf validated-packets {
               type uint64;
               description
                 "Macsec received packets validated";
             }
             leaf validated-bytes {
               type uint64;
               description
                 "Macsec received bytes validated";
             }
             leaf untagged-packets {
               type uint64;
               description
                 "Macsec untagged packets";
             }
             leaf toolong-packets {
               type uint64;
               description
                 "Macsec too long packets transmitted on a secure channel";
             }
             leaf control-packets {
               type uint64;
               description
                 "Macsec control packets received on a secure channel";
             }
             leaf tagged-miss-packets {
               type uint64;
               description
                 "Macsec tagged miss packets received on a secure channel";
             }
             leaf untagged-hit-packets {
               type uint64;
               description
                 "Macsec untagged hit packets received on a secure channel";
             }
             leaf notag-packets {
               type uint64;
               description
                 "Macsec no tag packets received on a secure channel";
             }
             leaf badtag-packets {
               type uint64;
               description
                 "Macsec bad tag packets received on a secure channel";
             }
             leaf unknown-sci-packets {
               type uint64;
               description
                 "Macsec unknown sci packets received on a secure channel";
             }
             leaf no-sci-packets {
               type uint64;
               description
                 "Macsec no sci packets received on a secure channel";
             }
             leaf control-pass-packets {
               type uint64;
               description
                 "Macsec allowed control packets received on a secure 
                 channel";
             }
             leaf uncontrol-pass-packets {
               type uint64;
               description
                 "Macsec allowed uncontrol packets received on a secure 
                 channel";
             }
             leaf control-fail-packets {
               type uint64;
               description
                 "Macsec dropped control packets received on a secure 
                 channel";
             }
             leaf uncontrol-fail-packets {
               type uint64;
               description
                 "Macsec dropped uncontrol packets received on a secure 
                 channel";
             }
             leaf hit-dropped-packets {
               type uint64;
               description
                 "Macsec hit dropped packets received on a security channel";
             }
             leaf notusing-sa-packets {
               type uint64;
               description
                 "Macsec not using sa packets received on a security channel";
             }
             leaf unused-sa-packets {
               type uint64;
               description
                 "Macsec unused sa packets received on a security channel";
             }
             leaf late-packets {
               type uint64;
               description
                 "Macsec late packets dropped on a security channel";
             }
             leaf delayed-packets {
               type uint64;
               description
                 "Macsec delayed packets accepted on a security channel";
             }
             leaf unchecked-packets {
               type uint64;
               description
                 "Macsec unchecked packets accepted on a security channel";
             }
             leaf notvalid-packets {
               type uint64;
               description
                 "Macsec not valid packets dropped on a security channel";
             }
             leaf invalid-packets {
               type uint64;
               description
                 "Macsec invalid packets accepted on a security channel";
             }
             list secure-channel-sent {
               leaf encrypted-packets {
                 type uint64;
                 description
                   "Macsec encrypted packets sent";
               }
               leaf encrypted-bytes {
                 type uint64;
                 description
                   "Macsec encrypted bytes sent";
               }
               leaf protected-packets {
                 type uint64;
                 description
                   "Macsec packets sent with only integrity protection";
               }
               leaf protected-bytes {
                 type uint64;
                 description
                   "Macsec bytes sent with only integrity protection";
               }
             }
             list secure-association-sent {
               leaf encrypted-packets {
                 type uint64;
                 description
                   "Macsec encrypted packets sent";
               }
               leaf encrypted-bytes {
                 type uint64;
                 description
                   "Macsec encrypted bytes sent";
               }
               leaf protected-packets {
                 type uint64;
                 description
                   "Macsec packets sent with only integrity protection";
               }
               leaf protected-bytes {
                 type uint64;
                 description
                   "Macsec bytes sent with only integrity protection";
               }
             }
             list secure-channel-received {
               leaf ok-packets {
                 type uint64;
                 description
                   "Macsec packets accepted";
               }
               leaf decrypted-packets {
                 type uint64;
                 description
                   "Macsec received packets decrypted";
               }
               leaf decrypted-bytes {
                 type uint64;
                 description
                   "Macsec received bytes decrypted";
               }
               leaf validated-packets {
                 type uint64;
                 description
                   "Macsec received packets validated";
               }
               leaf validated-bytes {
                 type uint64;
                 description
                   "Macsec received bytes validated";
               }
             }
             list secure-association-received {
               leaf ok-packets {
                 type uint64;
                 description
                   "Macsec packets accepted";
               }
               leaf decrypted-packets {
                 type uint64;
                 description
                   "Macsec received packets decrypted";
               }
               leaf decrypted-bytes {
                 type uint64;
                 description
                   "Macsec received bytes decrypted";
               }
               leaf validated-packets {
                 type uint64;
                 description
                   "Macsec received packets validated";
               }
               leaf validated-bytes {
                 type uint64;
                 description
                   "Macsec received bytes validated";
               }
             }
             list macsec-error-information {
               list secure-channel-sent-errors {
                 leaf untagged-packets {
                   type uint64;
                   description
                     "Macsec untagged packets";
                 }
                 leaf toolong-packets {
                   type uint64;
                   description
                     "Macsec too long packets transmitted on a secure 
                     channel";
                 }
               }
               list secure-channel-received-errors {
                 leaf control-packets {
                   type uint64;
                   description
                     "Macsec control packets received on a secure channel";
                 }
                 leaf tagged-miss-packets {
                   type uint64;
                   description
                     "Macsec tagged miss packets received on a secure 
                     channel";
                 }
                 leaf untagged-hit-packets {
                   type uint64;
                   description
                     "Macsec untagged hit packets received on a secure 
                     channel";
                 }
                 leaf untagged-packets {
                   type uint64;
                   description
                     "Macsec untagged packets";
                 }
                 leaf notag-packets {
                   type uint64;
                   description
                     "Macsec no tag packets received on a secure channel";
                 }
                 leaf badtag-packets {
                   type uint64;
                   description
                     "Macsec bad tag packets received on a secure channel";
                 }
                 leaf unknown-sci-packets {
                   type uint64;
                   description
                     "Macsec unknown sci packets received on a secure 
                     channel";
                 }
                 leaf no-sci-packets {
                   type uint64;
                   description
                     "Macsec no sci packets received on a secure channel";
                 }
                 leaf control-pass-packets {
                   type uint64;
                   description
                     "Macsec allowed control packets received on a secure 
                     channel";
                 }
                 leaf control-fail-packets {
                   type uint64;
                   description
                     "Macsec dropped control packets received on a secure 
                     channel";
                 }
                 leaf uncontrol-pass-packets {
                   type uint64;
                   description
                     "Macsec allowed uncontrol packets received on a secure 
                     channel";
                 }
                 leaf uncontrol-fail-packets {
                   type uint64;
                   description
                     "Macsec dropped uncontrol packets received on a secure 
                     channel";
                 }
               }
               list secure-channel-received-extended {
                 leaf hit-dropped-packets {
                   type uint64;
                   description
                     "Macsec hit dropped packets received on a security 
                     channel";
                 }
                 leaf invalid-packets {
                   type uint64;
                   description
                     "Macsec invalid packets accepted on a security channel";
                 }
                 leaf late-packets {
                   type uint64;
                   description
                     "Macsec late packets dropped on a security channel";
                 }
                 leaf delayed-packets {
                   type uint64;
                   description
                     "Macsec delayed packets accepted on a security channel";
                 }
                 leaf unchecked-packets {
                   type uint64;
                   description
                     "Macsec unchecked packets accepted on a security 
                     channel";
                 }
                 leaf notvalid-packets {
                   type uint64;
                   description
                     "Macsec not valid packets dropped on a security channel";
                 }
                 leaf notusing-sa-packets {
                   type uint64;
                   description
                     "Macsec not using sa packets received on a security 
                     channel";
                 }
                 leaf unused-sa-packets {
                   type uint64;
                   description
                     "Macsec unused sa packets received on a security 
                     channel";
                 }
                 leaf untagged-hit-packets {
                   type uint64;
                   description
                     "Macsec untagged hit packets received on a secure 
                     channel";
                 }
               }
             }
           }
           container lag-traffic-statistics {
             container lag-multicast-statistics {
               leaf lag-multicast-statistics-header {
                 type empty;
               }
               container lag-ipv4-multicast-statistics {
                 leaf input-packets {
                   type int32;
                 }
                 leaf input-pps {
                   type int32;
                 }
                 leaf input-bytes {
                   type int32;
                 }
                 leaf input-bps {
                   type int32;
                 }
                 leaf output-packets {
                   type int32;
                 }
                 leaf output-pps {
                   type int32;
                 }
                 leaf output-bytes {
                   type int32;
                 }
                 leaf output-bps {
                   type int32;
                 }
               }
               container lag-ipv6-multicast-statistics {
                 leaf input-packets {
                   type int32;
                 }
                 leaf input-pps {
                   type int32;
                 }
                 leaf input-bytes {
                   type int32;
                 }
                 leaf input-bps {
                   type int32;
                 }
                 leaf output-packets {
                   type int32;
                 }
                 leaf output-pps {
                   type int32;
                 }
                 leaf output-bytes {
                   type int32;
                 }
                 leaf output-bps {
                   type int32;
                 }
               }
             }
             list if-distribution-list-information {
             }
           }
           container layer2-input-policer-statistics {
             description
               "Layer 2 input policer statistics for interface";
             leaf policer-medium-low-frames {
               type int32;
               description
                 "Number of loss priority medium low frames";
             }
             leaf policer-medium-low-bytes {
               type int32;
               description
                 "Number of loss priority medium low bytes";
             }
             leaf policer-medium-low-rate {
               type int32;
               description
                 "Rate of loss priority medium low pkts";
             }
           }
           container layer2-output-policer-statistics {
             description
               "Layer 2 output policer statistics for interface";
             leaf policer-medium-low-frames {
               type int32;
               description
                 "Number of loss priority medium low frames";
             }
             leaf policer-medium-low-bytes {
               type int32;
               description
                 "Number of loss priority medium low bytes";
             }
             leaf policer-medium-low-rate {
               type int32;
               description
                 "Rate of loss priority medium low pkts";
             }
           }
           container mac-policer-information {
             container ether-policer-list {
             }
           }
         }
         container active-alarms-otn {
         }
         container active-defects-otn {
         }
         container active-alarms-optics {
         }
         container active-defects-optics {
         }
         container optics-defect-information {
           list media-alarm {
             leaf media-alarm-name {
               type string;
             }
             leaf media-alarm-seconds {
               type int32;
             }
             leaf media-alarm-count {
               type int32;
             }
             leaf media-alarm-state {
               type string;
             }
           }
         }
         container optics-fec-information {
           list media-alarm {
             leaf media-alarm-name {
               type string;
             }
             leaf media-alarm-seconds {
               type int32;
             }
             leaf media-alarm-count {
               type int32;
             }
             leaf media-alarm-state {
               type string;
             }
           }
         }
         container active-alerts-otn {
         }
         container links {
           description
             "Aggregated SONET/SDH link information";
           list link-entry {
             description
               "SONET/SDH link information";
             leaf sonet-payload-pointer-curptr {
               type string;
               description
                 "Value of the SONET/SDH payload pointer, derived from the 
                 H1 and H2 overhead bytes";
             }
             leaf sonet-payload-pointer-ptrinc-count {
               type string;
               description
                 "Number of times the value of the SONET/SDH payload pointer
                 had positive justification";
             }
             leaf sonet-payload-pointer-ptrdec-count {
               type string;
               description
                 "Number of times the value of the SONET/SDH payload pointer
                 had negative justification";
             }
             leaf sonet-payload-pointer-newptr-ndf-count {
               type string;
               description
                 "Number of times a new payload pointer was created with the
                 New Data Found flag set";
             }
             leaf sonet-rx-overhead {
               type string;
             }
             leaf sonet-tx-overhead {
               type string;
             }
             leaf sonet-rx-path-trace {
               type string;
               description
                 "Received SONET path trace";
             }
             leaf sonet-tx-path-trace {
               type string;
               description
                 "Transmitted SONET path trace";
             }
             container active-alarms {
             }
             container active-defects {
             }
             container sonet-errors {
               list media-alarm {
                 leaf media-alarm-name {
                   type string;
                 }
                 leaf media-alarm-count {
                   type int32;
                 }
               }
             }
             container sonet-physical-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-section-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-line-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-path-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-vt-information {
               list media-alarm {
                 leaf media-alarm-name {
                   type string;
                 }
                 leaf media-alarm-seconds {
                   type int32;
                 }
                 leaf media-alarm-count {
                   type int32;
                 }
                 leaf media-alarm-state {
                   type string;
                 }
               }
             }
             list optics-diagnostics {
               description
                 "Optics diagnostics";
               leaf optic-diagnostics-not-available {
                 type string;
                 description
                   "Optical diagnostics not supported by this transceiver";
               }
               leaf laser-bias-current-not-available {
                 type string;
                 description
                   "Laser bias current measurement not available";
               }
               leaf soa-bias-current-not-available {
                 type string;
                 description
                   "SOA bias current measurement not available";
               }
               leaf laser-tx-power-not-available {
                 type string;
                 description
                   "Laser output power measurement not available";
               }
               leaf module-temperature-not-available {
                 type string;
                 description
                   "Module temperature measurement not available";
               }
               leaf tx-module-temperature-not-available {
                 type string;
                 description
                   "Tx module temperature measurement not available";
               }
               leaf rx-module-temperature-not-available {
                 type string;
                 description
                   "Rx module temperature measurement not available";
               }
               leaf laser-rx-power-not-available {
                 type string;
                 description
                   "Laser receiver optical power measurement not available";
               }
               leaf laser-tx-power-high-alarm-threshold-not-available {
                 type string;
                 description
                   "Laser output power high alarm threshold not available";
               }
               leaf laser-tx-power-low-alarm-threshold-not-available {
                 type string;
                 description
                   "Laser output power low alarm threshold not available";
               }
               leaf laser-tx-power-high-warning-threshold-not-available {
                 type string;
                 description
                   "Laser output power high warning threshold not available";
               }
               leaf laser-tx-power-low-warning-threshold-not-available {
                 type string;
                 description
                   "Laser output power low warning threshold not available";
               }
               leaf laser-bias-current {
                 type string;
                 description
                   "Laser bias current (milliamperes)";
               }
               leaf soa-bias-current {
                 type string;
                 description
                   "SOA bias current (milliamperes)";
               }
               leaf laser-output-power {
                 type string;
                 description
                   "Laser output power (milliwatts)";
               }
               leaf laser-output-power-dbm {
                 type string;
                 description
                   "Laser output power (dBm)";
               }
               leaf module-temperature {
                 type string;
                 description
                   "Module temperature";
               }
               leaf tx-module-temperature {
                 type string;
                 description
                   "Tx module temperature";
               }
               leaf rx-module-temperature {
                 type string;
                 description
                   "Rx module temperature";
               }
               leaf module-voltage {
                 type string;
                 description
                   "Module voltage";
               }
               leaf corrected-error-ratio {
                 type string;
                 description
                   "Corrected error ratio";
               }
               leaf uncorrected-words-ratio {
                 type string;
                 description
                   "Uncorrected words ratio";
               }
               leaf tx-module-voltage {
                 type string;
                 description
                   "Tx module voltage";
               }
               leaf rx-module-voltage {
                 type string;
                 description
                   "Rx module voltage";
               }
               leaf rx-signal-avg-optical-power {
                 type string;
                 description
                   "Receiver signal average power (milliwatts)";
               }
               leaf rx-signal-avg-optical-power-dbm {
                 type string;
                 description
                   "Receiver signal average power (dBm)";
               }
               leaf laser-rx-optical-power {
                 type string;
                 description
                   "Laser receiver optical power (milliwatts)";
               }
               leaf laser-rx-optical-power-dbm {
                 type string;
                 description
                   "Laser receiver optical power (dBm)";
               }
               leaf wavelength-channel {
                 type string;
                 description
                   "Wavelength channel number set";
               }
               leaf wavelength-setpoint {
                 type string;
                 description
                   "Wavelength point set";
               }
               leaf tx-dither {
                 type string;
                 description
                   "Tx dither status";
               }
               leaf frequency-error {
                 type string;
                 description
                   "Frequency error value";
               }
               leaf wavelength-error {
                 type string;
                 description
                   "Wavelength error value";
               }
               leaf laser-bias-current-high-alarm {
                 type string;
                 description
                   "Laser bias current high alarm";
               }
               leaf laser-bias-current-low-alarm {
                 type string;
                 description
                   "Laser bias current low alarm";
               }
               leaf laser-bias-current-high-warn {
                 type string;
                 description
                   "Laser bias current high warning";
               }
               leaf laser-bias-current-low-warn {
                 type string;
                 description
                   "Laser bias current low warning";
               }
               leaf soa-bias-current-high-alarm {
                 type string;
                 description
                   "SOA bias current high alarm";
               }
               leaf soa-bias-current-low-alarm {
                 type string;
                 description
                   "SOA bias current low alarm";
               }
               leaf soa-bias-current-high-warn {
                 type string;
                 description
                   "SOA bias current high warning";
               }
               leaf soa-bias-current-low-warn {
                 type string;
                 description
                   "SOA bias current low warning";
               }
               leaf laser-tx-power-high-alarm {
                 type string;
                 description
                   "Laser output power high alarm";
               }
               leaf laser-tx-power-low-alarm {
                 type string;
                 description
                   "Laser output power low alarm";
               }
               leaf laser-tx-power-high-warn {
                 type string;
                 description
                   "Laser output power high warning";
               }
               leaf laser-tx-power-low-warn {
                 type string;
                 description
                   "Laser output power low warning";
               }
               leaf tx-power-high-alarm {
                 type string;
                 description
                   "Tx power high alarm";
               }
               leaf tx-power-low-alarm {
                 type string;
                 description
                   "Tx power low alarm";
               }
               leaf tx-power-high-warn {
                 type string;
                 description
                   "Tx power high warning";
               }
               leaf tx-power-low-warn {
                 type string;
                 description
                   "Tx power low warning";
               }
               leaf module-temperature-high-alarm {
                 type string;
                 description
                   "Module temperature high alarm";
               }
               leaf module-temperature-low-alarm {
                 type string;
                 description
                   "Module temperature low alarm";
               }
               leaf module-temperature-high-warn {
                 type string;
                 description
                   "Module temperature high warning";
               }
               leaf module-temperature-low-warn {
                 type string;
                 description
                   "Module temperature low warning";
               }
               leaf tx-module-temperature-high-alarm {
                 type string;
                 description
                   "Tx module temperature high alarm";
               }
               leaf tx-module-temperature-low-alarm {
                 type string;
                 description
                   "Tx module temperature low alarm";
               }
               leaf rx-module-temperature-high-alarm {
                 type string;
                 description
                   "Rx module temperature high alarm";
               }
               leaf rx-module-temperature-low-alarm {
                 type string;
                 description
                   "Rx module temperature low alarm";
               }
               leaf module-voltage-high-alarm {
                 type string;
                 description
                   "Module voltage high alarm";
               }
               leaf module-voltage-low-alarm {
                 type string;
                 description
                   "Module voltage low alarm";
               }
               leaf module-voltage-high-warn {
                 type string;
                 description
                   "Module voltage high warning";
               }
               leaf module-voltage-low-warn {
                 type string;
                 description
                   "Module voltage low warning";
               }
               leaf tx-module-voltage-high-alarm {
                 type string;
                 description
                   "Tx module voltage high alarm";
               }
               leaf tx-module-voltage-low-alarm {
                 type string;
                 description
                   "Tx module voltage low alarm";
               }
               leaf rx-module-voltage-high-alarm {
                 type string;
                 description
                   "Rx module voltage high alarm";
               }
               leaf rx-module-voltage-low-alarm {
                 type string;
                 description
                   "Rx module voltage low alarm";
               }
               leaf laser-rx-power-high-alarm {
                 type string;
                 description
                   "Laser receiver power high alarm";
               }
               leaf laser-rx-power-low-alarm {
                 type string;
                 description
                   "Laser receiver power low alarm";
               }
               leaf laser-rx-power-high-warn {
                 type string;
                 description
                   "Laser receiver power high warning";
               }
               leaf laser-rx-power-low-warn {
                 type string;
                 description
                   "Laser receiver power low warning";
               }
               leaf rx-power-high-alarm {
                 type string;
                 description
                   "Receiver power high alarm";
               }
               leaf rx-power-low-alarm {
                 type string;
                 description
                   "Receiver power low alarm";
               }
               leaf rx-power-high-warn {
                 type string;
                 description
                   "Receiver power high warning";
               }
               leaf rx-power-low-warn {
                 type string;
                 description
                   "Receiver power low warning";
               }
               leaf laser-end-of-life-alarm {
                 type string;
                 description
                   "Laser end-of-life alarm";
               }
               leaf laser-wavelength-alarm {
                 type string;
                 description
                   "Laser wavelength alarm";
               }
               leaf laser-bias-current-alarm {
                 type string;
                 description
                   "Laser bias current alarm";
               }
               leaf module-temperature-alarm {
                 type string;
                 description
                   "Module temperature alarm";
               }
               leaf laser-power-alarm {
                 type string;
                 description
                   "Laser power alarm";
               }
               leaf modulator-temperature-alarm {
                 type string;
                 description
                   "Modulator temperature alarm";
               }
               leaf modulator-bias-alarm {
                 type string;
                 description
                   "Modulator bias alarm";
               }
               leaf module-not-ready-alarm {
                 type string;
                 description
                   "Module not ready alarm";
               }
               leaf module-power-down-alarm {
                 type string;
                 description
                   "Module power down alarm";
               }
               leaf module-not-init-done-alarm {
                 type string;
                 description
                   "Module initialization not done alarm";
               }
               leaf module-not-high-power-on-alarm {
                 type string;
                 description
                   "Module not high powered on alarm";
               }
               leaf module-fault-alarm {
                 type string;
                 description
                   "Module in fault state alarm";
               }
               leaf pld-flash-init-fault-alarm {
                 type string;
                 description
                   "PLD or Flash initialization fault alarm";
               }
               leaf power-supply-fault-alarm {
                 type string;
                 description
                   "Power supply fault alarm";
               }
               leaf checksum-fault-alarm {
                 type string;
                 description
                   "Checksum fault alarm";
               }
               leaf apd-supply-fault-alarm {
                 type string;
                 description
                   "APD supply fault alarm";
               }
               leaf tec-fault-alarm {
                 type string;
                 description
                   "TEC fault alarm";
               }
               leaf wavelength-unlocked-alarm {
                 type string;
                 description
                   "Wavelength unlocked alarm";
               }
               leaf tx-tune-alarm {
                 type string;
                 description
                   "Tx tune alarm";
               }
               leaf tx-mux-fifo-error-alarm {
                 type string;
                 description
                   "Tx multiplexer fifo error alarm";
               }
               leaf tx-loss-of-pll-alarm {
                 type string;
                 description
                   "Tx loss of PLL alarm";
               }
               leaf tx-data-not-ready-alarm {
                 type string;
                 description
                   "Tx data not ready alarm";
               }
               leaf tx-not-ready-alarm {
                 type string;
                 description
                   "Tx not ready alarm";
               }
               leaf tx-laser-fault-alarm {
                 type string;
                 description
                   "Tx laser fault alarm";
               }
               leaf tx-laser-disabled-alarm {
                 type string;
                 description
                   "Tx laser disabled alarm";
               }
               leaf tx-loss-of-signal-functionality-alarm {
                 type string;
                 description
                   "Tx loss of signal functionality alarm";
               }
               leaf tx-cdr-loss-of-lock-alarm {
                 type string;
                 description
                   "Tx CDR loss of lock alarm";
               }
               leaf rx-loss-avg-opt-power-alarm {
                 type string;
                 description
                   "Receiver loss of average optical power alarm";
               }
               leaf rx-loss-ac-power-alarm {
                 type string;
                 description
                   "Receiver loss of AC power alarm";
               }
               leaf rx-loss-of-pll-alarm {
                 type string;
                 description
                   "Receiver loss of PLL alarm";
               }
               leaf rx-not-ready-alarm {
                 type string;
                 description
                   "Receiver not ready alarm";
               }
               leaf rx-loss-of-signal-alarm {
                 type string;
                 description
                   "Receiver loss of signal alarm";
               }
               leaf rx-cdr-loss-of-lock-alarm {
                 type string;
                 description
                   "Receiver CDR loss of lock alarm";
               }
               leaf laser-bias-current-high-alarm-threshold {
                 type string;
                 description
                   "Laser bias current high alarm threshold (milliamperes)";
               }
               leaf laser-bias-current-low-alarm-threshold {
                 type string;
                 description
                   "Laser bias current low alarm threshold (milliamperes)";
               }
               leaf laser-bias-current-high-warn-threshold {
                 type string;
                 description
                   "Laser bias current high warning threshold (milliamperes)";
               }
               leaf laser-bias-current-low-warn-threshold {
                 type string;
                 description
                   "Laser bias current low warning threshold (milliamperes)";
               }
               leaf soa-bias-current-high-alarm-threshold {
                 type string;
                 description
                   "SOA bias current high alarm threshold (milliamperes)";
               }
               leaf soa-bias-current-low-alarm-threshold {
                 type string;
                 description
                   "SOA bias current low alarm threshold (milliamperes)";
               }
               leaf soa-bias-current-high-warn-threshold {
                 type string;
                 description
                   "SOA bias current high warning threshold (milliamperes)";
               }
               leaf soa-bias-current-low-warn-threshold {
                 type string;
                 description
                   "SOA bias current low warning threshold (milliamperes)";
               }
               leaf laser-tx-power-high-alarm-threshold {
                 type string;
                 description
                   "Laser transmitter power high alarm threshold 
                   (milliwatts)";
               }
               leaf laser-tx-power-high-alarm-threshold-dbm {
                 type string;
                 description
                   "Laser transmitter power high alarm threshold (dBm)";
               }
               leaf laser-tx-power-low-alarm-threshold {
                 type string;
                 description
                   "Laser transmitter power low alarm threshold (milliwatts)";
               }
               leaf laser-tx-power-low-alarm-threshold-dbm {
                 type string;
                 description
                   "Laser transmitter power low alarm threshold (dBm)";
               }
               leaf laser-tx-power-high-warn-threshold {
                 type string;
                 description
                   "Laser transmitter power high warning threshold 
                   (milliwatts)";
               }
               leaf laser-tx-power-high-warn-threshold-dbm {
                 type string;
                 description
                   "Laser transmitter power high warning threshold (dBm)";
               }
               leaf laser-tx-power-low-warn-threshold {
                 type string;
                 description
                   "Laser transmitter power low warning threshold 
                   (milliwatts)";
               }
               leaf laser-tx-power-low-warn-threshold-dbm {
                 type string;
                 description
                   "Laser transmitter power low warning threshold (dBm)";
               }
               leaf module-temperature-high-alarm-threshold {
                 type string;
                 description
                   "Module temperature high alarm threshold";
               }
               leaf module-temperature-low-alarm-threshold {
                 type string;
                 description
                   "Module temperature low alarm threshold";
               }
               leaf module-temperature-high-warn-threshold {
                 type string;
                 description
                   "Module temperature high warning threshold";
               }
               leaf module-temperature-low-warn-threshold {
                 type string;
                 description
                   "Module temperature low warning threshold";
               }
               leaf laser-temperature-high-alarm-threshold {
                 type string;
                 description
                   "Laser temperature high alarm threshold";
               }
               leaf laser-temperature-low-alarm-threshold {
                 type string;
                 description
                   "Laser temperature low alarm threshold";
               }
               leaf laser-temperature-high-warn-threshold {
                 type string;
                 description
                   "Laser temperature high warning threshold";
               }
               leaf laser-temperature-low-warn-threshold {
                 type string;
                 description
                   "Laser temperature low warning threshold";
               }
               leaf module-voltage-high-alarm-threshold {
                 type string;
                 description
                   "Module voltage high alarm threshold (volts)";
               }
               leaf module-voltage-low-alarm-threshold {
                 type string;
                 description
                   "Module voltage low alarm threshold (volts)";
               }
               leaf module-voltage-high-warn-threshold {
                 type string;
                 description
                   "Module voltage high warning threshold (volts)";
               }
               leaf module-voltage-low-warn-threshold {
                 type string;
                 description
                   "Module voltage low warning threshold (volts)";
               }
               leaf laser-rx-power-high-alarm-threshold {
                 type string;
                 description
                   "Laser receiver power high alarm (milliwatts)";
               }
               leaf laser-rx-power-high-alarm-threshold-dbm {
                 type string;
                 description
                   "Laser receiver power high alarm (dBm)";
               }
               leaf laser-rx-power-low-alarm-threshold {
                 type string;
                 description
                   "Laser receiver power low alarm (milliwatts)";
               }
               leaf laser-rx-power-low-alarm-threshold-dbm {
                 type string;
                 description
                   "Laser receiver power low alarm (dBm)";
               }
               leaf laser-rx-power-high-warn-threshold {
                 type string;
                 description
                   "Laser receiver power high warning (milliwatts)";
               }
               leaf laser-rx-power-high-warn-threshold-dbm {
                 type string;
                 description
                   "Laser receiver power high warning (dBm)";
               }
               leaf laser-rx-power-low-warn-threshold {
                 type string;
                 description
                   "Laser receiver power low warning (milliwatts)";
               }
               leaf laser-rx-power-low-warn-threshold-dbm {
                 type string;
                 description
                   "Laser receiver power low warning (dBm)";
               }
               leaf rx-power-high-alarm-threshold {
                 type string;
                 description
                   "Receiver power high alarm (milliwatts)";
               }
               leaf rx-power-high-alarm-threshold-dbm {
                 type string;
                 description
                   "Receiver power high alarm (dBm)";
               }
               leaf rx-power-low-alarm-threshold {
                 type string;
                 description
                   "Receiver power low alarm (milliwatts)";
               }
               leaf rx-power-low-alarm-threshold-dbm {
                 type string;
                 description
                   "Receiver power low alarm (dBm)";
               }
               leaf rx-power-high-warning-threshold {
                 type string;
                 description
                   "Receiver power high warning (milliwatts)";
               }
               leaf rx-power-high-warning-threshold-dbm {
                 type string;
                 description
                   "Receiver power high warning (dBm)";
               }
               leaf rx-power-low-warning-threshold {
                 type string;
                 description
                   "Receiver power low warning (milliwatts)";
               }
               leaf rx-power-low-warning-threshold-dbm {
                 type string;
                 description
                   "Receiver power low warning (dBm)";
               }
               leaf los-alarm-threshold {
                 type string;
                 description
                   "LOS alarm threshold (milliwatts)";
               }
               leaf los-alarm-threshold-dbm {
                 type string;
                 description
                   "LOS alarm threshold (dBm)";
               }
               leaf los-warning-threshold {
                 type string;
                 description
                   "LOS warning threshold (milliwatts)";
               }
               leaf los-warning-threshold-dbm {
                 type string;
                 description
                   "LOS warning threshold (dBm)";
               }
               leaf dsp-module-state {
                 type string;
                 description
                   "DSP module state";
               }
               leaf output-power {
                 type string;
                 description
                   "Output power (milliwatts)";
               }
               leaf output-power-dbm {
                 type string;
                 description
                   "Output power (dBm)";
               }
               leaf input-power {
                 type string;
                 description
                   "Input power (milliwatts)";
               }
               leaf input-power-dbm {
                 type string;
                 description
                   "Input power (dBm)";
               }
               leaf per-wave-rx-optical-power {
                 type string;
                 description
                   "Per-wavelength receiver optical power (milliwatts)";
               }
               leaf per-wave-rx-optical-power-dbm {
                 type string;
                 description
                   "Per-wavelength receiver optical power (dBm)";
               }
               leaf lane-laser-frequency-error {
                 type string;
                 description
                   "Lane laser frequency error (MHz)";
               }
               leaf tec-current {
                 type string;
                 description
                   "Tec current";
               }
               leaf residual-isi {
                 type string;
                 description
                   "Residual ISI";
               }
               container optics-diagnostics-ot {
                 description
                   "OT interface optics diagnostics";
                 leaf module-temp-fault {
                   type string;
                   description
                     "Module temperature fault";
                 }
                 leaf specific-hw-fault {
                   type string;
                   description
                     "Specific HW fault";
                 }
                 leaf internal-power-fault {
                   type string;
                   description
                     "Internal power fault";
                 }
                 leaf post-therm-fault {
                   type string;
                   description
                     "Power thermal fault";
                 }
                 leaf post-fault {
                   type string;
                   description
                     "Post fault";
                 }
                 leaf command-error {
                   type string;
                   description
                     "Command error";
                 }
                 leaf rx-pll-lock {
                   type string;
                   description
                     "RX PLL lock";
                 }
                 leaf network-lane-los {
                   type string;
                   description
                     "Network Lane LOS";
                 }
                 leaf network-lane-lof {
                   type string;
                   description
                     "Network Lane LOF";
                 }
                 leaf network-lane-oof {
                   type string;
                   description
                     "Network Lane OOF";
                 }
                 leaf network-lane-lom {
                   type string;
                   description
                     "Network Lane LOM";
                 }
                 leaf network-lane-oom {
                   type string;
                   description
                     "Network Lane OOM";
                 }
                 leaf network-lane-otu-bdi {
                   type string;
                   description
                     "Network Lane OTU BDI";
                 }
                 leaf lane-rx-fifo-error {
                   type string;
                   description
                     "Lane RX FIFO error";
                 }
                 leaf tx-reference-clock-fault {
                   type string;
                   description
                     "TX reference clock fault";
                 }
                 leaf rx-modem-sync-fault {
                   type string;
                   description
                     "Rx modem sync fault";
                 }
                 leaf rx-modem-loss-of-lock {
                   type string;
                   description
                     "RX modem loss of lock";
                 }
                 leaf rx-loss-of-alignment {
                   type string;
                   description
                     "RX loss of alignment";
                 }
                 leaf rx-out-of-alignment {
                   type string;
                   description
                     "RX out of alignment";
                 }
                 leaf rx-timing-fault {
                   type string;
                   description
                     "Rx timing fault";
                 }
                 leaf link-msg-data-available {
                   type string;
                   description
                     "Link msg data available";
                 }
                 leaf modulator-bias-control-loop-fail {
                   type string;
                   description
                     "Modulator Bias Control Loop Fail";
                 }
                 leaf itla-fault {
                   type string;
                   description
                     "ITLA fault";
                 }
                 leaf dac-calib-fault {
                   type string;
                   description
                     "DAC calib fault";
                 }
                 leaf adc-calib-fault {
                   type string;
                   description
                     "ADC calib fault";
                 }
                 leaf prom-fault {
                   type string;
                   description
                     "PROM fault";
                 }
                 leaf tx-mod-bias-voa-ctrl-loop-high-alarm {
                   type string;
                   description
                     "TX mod bias VOA ctrl loop high alarm";
                 }
                 leaf tx-mod-bias-voa-ctrl-loop-low-alarm {
                   type string;
                   description
                     "TX mod bias VOA ctrl loop low alarm";
                 }
                 leaf rx-phase-control-loop-high-alarm {
                   type string;
                   description
                     "RX phase control loop high alarm";
                 }
                 leaf rx-phase-control-loop-low-alarm {
                   type string;
                   description
                     "RX phase control loop low alarm";
                 }
                 leaf rx-phase-control-loop-high-warning {
                   type string;
                   description
                     "RX phase control loop high warning";
                 }
                 leaf rx-phase-control-loop-low-warning {
                   type string;
                   description
                     "RX phase control loop low warning";
                 }
                 leaf oa-pump-bias-current-high-alarm {
                   type string;
                   description
                     "OA pump bias current high alarm";
                 }
                 leaf oa-pump-bias-current-low-alarm {
                   type string;
                   description
                     "OA pump bias current low alarm";
                 }
                 leaf oa-pump-bias-current-high-warning {
                   type string;
                   description
                     "OA pump bias current high warning";
                 }
                 leaf oa-pump-bias-current-low-warning {
                   type string;
                   description
                     "OA pump bias current low warning";
                 }
                 leaf tx-jitter-pll-lol-input-nw-lane {
                   type string;
                   description
                     "Tx jitter PLL LOL i/p nw lane";
                 }
                 leaf tx-out-of-alignment {
                   type string;
                   description
                     "TX out of alignment";
                 }
                 leaf tx-cmu-lock-fault {
                   type string;
                   description
                     "Tx CMU lock fault";
                 }
                 leaf adc-signal-below-threshold {
                   type string;
                   description
                     "ADC signal below threshold";
                 }
                 leaf tx-output-power-adjustment-fault {
                   type string;
                   description
                     "Tx output power adjustment fault";
                 }
                 leaf tx-output-mod-converge-fault {
                   type string;
                   description
                     "TX output mod converge fault";
                 }
                 leaf tx-laser-ready-fault {
                   type string;
                   description
                     "Tx laser ready fault";
                 }
                 leaf tx-laser-ready-off-fault {
                   type string;
                   description
                     "Tx laser ready off fault";
                 }
                 leaf tx-asic-ready-fault {
                   type string;
                   description
                     "Tx asic ready fault";
                 }
                 leaf tx-initialization-fault {
                   type string;
                   description
                     "Tx initialization fault";
                 }
                 leaf rx-demodulator-lock-fault {
                   type string;
                   description
                     "Rx demodulator lock fault";
                 }
                 leaf rx-dispersion-lock-fault {
                   type string;
                   description
                     "Rx dispersion lock fault";
                 }
                 leaf rx-adc-output-fault {
                   type string;
                   description
                     "Rx ADC output fault";
                 }
                 leaf rx-optical-input-fault {
                   type string;
                   description
                     "Rx optical input fault";
                 }
                 leaf rx-asic-ready-fault {
                   type string;
                   description
                     "Rx asic ready fault";
                 }
                 leaf rx-initialization-fault {
                   type string;
                   description
                     "Rx initialization fault";
                 }
                 leaf tx-mod-bias-high-alarm {
                   type string;
                   description
                     "TX modulator bias high alarm";
                 }
                 leaf tx-mod-bias-low-alarm {
                   type string;
                   description
                     "TX modulator bias low alarm";
                 }
                 leaf tx-mod-bias-high-warning {
                   type string;
                   description
                     "TX modulator bias high warning";
                 }
                 leaf tx-mod-bias-low-warning {
                   type string;
                   description
                     "TX modulator bias low warning";
                 }
                 leaf rx-pwr-high-alarm {
                   type string;
                   description
                     "RX power high alarm";
                 }
                 leaf rx-pwr-low-alarm {
                   type string;
                   description
                     "RX power low alarm";
                 }
                 leaf rx-pwr-high-warn {
                   type string;
                   description
                     "RX power high warning";
                 }
                 leaf rx-pwr-low-warn {
                   type string;
                   description
                     "RX power low warning";
                 }
                 leaf tx-laser-power-high-alarm {
                   type string;
                   description
                     "TX laser power high alarm";
                 }
                 leaf tx-laser-power-low-alarm {
                   type string;
                   description
                     "TX laser power low alarm";
                 }
                 leaf tx-laser-power-high-warn {
                   type string;
                   description
                     "TX laser power high warning";
                 }
                 leaf tx-laser-power-low-warn {
                   type string;
                   description
                     "TX laser power low warning";
                 }
                 leaf tx-bias-high-alarm {
                   type string;
                   description
                     "TX laser current high alarm";
                 }
                 leaf tx-bias-low-alarm {
                   type string;
                   description
                     "TX laser current low alarm";
                 }
                 leaf tx-bias-high-warn {
                   type string;
                   description
                     "TX laser current high warning";
                 }
                 leaf tx-bias-low-warn {
                   type string;
                   description
                     "TX laser current low warning";
                 }
                 leaf tx-laser-temp-high-alarm {
                   type string;
                   description
                     "TX laser temperature high alarm";
                 }
                 leaf tx-laser-temp-low-alarm {
                   type string;
                   description
                     "TX laser temperature low alarm";
                 }
                 leaf tx-laser-temp-high-warn {
                   type string;
                   description
                     "TX laser temperature high warning";
                 }
                 leaf tx-laser-temp-low-warn {
                   type string;
                   description
                     "TX laser temperature low warning";
                 }
               }
             }
             list optics-diagnostics-vendor-extension {
               description
                 "Optics diagnostics vendor extension";
               leaf optics-vendor-part-number {
                 type string;
                 description
                   "Optics component vendor part number";
               }
               leaf optics-vendor-material-number {
                 type string;
                 description
                   "Optic component vendor material number";
               }
             }
           }
         }
         container peer-configuration-status {
           description
             "Nonmatching DCE end DLCIs";
           leaf peer-nonmatching-dlci {
             type int32;
             description
               "DCE end DLCIs that does not match the DTE";
           }
         }
         container lsi-traffic-statistics {
           leaf input-bytes {
             type int32;
           }
           leaf input-bps {
             type int32;
           }
           leaf input-packets {
             type int32;
           }
           leaf input-pps {
             type int32;
           }
         }
         container stp-traffic-statistics {
           leaf stp-input-bytes-dropped {
             type int32;
             description
               "Drop statistics due to stp state at ingress in bytes";
           }
           leaf stp-output-bytes-dropped {
             type int32;
             description
               "Drop statistics due to stp state at egress in bytes";
           }
           leaf stp-input-packets-dropped {
             type int32;
             description
               "Drop statistics due to stp state at ingress in packets";
           }
           leaf stp-output-packets-dropped {
             type int32;
             description
               "Drop statistics due to stp state at egress in packets";
           }
         }
         container af-fe-info {
         }
         container af-fe-q-pkts {
         }
         container af-fe-q-bytes {
         }
         container chassis-queue-counters {
           description
             "Chassis queue counter statistics";
           container interface-chassis-cos-summary {
             description
               "Packet Forwarding Engine chassis forwarding class and queue 
               information for an interface";
             leaf intf-cos-chassis-num-queues-supported {
               type int32;
               description
                 "Number of Packet Forwarding Engine chassis queues the 
                 interface supports";
             }
             leaf intf-cos-chassis-num-queues-in-use {
               type int32;
               description
                 "Number of Packet Forwarding Engine chassis queues in use 
                 on the interface";
             }
           }
           list queue {
             description
               "Counters for a single queue";
             leaf queue-number {
               type int32;
               description
                 "Queue number";
             }
             leaf forwarding-class-name {
               type string;
               description
                 "Forwarding class name associated with queue";
             }
             leaf queue-counters-queued-packets {
               type uint64;
               description
                 "Queued packet count";
             }
             leaf queue-counters-queued-packets-rate {
               type uint64;
               description
                 "Rate at which packets are queued";
             }
             leaf queue-counters-queued-bytes {
               type uint64;
               description
                 "Queued bytes count";
             }
             leaf queue-counters-queued-bytes-rate {
               type uint64;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets {
               type uint64;
               description
                 "Total number of transmitted packets";
             }
             leaf queue-counters-trans-packets-rate {
               type uint64;
               description
                 "Rate at which packets are transmitted";
             }
             leaf queue-counters-trans-bytes {
               type uint64;
               description
                 "Total number of transmitted bytes";
             }
             leaf queue-counters-trans-bytes-rate {
               type uint64;
               description
                 "Rate at which bytes are transmitted";
             }
             leaf queue-counters-tail-drop-packets-na {
               type string;
               description
                 "Number of packets dropped due to tail drop not available";
             }
             leaf queue-counters-tail-drop-packets {
               type uint64;
               description
                 "Number of packets dropped at the tail of the queue";
             }
             leaf queue-counters-tail-drop-packets-rate {
               type uint64;
               description
                 "Rate at which packets are dropped at tail of queue";
             }
             leaf queue-counters-tail-drop-bytes {
               type uint64;
               description
                 "Number of packets dropped at tail drop of the queue";
             }
             leaf queue-counters-tail-drop-bytes-rate {
               type uint64;
               description
                 "Number of packets dropped at tail drop of the queue";
             }
             leaf queue-counters-rate-limit-drop-packets-na {
               type string;
               description
                 "Number of packets dropped due to rate-limit drop not 
                 available";
             }
             leaf queue-counters-rate-limit-drop-packets {
               type uint64;
               description
                 "Number of packets dropped by rate-limit for the queue";
             }
             leaf queue-counters-rate-limit-drop-packets-rate {
               type uint64;
               description
                 "Rate at which packets are dropped by rate-limit for the 
                 queue";
             }
             leaf queue-counters-rate-limit-drop-bytes-na {
               type string;
               description
                 "Number of bytes dropped due to tail drop not available";
             }
             leaf queue-counters-rate-limit-drop-bytes {
               type uint64;
               description
                 "Number of bytes dropped at the tail of the queue";
             }
             leaf queue-counters-rate-limit-drop-bytes-rate {
               type uint64;
               description
                 "Rate at which bytes are dropped at the tail of the queue";
             }
             leaf queue-counters-red-packets-na {
               type string;
               description
                 "Number of packets dropped due to RED not available";
             }
             leaf queue-counters-red-packets {
               type uint64;
               description
                 "Number of packets dropped due to RED";
             }
             leaf queue-counters-red-packets-rate {
               type uint64;
               description
                 "Rate at which packets are dropped due to RED";
             }
             leaf queue-counters-red-packets-ln {
               type uint64;
               description
                 "Number of RED dropped low-loss, non-TCP packets";
             }
             leaf queue-counters-red-packets-rate-ln {
               type uint64;
               description
                 "RED drop rate for low-loss, non-TCP packets";
             }
             leaf queue-counters-red-packets-lt {
               type uint64;
               description
                 "Number of RED dropped of low-loss, TCP packets";
             }
             leaf queue-counters-red-packets-rate-lt {
               type uint64;
               description
                 "RED drop rate for low-loss, TCP packets";
             }
             leaf queue-counters-red-packets-hn {
               type uint64;
               description
                 "Number of RED dropped high-loss, non-TCP packets";
             }
             leaf queue-counters-red-packets-rate-hn {
               type uint64;
               description
                 "RED drop rate for high-loss, non-TCP packets";
             }
             leaf queue-counters-red-packets-ht {
               type uint64;
               description
                 "Number of RED dropped high-loss, TCP packets";
             }
             leaf queue-counters-red-packets-rate-ht {
               type uint64;
               description
                 "RED drop rate for high-loss, TCP packets";
             }
             leaf queue-counters-red-packets-low {
               type uint64;
               description
                 "Number of RED dropped low-loss packets";
             }
             leaf queue-counters-red-packets-rate-low {
               type uint64;
               description
                 "RED drop rate for low-loss packets";
             }
             leaf queue-counters-red-packets-medium-low {
               type uint64;
               description
                 "Number of RED dropped medium-low-loss packets";
             }
             leaf queue-counters-red-packets-rate-medium-low {
               type uint64;
               description
                 "RED drop rate for medium-low-loss packets";
             }
             leaf queue-counters-red-packets-medium-high {
               type uint64;
               description
                 "Number of RED dropped medium-high-loss packets";
             }
             leaf queue-counters-red-packets-rate-medium-high {
               type uint64;
               description
                 "RED drop rate for medium-high-loss packets";
             }
             leaf queue-counters-red-packets-medium {
               type uint64;
               description
                 "Number of RED dropped medium-loss packets";
             }
             leaf queue-counters-red-packets-rate-medium {
               type uint64;
               description
                 "RED drop rate for medium-loss packets";
             }
             leaf queue-counters-red-packets-high {
               type uint64;
               description
                 "Number of RED dropped high-loss packets";
             }
             leaf queue-counters-red-packets-rate-high {
               type uint64;
               description
                 "RED drop rate for high-loss packets";
             }
             leaf queue-counters-red-bytes-na {
               type string;
               description
                 "Number of bytes dropped due to RED not available";
             }
             leaf queue-counters-red-bytes {
               type uint64;
               description
                 "Number of bytes dropped due to RED";
             }
             leaf queue-counters-red-bytes-rate {
               type uint64;
               description
                 "Rate at which bytes are dropped due to RED";
             }
             leaf queue-counters-red-bytes-ln {
               type uint64;
               description
                 "Number of RED dropped low-loss, non-TCP bytes";
             }
             leaf queue-counters-red-bytes-rate-ln {
               type uint64;
               description
                 "RED drop rate for low-loss, non-TCP bytes";
             }
             leaf queue-counters-red-bytes-lt {
               type uint64;
               description
                 "Number of RED dropped low-loss, TCP bytes";
             }
             leaf queue-counters-red-bytes-rate-lt {
               type uint64;
               description
                 "RED drop rate for low-loss, TCP bytes";
             }
             leaf queue-counters-red-bytes-hn {
               type uint64;
               description
                 "Number of RED dropped high-loss, non-TCP bytes";
             }
             leaf queue-counters-red-bytes-rate-hn {
               type uint64;
               description
                 "RED drop rate for high-loss, non-TCP bytes";
             }
             leaf queue-counters-red-bytes-ht {
               type uint64;
               description
                 "Number of RED dropped high-loss, TCP bytes";
             }
             leaf queue-counters-red-bytes-rate-ht {
               type uint64;
               description
                 "RED drop rate for high-loss, TCP bytes";
             }
             leaf queue-counters-red-bytes-low {
               type uint64;
               description
                 "Number of RED dropped low-loss bytes";
             }
             leaf queue-counters-red-bytes-rate-low {
               type uint64;
               description
                 "RED drop rate for low-loss bytes";
             }
             leaf queue-counters-red-bytes-medium-low {
               type uint64;
               description
                 "Number of RED dropped medium-low-loss bytes";
             }
             leaf queue-counters-red-bytes-rate-medium-low {
               type uint64;
               description
                 "RED drop rate for medium-low-loss bytes";
             }
             leaf queue-counters-red-bytes-medium-high {
               type uint64;
               description
                 "Number of RED dropped medium-high-loss bytes";
             }
             leaf queue-counters-red-bytes-rate-medium-high {
               type uint64;
               description
                 "RED drop rate for medium-high-loss bytes";
             }
             leaf queue-counters-red-bytes-medium {
               type uint64;
               description
                 "Number of RED dropped medium-loss bytes";
             }
             leaf queue-counters-red-bytes-rate-medium {
               type uint64;
               description
                 "RED drop rate for medium-loss bytes";
             }
             leaf queue-counters-red-bytes-high {
               type uint64;
               description
                 "Number of RED dropped high-loss bytes";
             }
             leaf queue-counters-red-bytes-rate-high {
               type uint64;
               description
                 "RED drop rate for high-loss bytes";
             }
             leaf queue-counters-timestamp {
               type uint64;
               description
                 "Last packet enqueued timestamp";
             }
             leaf queue-counters-total-drop-packets {
               type uint64;
               description
                 "Number of total packets dropped at the queue";
             }
             leaf queue-counters-total-drop-packets-rate {
               type uint64;
               description
                 "Number of total packets dropped at the queue";
             }
             leaf queue-counters-total-drop-bytes {
               type uint64;
               description
                 "Number of total packets dropped at the queue";
             }
             leaf queue-counters-total-drop-bytes-rate {
               type uint64;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
         }
         container ingress-queue-counters {
           description
             "Ingress queue counter statistics";
           list queue {
             description
               "Counters for a single queue";
             leaf queue-number {
               type int32;
               description
                 "Queue number";
             }
             leaf forwarding-class-name {
               type string;
               description
                 "Forwarding class name associated with queue";
             }
             leaf queue-counters-queued-packets {
               type uint64;
               description
                 "Queued packet count";
             }
             leaf queue-counters-queued-packets-rate {
               type uint64;
               description
                 "Rate at which packets are queued";
             }
             leaf queue-counters-queued-bytes {
               type uint64;
               description
                 "Queued bytes count";
             }
             leaf queue-counters-queued-bytes-rate {
               type uint64;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets {
               type uint64;
               description
                 "Total number of transmitted packets";
             }
             leaf queue-counters-trans-packets-rate {
               type uint64;
               description
                 "Rate at which packets are transmitted";
             }
             leaf queue-counters-trans-bytes {
               type uint64;
               description
                 "Total number of transmitted bytes";
             }
             leaf queue-counters-trans-bytes-rate {
               type uint64;
               description
                 "Rate at which bytes are transmitted";
             }
             leaf queue-counters-tail-drop-packets-na {
               type string;
               description
                 "Number of packets dropped due to tail drop not available";
             }
             leaf queue-counters-tail-drop-packets {
               type uint64;
               description
                 "Number of packets dropped at the tail of the queue";
             }
             leaf queue-counters-tail-drop-packets-rate {
               type uint64;
               description
                 "Rate at which packets are dropped at tail of queue";
             }
             leaf queue-counters-tail-drop-bytes {
               type uint64;
               description
                 "Number of packets dropped at tail drop of the queue";
             }
             leaf queue-counters-tail-drop-bytes-rate {
               type uint64;
               description
                 "Number of packets dropped at tail drop of the queue";
             }
             leaf queue-counters-rate-limit-drop-packets-na {
               type string;
               description
                 "Number of packets dropped due to rate-limit drop not 
                 available";
             }
             leaf queue-counters-rate-limit-drop-packets {
               type uint64;
               description
                 "Number of packets dropped by rate-limit for the queue";
             }
             leaf queue-counters-rate-limit-drop-packets-rate {
               type uint64;
               description
                 "Rate at which packets are dropped by rate-limit for the 
                 queue";
             }
             leaf queue-counters-rate-limit-drop-bytes-na {
               type string;
               description
                 "Number of bytes dropped due to tail drop not available";
             }
             leaf queue-counters-rate-limit-drop-bytes {
               type uint64;
               description
                 "Number of bytes dropped at the tail of the queue";
             }
             leaf queue-counters-rate-limit-drop-bytes-rate {
               type uint64;
               description
                 "Rate at which bytes are dropped at the tail of the queue";
             }
             leaf queue-counters-red-packets-na {
               type string;
               description
                 "Number of packets dropped due to RED not available";
             }
             leaf queue-counters-red-packets {
               type uint64;
               description
                 "Number of packets dropped due to RED";
             }
             leaf queue-counters-red-packets-rate {
               type uint64;
               description
                 "Rate at which packets are dropped due to RED";
             }
             leaf queue-counters-red-packets-ln {
               type uint64;
               description
                 "Number of RED dropped low-loss, non-TCP packets";
             }
             leaf queue-counters-red-packets-rate-ln {
               type uint64;
               description
                 "RED drop rate for low-loss, non-TCP packets";
             }
             leaf queue-counters-red-packets-lt {
               type uint64;
               description
                 "Number of RED dropped of low-loss, TCP packets";
             }
             leaf queue-counters-red-packets-rate-lt {
               type uint64;
               description
                 "RED drop rate for low-loss, TCP packets";
             }
             leaf queue-counters-red-packets-hn {
               type uint64;
               description
                 "Number of RED dropped high-loss, non-TCP packets";
             }
             leaf queue-counters-red-packets-rate-hn {
               type uint64;
               description
                 "RED drop rate for high-loss, non-TCP packets";
             }
             leaf queue-counters-red-packets-ht {
               type uint64;
               description
                 "Number of RED dropped high-loss, TCP packets";
             }
             leaf queue-counters-red-packets-rate-ht {
               type uint64;
               description
                 "RED drop rate for high-loss, TCP packets";
             }
             leaf queue-counters-red-packets-low {
               type uint64;
               description
                 "Number of RED dropped low-loss packets";
             }
             leaf queue-counters-red-packets-rate-low {
               type uint64;
               description
                 "RED drop rate for low-loss packets";
             }
             leaf queue-counters-red-packets-medium-low {
               type uint64;
               description
                 "Number of RED dropped medium-low-loss packets";
             }
             leaf queue-counters-red-packets-rate-medium-low {
               type uint64;
               description
                 "RED drop rate for medium-low-loss packets";
             }
             leaf queue-counters-red-packets-medium-high {
               type uint64;
               description
                 "Number of RED dropped medium-high-loss packets";
             }
             leaf queue-counters-red-packets-rate-medium-high {
               type uint64;
               description
                 "RED drop rate for medium-high-loss packets";
             }
             leaf queue-counters-red-packets-medium {
               type uint64;
               description
                 "Number of RED dropped medium-loss packets";
             }
             leaf queue-counters-red-packets-rate-medium {
               type uint64;
               description
                 "RED drop rate for medium-loss packets";
             }
             leaf queue-counters-red-packets-high {
               type uint64;
               description
                 "Number of RED dropped high-loss packets";
             }
             leaf queue-counters-red-packets-rate-high {
               type uint64;
               description
                 "RED drop rate for high-loss packets";
             }
             leaf queue-counters-red-bytes-na {
               type string;
               description
                 "Number of bytes dropped due to RED not available";
             }
             leaf queue-counters-red-bytes {
               type uint64;
               description
                 "Number of bytes dropped due to RED";
             }
             leaf queue-counters-red-bytes-rate {
               type uint64;
               description
                 "Rate at which bytes are dropped due to RED";
             }
             leaf queue-counters-red-bytes-ln {
               type uint64;
               description
                 "Number of RED dropped low-loss, non-TCP bytes";
             }
             leaf queue-counters-red-bytes-rate-ln {
               type uint64;
               description
                 "RED drop rate for low-loss, non-TCP bytes";
             }
             leaf queue-counters-red-bytes-lt {
               type uint64;
               description
                 "Number of RED dropped low-loss, TCP bytes";
             }
             leaf queue-counters-red-bytes-rate-lt {
               type uint64;
               description
                 "RED drop rate for low-loss, TCP bytes";
             }
             leaf queue-counters-red-bytes-hn {
               type uint64;
               description
                 "Number of RED dropped high-loss, non-TCP bytes";
             }
             leaf queue-counters-red-bytes-rate-hn {
               type uint64;
               description
                 "RED drop rate for high-loss, non-TCP bytes";
             }
             leaf queue-counters-red-bytes-ht {
               type uint64;
               description
                 "Number of RED dropped high-loss, TCP bytes";
             }
             leaf queue-counters-red-bytes-rate-ht {
               type uint64;
               description
                 "RED drop rate for high-loss, TCP bytes";
             }
             leaf queue-counters-red-bytes-low {
               type uint64;
               description
                 "Number of RED dropped low-loss bytes";
             }
             leaf queue-counters-red-bytes-rate-low {
               type uint64;
               description
                 "RED drop rate for low-loss bytes";
             }
             leaf queue-counters-red-bytes-medium-low {
               type uint64;
               description
                 "Number of RED dropped medium-low-loss bytes";
             }
             leaf queue-counters-red-bytes-rate-medium-low {
               type uint64;
               description
                 "RED drop rate for medium-low-loss bytes";
             }
             leaf queue-counters-red-bytes-medium-high {
               type uint64;
               description
                 "Number of RED dropped medium-high-loss bytes";
             }
             leaf queue-counters-red-bytes-rate-medium-high {
               type uint64;
               description
                 "RED drop rate for medium-high-loss bytes";
             }
             leaf queue-counters-red-bytes-medium {
               type uint64;
               description
                 "Number of RED dropped medium-loss bytes";
             }
             leaf queue-counters-red-bytes-rate-medium {
               type uint64;
               description
                 "RED drop rate for medium-loss bytes";
             }
             leaf queue-counters-red-bytes-high {
               type uint64;
               description
                 "Number of RED dropped high-loss bytes";
             }
             leaf queue-counters-red-bytes-rate-high {
               type uint64;
               description
                 "RED drop rate for high-loss bytes";
             }
             leaf queue-counters-timestamp {
               type uint64;
               description
                 "Last packet enqueued timestamp";
             }
             leaf queue-counters-total-drop-packets {
               type uint64;
               description
                 "Number of total packets dropped at the queue";
             }
             leaf queue-counters-total-drop-packets-rate {
               type uint64;
               description
                 "Number of total packets dropped at the queue";
             }
             leaf queue-counters-total-drop-bytes {
               type uint64;
               description
                 "Number of total packets dropped at the queue";
             }
             leaf queue-counters-total-drop-bytes-rate {
               type uint64;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
           container interface-cos-short-summary {
             description
               "Summary of queue information on an interface";
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           container queue-num-forwarding-class-name-map {
             leaf queue-number {
               type int32;
               description
                 "Queue number";
             }
             leaf forwarding-class-name {
               type string;
               description
                 "Forwarding class name associated with queue";
             }
           }
         }
         container otn-oc-information {
           list media-alarm {
             leaf media-alarm-name {
               type string;
             }
             leaf media-alarm-seconds {
               type int32;
             }
             leaf media-alarm-count {
               type int32;
             }
             leaf media-alarm-state {
               type string;
             }
           }
         }
         container otn-otu-information {
           list media-alarm {
             leaf media-alarm-name {
               type string;
             }
             leaf media-alarm-seconds {
               type int32;
             }
             leaf media-alarm-count {
               type int32;
             }
             leaf media-alarm-state {
               type string;
             }
           }
         }
         container otn-odu-information {
           list media-alarm {
             leaf media-alarm-name {
               type string;
             }
             leaf media-alarm-seconds {
               type int32;
             }
             leaf media-alarm-count {
               type int32;
             }
             leaf media-alarm-state {
               type string;
             }
           }
         }
         container otn-ot-module-information {
           list media-alarm {
             leaf media-alarm-name {
               type string;
             }
             leaf media-alarm-seconds {
               type int32;
             }
             leaf media-alarm-count {
               type int32;
             }
             leaf media-alarm-state {
               type string;
             }
           }
         }
         list otn-odu-tcm-information {
           list media-alarm {
             leaf media-alarm-name {
               type string;
             }
             leaf media-alarm-seconds {
               type int32;
             }
             leaf media-alarm-count {
               type int32;
             }
             leaf media-alarm-state {
               type string;
             }
           }
         }
         container ima-group-information {
           description
             "IMA group alarms";
         }
         container ima-link-information {
           description
             "IMA link alarms";
         }
         container ethernet-mac-pfc-statistics {
           description
             "Ethernet MAC Priority Flow control Statistics";
           leaf mac-pfc-dot1p {
             type int32;
           }
           leaf input-mac-pfc-frames {
             type int32;
           }
           leaf output-mac-pfc-frames {
             type int32;
           }
         }
         container cos-information {
           description
             "Information about class-of-service configuration";
           list cos-stream-information {
             description
               "Information about the traffic stream";
           }
           container cos-forwarding-class-information {
             container fc-map {
               description
                 "Class-of-service forwarding class to queue mapping";
               list fc-map-item {
                 leaf fc-name {
                   type string;
                   description
                     "Class-of-service forwarding class name";
                 }
                 leaf fc-number {
                   type uint32;
                   description
                     "Identifier for Class-of-service forwarding class";
                 }
                 leaf fc-queue-number {
                   type uint32;
                   description
                     "Class-of-service forwarding class queue number";
                 }
                 leaf fc-rqueue-number {
                   type uint32;
                   description
                     "Class-of-service forwarding class restricted queue 
                     number";
                 }
                 leaf fc-priority {
                   type string;
                   description
                     "Class-of-service forwarding class queue priority";
                 }
                 leaf fc-policing-priority {
                   type string;
                   description
                     "Class-of-service forwarding class policing priority";
                 }
                 leaf fc-spu-priority {
                   type string;
                   description
                     "Class-of-service forwarding class spu priority";
                 }
                 leaf fc-no-loss {
                   type string;
                   description
                     "Class-of-service forwarding class no-loss";
                 }
                 leaf fc-pfc-priority {
                   type string;
                   description
                     "Class-of-service forwarding class pfc-priority";
                 }
                 leaf fc-multicast {
                   type string;
                   description
                     "Class-of-service forwarding class multicast";
                 }
                 leaf fc-latency-ecn {
                   type string;
                   description
                     "Class-of-service forwarding class latency ECN";
                 }
               }
             }
           }
           container cos-forwarding-class-map-information {
             container fc-map {
               description
                 "Class-of-service forwarding class to queue mapping";
               list fc-map-item {
                 leaf fc-name {
                   type string;
                   description
                     "Class-of-service forwarding class name";
                 }
                 leaf fc-number {
                   type uint32;
                   description
                     "Identifier for Class-of-service forwarding class";
                 }
                 leaf fc-queue-number {
                   type uint32;
                   description
                     "Class-of-service forwarding class queue number";
                 }
                 leaf fc-rqueue-number {
                   type uint32;
                   description
                     "Class-of-service forwarding class restricted queue 
                     number";
                 }
                 leaf fc-priority {
                   type string;
                   description
                     "Class-of-service forwarding class queue priority";
                 }
                 leaf fc-policing-priority {
                   type string;
                   description
                     "Class-of-service forwarding class policing priority";
                 }
                 leaf fc-spu-priority {
                   type string;
                   description
                     "Class-of-service forwarding class spu priority";
                 }
                 leaf fc-no-loss {
                   type string;
                   description
                     "Class-of-service forwarding class no-loss";
                 }
                 leaf fc-pfc-priority {
                   type string;
                   description
                     "Class-of-service forwarding class pfc-priority";
                 }
                 leaf fc-multicast {
                   type string;
                   description
                     "Class-of-service forwarding class multicast";
                 }
                 leaf fc-latency-ecn {
                   type string;
                   description
                     "Class-of-service forwarding class latency ECN";
                 }
               }
             }
           }
           container cos-classifier-information {
             list classifier {
               description
                 "Class-of-service code point classifier";
               leaf classifier-name {
                 type string;
                 description
                   "Class-of-service classifier name";
               }
               leaf code-point-type {
                 type string;
                 description
                   "Class-of-service code point type";
               }
               leaf table-index {
                 type uint32;
                 description
                   "Table index";
               }
               container classifier-map {
                 list classifier-map-item {
                   leaf code-point {
                     type string;
                     description
                       "Class-of-service code point alias name or bits";
                   }
                   leaf fc-name {
                     type string;
                     description
                       "Class-of-service forwarding class name";
                   }
                   leaf loss-priority {
                     type string;
                     description
                       "Class-of-service loss priority";
                   }
                   leaf cntag-present {
                     type string;
                     description
                       "Class-of-service cntag present";
                   }
                 }
               }
             }
           }
           container cos-loss-priority-map-information {
             list loss-priority-map {
               description
                 "Class-of-service code point loss priority map";
               leaf loss-priority-map-name {
                 type string;
                 description
                   "Name of class-of-service loss priority map";
               }
               leaf code-point-type {
                 type string;
                 description
                   "Class-of-service code point type";
               }
               leaf table-index {
                 type uint32;
                 description
                   "Table index";
               }
               list loss-priority-map-table {
                 list loss-priority-map-item {
                   leaf code-point {
                     type string;
                     description
                       "Class-of-service code point alias name or bits";
                   }
                   leaf loss-priority {
                     type string;
                     description
                       "Class-of-service loss priority";
                   }
                 }
                 list loss-priority-map-table-entry {
                   leaf table-index {
                     type uint32;
                     description
                       "Table index";
                   }
                   leaf code-point {
                     type string;
                     description
                       "Class-of-service code point alias name or bits";
                   }
                   leaf loss-priority {
                     type string;
                     description
                       "Class-of-service loss priority";
                   }
                 }
               }
             }
           }
           container cos-drop-profile-information {
             list drop-profile {
               description
                 "Class-of-service drop profile";
               leaf profile-name {
                 type string;
                 description
                   "Class-of-service drop profile name";
               }
               leaf profile-type {
                 type string;
                 description
                   "Class-of-service drop profile type";
               }
               leaf table-index {
                 type uint32;
                 description
                   "Table index";
               }
               container profile-map {
                 list profile-map-item {
                   leaf fill-level {
                     type uint32;
                     description
                       "Class-of-service drop profile fill level value";
                   }
                   leaf probability {
                     type uint32;
                     description
                       "Class-of-service drop profile probability value";
                   }
                 }
               }
             }
           }
           container cos-mpls-ecn-map-information {
             list cos-mpls-ecn-map-info {
               description
                 "Class-of-service mpls-ecn-map information";
               leaf ecn-capable-exp {
                 type int32;
                 description
                   "ECN capable exp";
               }
               leaf congestion-experienced-exp {
                 type int32;
                 description
                   "Congestion Expereienced exp";
               }
             }
           }
           container cos-monitoring-profile-information {
             list monitoring-profile {
               description
                 "Class-of-service monitoring profile";
               leaf monitoring-profile-name {
                 type string;
                 description
                   "Class-of-service monitoring profile name";
               }
               container export-filters {
                 container export-filter {
                   leaf filter-name {
                     type string;
                     description
                       "Class-of-service monitoring profile filter name";
                   }
                   leaf monitoring-queue-number {
                     type uint32;
                     description
                       "Class-of-service monitoring profile filter queue 
                       value";
                   }
                   leaf peak-queue-length-value {
                     type uint32;
                     description
                       "Class-of-service monitoring profile peak queue 
                       length value";
                   }
                 }
               }
             }
           }
           container cos-rewrite-information {
             list rewrite {
               description
                 "Class-of-service drop profile";
               leaf rewrite-name {
                 type string;
                 description
                   "Class-of-service rewrite rule name";
               }
               leaf code-point-type {
                 type string;
                 description
                   "Class-of-service code point type";
               }
               leaf table-index {
                 type uint32;
                 description
                   "Table index";
               }
               container rewrite-map {
                 list rewrite-map-item {
                   leaf fc-name {
                     type string;
                     description
                       "Class-of-service forwarding class name";
                   }
                   leaf loss-priority {
                     type string;
                     description
                       "Class-of-service loss priority";
                   }
                   leaf code-point {
                     type string;
                     description
                       "Class-of-service code point alias name or bits";
                   }
                 }
               }
             }
           }
           container cos-loss-priority-rewrite-information {
             list loss-priority-rewrite {
               description
                 "Class-of-service loss priority to code point rewrite";
               leaf loss-priority-rewrite-name {
                 type string;
                 description
                   "Name of class-of-service loss priority rewrite";
               }
               leaf code-point-type {
                 type string;
                 description
                   "Class-of-service code point type";
               }
               leaf table-index {
                 type uint32;
                 description
                   "Table index";
               }
               list loss-priority-rewrite-table {
                 list loss-priority-rewrite-item {
                   leaf loss-priority {
                     type string;
                     description
                       "Class-of-service loss priority";
                   }
                   leaf code-point {
                     type string;
                     description
                       "Class-of-service code point alias name or bits";
                   }
                 }
                 list loss-priority-rewrite-table-entry {
                   leaf table-index {
                     type uint32;
                     description
                       "Table index";
                   }
                   leaf loss-priority {
                     type string;
                     description
                       "Class-of-service loss priority";
                   }
                   leaf code-point {
                     type string;
                     description
                       "Class-of-service code point alias name or bits";
                   }
                 }
               }
             }
           }
           container cos-code-point-map-information {
             list code-point-map {
               description
                 "Class-of-service code point alias map";
               leaf code-point-type {
                 type string;
                 description
                   "Class-of-service code point type";
               }
               container alias-map {
                 list alias-map-item {
                   leaf code-point-alias {
                     type string;
                     description
                       "Class-of-service code point alias name";
                   }
                   leaf code-point-bits {
                     type string;
                     description
                       "Class-of-service code point bit sequence";
                   }
                 }
               }
             }
           }
           container cos-fragmentation-map-information {
             list fragmentation-map {
               description
                 "Class-of-service fragmentation map";
               leaf fragmentation-map-name {
                 type string;
                 description
                   "Class-of-service fragmentation map name";
               }
               leaf fragmentation-map-index {
                 type uint32;
                 description
                   "Index number for Class-of-service fragmentation map";
               }
               list fragment-map {
                 leaf fc-name {
                   type string;
                   description
                     "Class-of-service forwarding class name";
                 }
                 leaf no-fragmentation {
                   type empty;
                   description
                     "Do not fragment packets of this class";
                 }
                 leaf fragment-threshold {
                   type string;
                   description
                     "Fragmentation threshold";
                 }
                 leaf fragment-multilink-class {
                   type int32;
                   description
                     "Identifier for multilink class";
                 }
               }
             }
           }
           container cos-translation-table-map-information {
             list translation-table {
               description
                 "Class-of-service code point translation table";
               leaf translation-table-name {
                 type string;
                 description
                   "Class-of-service translation table name";
               }
               leaf translation-table-type {
                 type string;
                 description
                   "Class-of-service translation table type";
               }
               leaf table-index {
                 type uint32;
                 description
                   "Table index";
               }
               container translation-table-map {
                 container translation-table-map-item {
                   leaf from-code-point {
                     type string;
                     description
                       "Class-of-service code point alias name or bits";
                   }
                   leaf to-code-point {
                     type string;
                     description
                       "Class-of-service code point alias name or bits";
                   }
                 }
               }
               list translation-table-entry {
                 leaf table-index {
                   type uint32;
                   description
                     "Table index";
                 }
                 leaf from-code-point {
                   type string;
                   description
                     "Class-of-service code point alias name or bits";
                 }
                 leaf to-code-point {
                   type string;
                   description
                     "Class-of-service code point alias name or bits";
                 }
               }
             }
           }
           container cos-multi-destination-information {
             container sm-md-map {
               leaf scheduler-map-name {
                 type string;
                 description
                   "Class-of-service scheduler map name";
               }
               leaf scheduler-map-index {
                 type uint64;
                 description
                   "Class-of-service scheduler map index";
               }
             }
             container fc-md-map {
               leaf fc-name {
                 type string;
                 description
                   "Class-of-service forwarding class name";
               }
               leaf fc-queue-number {
                 type uint32;
                 description
                   "Class-of-service forwarding class queue number";
               }
             }
             container cls-md-map {
               leaf multidest-classifier-name {
                 type string;
                 description
                   "Multi destination classifier name";
               }
               leaf multidest-classifier-type {
                 type string;
                 description
                   "Multi destination classifier type";
               }
               leaf multidest-classifier-index {
                 type uint32;
                 description
                   "Multi destination classifier id";
               }
             }
           }
           container cos-forwarding-class-set-information {
             list forwarding-class-set {
               description
                 "Class-of-service forwarding class set information";
               list forwarding-class-set-entry {
                 leaf forwarding-class-set-name {
                   type string;
                   description
                     "Class-of-service forwarding class set name";
                 }
                 leaf forwarding-class-set-type {
                   type string;
                   description
                     "Identifier for Class-of-service forwarding class set 
                     type";
                 }
                 leaf forwarding-class-set-index {
                   type uint32;
                   description
                     "Identifier for Class-of-service forwarding class set";
                 }
                 container fc-map {
                   description
                     "Class-of-service forwarding class to queue mapping";
                   list fc-map-item {
                     leaf fc-name {
                       type string;
                       description
                         "Class-of-service forwarding class name";
                     }
                     leaf fc-number {
                       type uint32;
                       description
                         "Identifier for Class-of-service forwarding class";
                     }
                     leaf fc-queue-number {
                       type uint32;
                       description
                         "Class-of-service forwarding class queue number";
                     }
                     leaf fc-rqueue-number {
                       type uint32;
                       description
                         "Class-of-service forwarding class restricted queue
                         number";
                     }
                     leaf fc-priority {
                       type string;
                       description
                         "Class-of-service forwarding class queue priority";
                     }
                     leaf fc-policing-priority {
                       type string;
                       description
                         "Class-of-service forwarding class policing 
                         priority";
                     }
                     leaf fc-spu-priority {
                       type string;
                       description
                         "Class-of-service forwarding class spu priority";
                     }
                     leaf fc-no-loss {
                       type string;
                       description
                         "Class-of-service forwarding class no-loss";
                     }
                     leaf fc-pfc-priority {
                       type string;
                       description
                         "Class-of-service forwarding class pfc-priority";
                     }
                     leaf fc-multicast {
                       type string;
                       description
                         "Class-of-service forwarding class multicast";
                     }
                     leaf fc-latency-ecn {
                       type string;
                       description
                         "Class-of-service forwarding class latency ECN";
                     }
                   }
                 }
               }
             }
           }
           container cos-policy-map-information {
             list policy-map {
               description
                 "Class-of-service Policy-map";
               leaf policy-map-name {
                 type string;
                 description
                   "Class-of-service Policy-map name";
               }
               leaf table-index {
                 type uint32;
                 description
                   "Table index";
               }
               leaf policy-map-user-attribute {
                 type uint32;
                 description
                   "User-defined attribute";
               }
               container policy-map-cp-entries {
                 leaf code-point-type {
                   type string;
                   description
                     "Class-of-service code point type";
                 }
                 leaf code-point {
                   type string;
                   description
                     "Class-of-service code point alias name or bits";
                 }
                 leaf code-point-option {
                   type string;
                   description
                     "Class-of-service code point option flag";
                 }
               }
             }
           }
           container cos-client-info {
             list cos-client {
               description
                 "Class-of-service Junos client information";
               leaf cos-client-info-internal-id {
                 type uint32;
                 description
                   "Junos client internal identifier";
               }
               leaf cos-client-info-requests {
                 type uint32;
                 description
                   "Number of requests from Junos client";
               }
               leaf cos-client-info-responses {
                 type uint32;
                 description
                   "Number of responses to Junos client";
               }
               leaf cos-client-info-failures {
                 type uint32;
                 description
                   "Number of failures while handling Junos client requests";
               }
               leaf cos-client-info-identifier {
                 type string;
                 description
                   "Junos client identifier";
               }
               leaf cos-client-name {
                 type string;
                 description
                   "Junos client name";
               }
               leaf cos-client-state {
                 type string;
                 description
                   "Junos client state information";
               }
               leaf cos-client-internal-name {
                 type string;
                 description
                   "Junos client internal name";
               }
               leaf cos-client-stats {
                 type string;
                 description
                   "Junos client statistics";
               }
               leaf cos-client-failure-stats {
                 type string;
                 description
                   "Junos client failure/error statistics";
               }
               leaf cos-client-validate-failures {
                 type uint32;
                 description
                   "Junos client request validation failures";
               }
               leaf cos-client-ownership-failures {
                 type uint32;
                 description
                   "Junos client ownership validation failures";
               }
               leaf cos-client-info-name {
                 type string;
                 description
                   "CoS client name";
               }
               leaf cos-client-internal-id {
                 type uint32;
                 description
                   "Junos client internal identifier";
               }
               leaf cos-client-requests {
                 type uint64;
                 description
                   "Number of requests from Junos client";
               }
               leaf cos-client-responses {
                 type uint64;
                 description
                   "Number of responses to Junos client";
               }
               leaf cos-client-failures {
                 type uint64;
                 description
                   "Number of failures while handling Junos client requests";
               }
               leaf cos-client-identifier {
                 type string;
                 description
                   "Junos client identifier";
               }
               leaf cos-client-status {
                 type string;
                 description
                   "Junos client status";
               }
               leaf cos-client-connected-time {
                 type string;
                 description
                   "Junos client time of connect";
               }
               leaf cos-client-reconnected-time {
                 type string;
                 description
                   "Junos client time of reconnect";
               }
               leaf cos-client-disconnected-time {
                 type string;
                 description
                   "Junos client time of disconnect";
               }
               leaf cos-client-message-type {
                 type string;
                 description
                   "Junos client message type";
               }
               leaf cos-client-operation-type {
                 type string;
                 description
                   "Junos client operation type";
               }
               leaf-list cos-bind-point-type {
                 type string;
                 description
                   "Class-of-service bind point type";
               }
               leaf-list cos-bind-point-owner-type {
                 type string;
                 description
                   "Class-of-service bind point owner type";
               }
               leaf-list cos-bind-point-owner-internal-id {
                 type uint32;
                 description
                   "Junos client internal identifier";
               }
               leaf-list cos-bind-point-name {
                 type string;
                 description
                   "Class-of-service bind point name";
               }
               leaf cos-bind-point-feature {
                 type string;
                 description
                   "Class-of-service bind point feature name";
               }
               leaf cos-bind-point-feature-object-name {
                 type string;
                 description
                   "Class-of-service bind point feature object name";
               }
             }
           }
           container cos-host-outbound-info {
             list cos-host-outbound-traffic-info {
               description
                 "Class-of-service host-outbound-traffic information";
               leaf cos-host-outbound-traffic-protocol-name {
                 type string;
                 description
                   "CoS host outbound traffic protocol name";
               }
               leaf cos-host-outbound-traffic-dscp {
                 type string;
                 description
                   "CoS host outbound traffic dscp";
               }
               leaf cos-host-outbound-traffic-dot1p {
                 type string;
                 description
                   "CoS host outbound traffic ieee 802.1p";
               }
               leaf cos-host-outbound-traffic-fc-id {
                 type string;
                 description
                   "CoS host outbound traffic forwarding class id";
               }
               leaf cos-host-outbound-traffic-queue-id {
                 type string;
                 description
                   "CoS host outbound traffic queue id";
               }
               leaf cos-host-outbound-traffic-restrict-queue-id {
                 type string;
                 description
                   "CoS host outbound traffic restrict queue id";
               }
               leaf cos-host-outbound-traffic-override-firewall {
                 type string;
                 description
                   "CoS host outbound traffic override firwall action";
               }
               leaf cos-host-outbound-traffic-rw-dot1p {
                 type string;
                 description
                   "CoS host outbound traffic - use ieee 802.1p rewrite 
                   rules";
               }
             }
           }
           container cos-drop-congestion-notification-information {
             list cos-drop-congestion-notification-info {
               description
                 "Class-of-service drop-congestion-notification information";
               leaf cos-dcn-fc-name {
                 type string;
                 description
                   "Cos DCN forwarding class";
               }
               leaf cos-dcn-udp-port {
                 type int32;
                 description
                   "Cos DCN udp port number";
               }
             }
             container cos-drop-congestion-notification-dscp-map {
               list cos-drop-congestion-notification-dscp-map-item {
                 leaf trimmable-dscp {
                   type uint32;
                   description
                     "Trimmable DSCP code-point";
                 }
                 leaf trimmed-dscp {
                   type uint32;
                   description
                     "Trimmed DSCP code-point";
                 }
               }
             }
           }
           container cos-dedicated-buffer-profile-information {
             list dedicated-buffer-profile {
               description
                 "Class-of-service dedicated buffer profile";
               leaf dedicated-buffer-profile-name {
                 type string;
                 description
                   "Class-of-service dedicated buffer profile name";
               }
               leaf dedicated-buffer-profile-index {
                 type int32;
                 description
                   "Class-of-service dedicated buffer profile index";
               }
               leaf ingress-buffer-size {
                 type string;
                 description
                   "Ingress per port dedicated buffer in cells";
               }
               leaf egress-buffer-size {
                 type string;
                 description
                   "Egress per port dedicated buffer in cells";
               }
             }
           }
           container cos-dynamic-threshold-profile-information {
             list dynamic-threshold-profile {
               key "dynamic-threshold-profile-name";
               description
                 "Class-of-service dynamic threshold profile";
               leaf dynamic-threshold-profile-name {
                 type string;
                 description
                   "Class-of-service dynamic threshold profile name";
               }
               leaf dynamic-threshold-profile-index {
                 type uint64;
                 description
                   "Class-of-service dynamic threshold profile index";
               }
               list dynamic-threshold-profile-entry {
                 key "dynamic-threshold-profile-priority-group";
                 description
                   "Class-of-service dynamic threshold profile entry";
                 leaf dynamic-threshold-profile-priority-group {
                   type string;
                   description
                     "Class-of-service dynamic threshold profile priority 
                     group";
                 }
                 leaf dynamic-threshold-profile-threshold-value {
                   type uint32;
                   description
                     "Class-of-service dynamic threshold profile threshold 
                     value";
                 }
               }
             }
           }
           container cos-decn-profile-information {
             list decn-profile {
               description
                 "Class-of-service decn profile";
               leaf decn-profile-name {
                 type string;
                 description
                   "Class-of-service decn profile name";
               }
               leaf decn-profile-index {
                 type uint64;
                 description
                   "Class-of-service decn profile index";
               }
               list decn-profile-queue {
                 description
                   "Class-of-service decn profile queue";
                 leaf dynamic-explicit-congestion-notification-queue {
                   type uint32;
                   description
                     "Class-of-service DECN queue";
                 }
                 leaf dynamic-explicit-congestion-notification-offset {
                   type uint32;
                   description
                     "Class-of-service DECN offset";
                 }
                 leaf dynamic-explicit-congestion-notification-floor {
                   type uint32;
                   description
                     "Class-of-service DECN floor";
                 }
               }
             }
           }
           container cos-scheduler-map-information {
             list scheduler-map {
               description
                 "Class-of-service scheduler map";
               leaf scheduler-map-name {
                 type string;
                 description
                   "Class-of-service scheduler map name";
               }
               leaf scheduler-map-index {
                 type uint64;
                 description
                   "Class-of-service scheduler map index";
               }
               leaf user-plane-name {
                 type string;
                 description
                   "Class-of-service user-plane name for XDA";
               }
               list scheduler {
                 leaf scheduler-name {
                   type string;
                   description
                     "Class-of-service scheduler name";
                 }
                 leaf fc-name {
                   type string;
                   description
                     "Class-of-service forwarding class name";
                 }
                 leaf scheduler-index {
                   type uint64;
                   description
                     "Class of service scheduler index";
                 }
                 leaf scheduler-tx-rate {
                   type string;
                   description
                     "Class-of-service scheduler transmit rate";
                 }
                 leaf scheduler-tx-limit {
                   type string;
                   description
                     "Class-of-service scheduler transmit limit";
                 }
                 leaf scheduler-buffer-size {
                   type string;
                   description
                     "Class-of-service scheduler buffer size";
                 }
                 leaf scheduler-buffer-multicast-share {
                   type uint32;
                   description
                     "Class-of-service scheduler multicast buffer share";
                 }
                 leaf scheduler-buffer-limit {
                   type string;
                   description
                     "Class-of-service scheduler buffer limit";
                 }
                 leaf scheduler-buffer-rate {
                   type string;
                   description
                     "Class-of-service scheduler buffer rate";
                 }
                 leaf scheduler-shared-buffer-maximum-percentage {
                   type uint32;
                   description
                     "Shared Buffer maximum percentage";
                 }
                 leaf scheduler-shared-buffer-multicast-maximum-percentage {
                   type uint32;
                   description
                     "Shared Buffer multicast maximum percentage";
                 }
                 leaf scheduler-buffer-dynamic-threshold {
                   type uint32;
                   description
                     "Queue shared-buffer dynamic threshold";
                 }
                 leaf scheduler-priority {
                   type string;
                   description
                     "Class-of-service scheduler priority";
                 }
                 leaf scheduler-shaping-rate {
                   type string;
                   description
                     "Class-of-service scheduler shaping rate";
                 }
                 leaf scheduler-shaping-rate-burst {
                   type string;
                   description
                     "Class-of-service scheduler shaping rate burst";
                 }
                 leaf scheduler-adjust-minimum {
                   type int32;
                   description
                     "Class-of-service scheduler adjustment minimum rate";
                 }
                 leaf scheduler-adjust-percent {
                   type int32;
                   description
                     "Class-of-service scheduler percent adjustment for a 
                     queue";
                 }
                 leaf scheduler-excess-priority {
                   type string;
                   description
                     "Class-of-service scheduler excess priority";
                 }
                 leaf scheduler-excess-rate {
                   type string;
                   description
                     "Class-of-service scheduler excess rate";
                 }
                 leaf scheduler-explicit-congestion-notification {
                   type string;
                   description
                     "Class-of-service ECN status of queue";
                 }
                 leaf scheduler-ecn-rtlog-rate-limit {
                   type uint32;
                   description
                     "Class-of-service ECN Security Log Rate Limit";
                 }
                 leaf scheduler-ecn-no-pfc-assist {
                   type string;
                   description
                     "Class-of-service ECN no pfc assist";
                 }
                 leaf scheduler-latency-ecn {
                   type string;
                   description
                     "Latency based ECN";
                 }
                 leaf scheduler-latency-ecn-threshold {
                   type uint32;
                   description
                     "Latency threshold";
                 }
                 leaf scheduler-queue-monitoring {
                   type string;
                   description
                     "Class-of-service queue depth monitoring of queue";
                 }
                 leaf scheduler-drop-profile-ln-index {
                   type uint32;
                   description
                     "Class-of-service scheduler drop profile index low, 
                     non-TCP";
                 }
                 leaf scheduler-drop-profile-ln {
                   type string;
                   description
                     "Class-of-service scheduler drop profile low, non-TCP";
                 }
                 leaf scheduler-drop-profile-lt-index {
                   type uint32;
                   description
                     "Class-of-service scheduler drop profile index low, TCP";
                 }
                 leaf scheduler-drop-profile-lt {
                   type string;
                   description
                     "Class-of-service scheduler drop profile low, TCP";
                 }
                 leaf scheduler-drop-profile-hn-index {
                   type uint32;
                   description
                     "Class-of-service scheduler drop profile index high, 
                     non-TCP";
                 }
                 leaf scheduler-drop-profile-hn {
                   type string;
                   description
                     "Class-of-service scheduler drop profile high, non-TCP";
                 }
                 leaf scheduler-drop-profile-ht-index {
                   type uint32;
                   description
                     "Class-of-service scheduler drop profile index high, 
                     TCP";
                 }
                 leaf scheduler-drop-profile-ht {
                   type string;
                   description
                     "Class-of-service scheduler drop profile high, TCP";
                 }
                 leaf scheduler-drop-profile-la-index {
                   type uint32;
                   description
                     "Class-of-service scheduler drop profile index low";
                 }
                 leaf scheduler-drop-profile-la {
                   type string;
                   description
                     "Class-of-service scheduler drop profile low";
                 }
                 leaf scheduler-drop-profile-ma-index {
                   type uint32;
                   description
                     "Class-of-service scheduler drop profile index medium";
                 }
                 leaf scheduler-drop-profile-ma {
                   type string;
                   description
                     "Class-of-service scheduler drop profile medium";
                 }
                 leaf scheduler-drop-profile-mla-index {
                   type uint32;
                   description
                     "Class-of-service scheduler drop profile index 
                     medium-low";
                 }
                 leaf scheduler-drop-profile-mla {
                   type string;
                   description
                     "Class-of-service scheduler drop profile medium-low";
                 }
                 leaf scheduler-drop-profile-mha-index {
                   type uint32;
                   description
                     "Class-of-service scheduler drop profile index 
                     medium-high";
                 }
                 leaf scheduler-drop-profile-mha {
                   type string;
                   description
                     "Class-of-service scheduler drop profile medium-high";
                 }
                 leaf scheduler-drop-profile-ha-index {
                   type uint32;
                   description
                     "Class-of-service scheduler drop profile index high";
                 }
                 leaf scheduler-drop-profile-ha {
                   type string;
                   description
                     "Class-of-service scheduler drop profile high";
                 }
               }
             }
           }
           container cos-traffic-control-profile-information {
             list traffic-control-profile {
               description
                 "Information about one or more traffic control profiles";
               leaf traffic-control-profile-name {
                 type string;
                 description
                   "Class-of-service traffic control profile name";
               }
               leaf traffic-control-profile-index {
                 type uint64;
                 description
                   "Index number for Class-of-service traffic control 
                   profile";
               }
               leaf user-plane-name {
                 type string;
                 description
                   "Class-of-service user-plane name for XDA";
               }
               leaf scheduler-map-name {
                 type string;
                 description
                   "Class-of-service scheduler map name";
               }
               leaf atm-service {
                 type string;
                 description
                   "Class-of-service traffic control profile atm service";
               }
               leaf shaping-rate {
                 type uint64;
                 description
                   "Class-of-service shaping rate";
               }
               leaf shaping-rate-burst {
                 type uint32;
                 description
                   "Class-of-service shaping rate burst, in bytes";
               }
               leaf low-granularity {
                 type uint32;
                 description
                   "Class-of-service low-granularity mode support";
               }
               leaf queue-mode-4q {
                 type uint32;
                 description
                   "Class-of-service tcp-voq-mode(4Q) mode support";
               }
               leaf shaping-rate-priority-strict-high {
                 type uint64;
                 description
                   "Class-of-service shaping rate for priority strict high";
               }
               leaf shaping-rate-priority-strict-high-burst {
                 type uint32;
                 description
                   "Class-of-service shaping rate burst for priority 
                   strict-high";
               }
               leaf shaping-rate-priority-high {
                 type uint64;
                 description
                   "Class-of-service shaping rate for priority high";
               }
               leaf shaping-rate-priority-high-burst {
                 type uint32;
                 description
                   "Class-of-service shaping rate for priority high burst";
               }
               leaf shaping-rate-priority-medium {
                 type uint64;
                 description
                   "Class-of-service shaping rate for priority medium";
               }
               leaf shaping-rate-priority-medium-burst {
                 type uint32;
                 description
                   "Class-of-service shaping rate for priority medium burst";
               }
               leaf shaping-rate-priority-medium-low {
                 type uint64;
                 description
                   "Class-of-service shaping rate for priority medium-low";
               }
               leaf shaping-rate-priority-medium-low-burst {
                 type uint32;
                 description
                   "Class-of-service shaping rate burst for priority 
                   medium-low";
               }
               leaf shaping-rate-priority-low {
                 type uint64;
                 description
                   "Class-of-service shaping rate for priority low";
               }
               leaf shaping-rate-priority-low-burst {
                 type uint32;
                 description
                   "Class-of-service shaping rate for priority low burst";
               }
               leaf shaping-rate-excess-high {
                 type uint64;
                 description
                   "Class-of-service shaping rate for excess high";
               }
               leaf shaping-rate-excess-high-burst {
                 type uint32;
                 description
                   "Class-of-service shaping rate for excess high burst";
               }
               leaf shaping-rate-excess-medium-high {
                 type uint64;
                 description
                   "Class-of-service shaping rate for excess medium-high";
               }
               leaf shaping-rate-excess-medium-high-burst {
                 type uint32;
                 description
                   "Class-of-service shaping rate burst for excess 
                   medium-high";
               }
               leaf shaping-rate-excess-medium-low {
                 type uint64;
                 description
                   "Class-of-service shaping rate for excess medium-low";
               }
               leaf shaping-rate-excess-medium-low-burst {
                 type uint32;
                 description
                   "Class-of-service shaping rate burst for excess 
                   medium-low";
               }
               leaf shaping-rate-excess-low {
                 type uint64;
                 description
                   "Class-of-service shaping rate for excess low";
               }
               leaf shaping-rate-excess-low-burst {
                 type uint32;
                 description
                   "Class-of-service shaping rate for excess low burst";
               }
               leaf guaranteed-rate {
                 type uint64;
                 description
                   "Class-of-service guaranteed rate";
               }
               leaf guaranteed-rate-burst {
                 type uint32;
                 description
                   "Class-of-service guaranteed rate burst, in bytes";
               }
               leaf delay-buffer-rate {
                 type uint64;
                 description
                   "Class-of-service delay buffer rate";
               }
               leaf excess-rate {
                 type uint32;
                 description
                   "Class-of-service excess rate";
               }
               leaf excess-rate-high {
                 type uint32;
                 description
                   "Class-of-service excess rate for excess-high priority 
                   traffic";
               }
               leaf excess-rate-medium-high {
                 type uint32;
                 description
                   "Class-of-service excess rate for excess-medium-high 
                   priority traffic";
               }
               leaf excess-rate-medium-low {
                 type uint32;
                 description
                   "Class-of-service excess rate for excess-medium-low 
                   priority traffic";
               }
               leaf excess-rate-low {
                 type uint32;
                 description
                   "Class-of-service excess rate for excess-low priority 
                   traffic";
               }
               leaf adjust-minimum {
                 type uint64;
                 description
                   "Class-of-service adjustment minimum rate";
               }
               leaf overhead-bytes {
                 type int32;
                 description
                   "Class-of-service Overhead bytes";
               }
               leaf frame-mode-bytes {
                 type int32;
                 description
                   "Class-of-service overhead bytes when in frame-mode";
               }
               leaf cell-mode-bytes {
                 type int32;
                 description
                   "Class-of-service overhead bytes when in cell-mode";
               }
               leaf overhead-accounting-mode {
                 type string;
                 description
                   "Class-of-service Overhead Accounting Mode";
               }
               list traffic-control-profile-instance {
                 description
                   "Class-of-service traffic control profile instance";
                 leaf traffic-control-profile-instance-name {
                   type string;
                   description
                     "Class-of-service traffic control profile instance";
                 }
                 leaf traffic-control-profile-instance-index {
                   type uint32;
                   description
                     "Index number for Class-of-service traffic control 
                     profile instance";
                 }
                 leaf instance-reference-count {
                   type uint32;
                   description
                     "Instance reference count";
                 }
               }
             }
           }
           container cos-routing-instance-information {
             list routing-instance-map {
               description
                 "Mapping between class-of-service objects and routing 
                 instances";
               leaf routing-instance-name {
                 type string;
                 description
                   "Name of class-of-service routing instance";
               }
               list i-logical-map {
                 leaf i-logical-name {
                   type string;
                   description
                     "Class-of-service logical interface name";
                 }
                 leaf i-logical-index {
                   type uint32;
                   description
                     "Class-of-service logical interface index";
                 }
                 leaf monitoring-profile-map-name {
                   type string;
                   description
                     "Monitoring Profile Name";
                 }
                 list cos-objects {
                   description
                     "Class-of-service object  mappings";
                   leaf cos-object-type {
                     type string;
                     description
                       "Class-of-service object type";
                   }
                   leaf cos-object-name {
                     type string;
                     description
                       "Class-of-service object name";
                   }
                   leaf cos-object-subtype {
                     type string;
                     description
                       "Class-of-service object subtype";
                   }
                   leaf cos-object-index {
                     type uint64;
                     description
                       "Class-of-service object index";
                   }
                 }
               }
             }
           }
           container cos-fabric-scheduler-map-information {
             container fabric-scheduler-map {
               list fabric-scheduler {
                 leaf fabric-scheduler-name {
                   type string;
                   description
                     "Class-of-service scheduler name";
                 }
                 leaf fabric-scheduler-index {
                   type uint32;
                   description
                     "Class of service scheduler index";
                 }
                 leaf fabric-scheduler-drop-profile-ln-index {
                   type uint32;
                   description
                     "Class-of-service scheduler drop profile index low, 
                     non-TCP";
                 }
                 leaf fabric-scheduler-drop-profile-ln {
                   type string;
                   description
                     "Class-of-service scheduler drop profile low, non-TCP";
                 }
                 leaf fabric-scheduler-drop-profile-lt-index {
                   type uint32;
                   description
                     "Class-of-service scheduler drop profile index low, TCP";
                 }
                 leaf fabric-scheduler-drop-profile-lt {
                   type string;
                   description
                     "Class-of-service scheduler drop profile low, TCP";
                 }
                 leaf fabric-scheduler-drop-profile-hn-index {
                   type uint32;
                   description
                     "Class-of-service scheduler drop profile index high, 
                     non-TCP";
                 }
                 leaf fabric-scheduler-drop-profile-hn {
                   type string;
                   description
                     "Class-of-service scheduler drop profile high, non-TCP";
                 }
                 leaf fabric-scheduler-drop-profile-ht-index {
                   type uint32;
                   description
                     "Class-of-service scheduler drop profile index high, 
                     TCP";
                 }
                 leaf fabric-scheduler-drop-profile-ht {
                   type string;
                   description
                     "Class-of-service scheduler drop profile high, TCP";
                 }
                 leaf fabric-scheduler-priority {
                   type string;
                 }
               }
             }
           }
           container cos-tcm-information {
             list tcm {
               description
                 "Class-of-service traffic-class-map";
               leaf tcm-name {
                 type string;
                 description
                   "Class-of-service traffic-class-map name";
               }
               leaf tcm-type {
                 type string;
                 description
                   "Class-of-service traffic-class-map type";
               }
               leaf table-index {
                 type uint32;
                 description
                   "Table index";
               }
               container tcm-map {
                 list tcm-map-item {
                   leaf code-point {
                     type string;
                     description
                       "Class-of-service code point alias name or bits";
                   }
                   leaf tc-name {
                     type string;
                     description
                       "Class-of-service traffic-class-map traffic-class 
                       name";
                   }
                 }
               }
             }
           }
           container cos-lecn-profile-information {
             list lecn-profile {
               description
                 "Class-of-service lecn profile";
               leaf lecn-profile-name {
                 type string;
                 description
                   "Class-of-service lecn profile name";
               }
               leaf lecn-profile-index {
                 type uint64;
                 description
                   "Class-of-service lecn profile index";
               }
               list lecn-profile-queue {
                 description
                   "Class-of-service lecn profile queue";
                 leaf latency-explicit-congestion-notification-queue {
                   type uint32;
                   description
                     "Class-of-service LECN queue";
                 }
                 leaf latency-explicit-congestion-notification-latency {
                   type uint32;
                   description
                     "Class-of-service LECN latency";
                 }
               }
             }
           }
         }
         container physical-interface-cos-information {
           description
             "Physical interface class-of-service parameters";
         }
         container precl-statistics {
           description
             "Preclassifier Statistics ";
           container precl-information {
             description
               "Preclassifier Statistics";
           }
         }
         container mlfr-uni-nni-traffic-statistics {
           container bundle {
           }
         }
       }
       list logical-interface {
         key "name";
         description
           "Information about a single logical interface";
         leaf name {
           type string;
           description
             "Name of this item";
         }
         leaf admin-status {
           type string;
           description
             "Desired state of the interface";
         }
         leaf oper-status {
           type string;
           description
             "Current operational state of the interface";
         }
         leaf vrfname {
           type string;
           description
             "Routing instance name";
         }
         leaf zonename {
           type string;
           description
             "Zone name";
         }
         leaf subunit {
           type int32;
           description
             "Subunit for this interface";
         }
         leaf dialer-time-to-disconnect {
           type string;
           description
             "Time for dialer to disconnect due to idle timeout";
         }
         leaf lcp-state {
           type string;
           description
             "State of the Line Control Protocol";
         }
         leaf chap-state {
           type string;
           description
             "State of the Challenge Handshake Authentication Protocol";
         }
         leaf pap-state {
           type string;
           description
             "State of the Password Authentication Protocol";
         }
         container layer2-input-policer-information {
           description
             "Information about Layer 2 input policer for interface";
           leaf layer2-input-policer {
             type string;
             description
               "Name of the Layer 2 input policer";
           }
         }
         container layer2-output-policer-information {
           description
             "Information about Layer 2 output policer for interface";
           leaf layer2-output-policer {
             type string;
             description
               "Name of the Layer 2 output policer";
           }
         }
         container pppoe-information {
           description
             "PPPoE information";
           list pppoe-interface {
             leaf state {
               type string;
               description
                 "State";
             }
             leaf session-id {
               type string;
               description
                 "Session ID";
             }
             leaf ac-name-session {
               type string;
               description
                 "Session AC name";
             }
             leaf remote-mac {
               type string;
               description
                 "Remote MAC address";
             }
             leaf ac-name-config {
               type string;
               description
                 "Configured AC name";
             }
             leaf service-name {
               type string;
               description
                 "Service name";
             }
             leaf auto-reconnect {
               type string;
               description
                 "Autoreconnect timeout";
             }
             leaf idle-timeout {
               type string;
               description
                 "Idle timeout";
             }
             leaf underlying-interface-name {
               type string;
               description
                 "Underlying interface name";
             }
             leaf underlying-interface-index {
               type string;
               description
                 "Underlying interface index";
             }
             leaf padg-credits {
               type int32;
               description
                 "PADG transmit credits";
             }
             leaf pppoe-credit-scale-factor {
               type string;
               description
                 "Scaling factor";
             }
             leaf ignore-eol-tag {
               type string;
               description
                 "Ignore End-of-List TAG";
             }
             leaf ppp-max-payload-tag {
               type int32;
               description
                 "PPP-Max-Payload TAG";
             }
             leaf interface-name {
               type string;
               description
                 "Class-of-service interface name";
             }
             leaf interface-index {
               type uint32;
               description
                 "Class-of-service interface index";
             }
             leaf aci-iflset-name {
               type string;
               description
                 "ACI Interface Set name";
             }
             leaf aci-iflset-index {
               type string;
               description
                 "ACI Interface Set index";
             }
             leaf ifl-type {
               type string;
               description
                 "Type";
             }
             leaf session-uptime {
               type string;
               description
                 "Duration for which the session has been up";
             }
             leaf dynamic-profile {
               type string;
               description
                 "Dynamic Profile name";
             }
             leaf pppoe-credits {
               type string;
               description
                 "Forwarding credit balances";
             }
             leaf dynamic-interface-bandwidth {
               type string;
               description
                 "Dynamic interface bandwidth";
             }
             leaf agent-circuit-id {
               type string;
               description
                 "Agent Circuit ID";
             }
             leaf agent-remote-id {
               type string;
               description
                 "Agent Remote ID";
             }
             leaf padm-motm {
               type string;
               description
                 "PADM Message of the Moment tag";
             }
             leaf padm-hurl {
               type string;
               description
                 "PADM HTTP URL tag";
             }
           }
         }
         container pppoe-underlying-information {
           description
             "PPPoE Underlying information";
           list pppoe-underlying-interface {
             leaf dynamic-profile {
               type string;
               description
                 "Dynamic Profile name";
             }
             leaf service-name-table {
               type string;
               description
                 "Name of Service Name Table";
             }
             leaf max-sessions {
               type int32;
               description
                 "Maximum number of PPPoE sessions";
             }
             leaf max-sessions-vsa-ignore {
               type string;
               description
                 "Ignore max-sessions VSA";
             }
             leaf duplicate-protection {
               type string;
               description
                 "Duplicate protection mode";
             }
             leaf short-cycle-protection {
               type string;
               description
                 "Short cycle protection mode";
             }
             leaf direct-connect {
               type string;
               description
                 "Direct connect mode";
             }
             leaf ac-name {
               type string;
               description
                 "Access Concentrator name";
             }
             leaf underlying-interface-name {
               type string;
               description
                 "Underlying interface name";
             }
             leaf underlying-interface-index {
               type string;
               description
                 "Underlying interface index";
             }
             leaf encapsulation-type-identifier {
               type string;
               description
                 "Encapsulation type identifier";
             }
             leaf state {
               type string;
               description
                 "State";
             }
             leaf active-sessions {
               type int32;
               description
                 "Number of active PPPoE sessions";
             }
             leaf aci-autosensing {
               type string;
               description
                 "ACI VLAN Autosensing mode";
             }
             leaf line-identity-autosensing {
               type string;
               description
                 "Line Identity Autosensing mode";
             }
           }
         }
         container aci-vlan-information {
           leaf dynamic-profile {
             type string;
             description
               "Dynamic Profile name";
           }
         }
         container line-identity-information {
           leaf dynamic-profile {
             type string;
             description
               "Dynamic Profile name";
           }
           leaf circuit-id {
             type string;
             description
               "Aci vlan attribute";
           }
           leaf remote-id {
             type string;
             description
               "Aci vlan attribute";
           }
           leaf accept-no-ids {
             type string;
             description
               "Aci vlan attribute";
           }
         }
         container demux-information {
           description
             "Demux information";
           container demux-interface {
             leaf demux-underlying-interface-name {
               type string;
               description
                 "Underlying interface name";
             }
             leaf demux-underlying-interface-index {
               type string;
               description
                 "Underlying interface index";
             }
             leaf demux-inet-prefix-type {
               type string;
               description
                 "Prefix type";
             }
             leaf demux-inet-prefix-count {
               type string;
               description
                 "IPv4 Prefix count";
             }
             leaf demux-inet-prefix {
               type string;
               description
                 "IPv4 Prefix";
             }
             leaf demux-inet6-prefix-type {
               type string;
               description
                 "Prefix type";
             }
             leaf demux-inet6-prefix-count {
               type string;
               description
                 "IPv6 Prefix count";
             }
             leaf demux-inet6-prefix {
               type string;
               description
                 "IPv6 Prefix";
             }
           }
         }
         container dual-ad-icl-color-information {
           container dual-ad-icl-color-info {
             description
               "Dual-AD ICL Color Information";
             leaf dual-ad-icl-color-type {
               type uint32;
               description
                 "Dual-AD ICL Color Type";
             }
             leaf dual-ad-icl-color {
               type uint32;
               description
                 "Dual-AD ICL Color";
             }
           }
         }
         container dialer-information {
           description
             "Dialer information";
           leaf dialer-time-to-disconnect {
             type string;
             description
               "Time for dialer to disconnect due to idle timeout";
           }
           container dialer-interface {
             leaf dialer-interface-name {
               type string;
               description
                 "Interface name";
             }
             leaf dialer-interface-state {
               type string;
               description
                 "Dialer interface state";
             }
             leaf pool-id {
               type string;
               description
                 "Pool identifier";
             }
             leaf primary-interface {
               type string;
               description
                 "Primary interface";
             }
             leaf activation-delay {
               type string;
               description
                 "Activation delay";
             }
             leaf deactivation-delay {
               type string;
               description
                 "Deactivation delay";
             }
             leaf activation-delay-elapsed {
               type string;
               description
                 "Activation delay elapsed";
             }
             leaf deactivation-delay-elapsed {
               type string;
               description
                 "Deactivation delay elapsed";
             }
             leaf call-idle-timeout {
               type string;
               description
                 "Call idle timeout";
             }
             leaf initial-route-check {
               type string;
               description
                 "Initial route check delay";
             }
             leaf redial-delay {
               type string;
               description
                 "Delay before dialer dials out again (seconds)";
             }
             leaf callback-wait-period {
               type string;
               description
                 "Delay before dialer attempts callback (seconds)";
             }
             leaf callback-wait-period-elapsed {
               type string;
               description
                 "Number of seconds in callback wait period that have 
                 elapsed";
             }
             leaf load-threshold {
               type string;
               description
                 "Load threshold that determines when interfaces are added 
                 to bundle";
             }
             leaf load-interval {
               type string;
               description
                 "Interval over which average load is calculated";
             }
             container dialer-interface-flags {
               description
                 "Flags indicating interface configuration";
               leaf backup {
                 type empty;
                 description
                   "Dialer backup";
               }
               leaf multilink {
                 type empty;
                 description
                   "Dialer multilink";
               }
               leaf watchlist {
                 type empty;
                 description
                   "Dialer watchlist";
               }
               leaf interesting-detected {
                 type empty;
                 description
                   "Interesting packet detected";
               }
             }
           }
         }
         container shared-interface-information {
           description
             "Shared interface information";
           container shared-interface-logical-interface {
             description
               "Shared interface logical interface";
             leaf peer-interface-name {
               type string;
               description
                 "Peer interface name";
             }
             leaf interface-shared-with {
               type string;
               description
                 "Logical interface owner";
             }
             leaf rx-fe {
               type string;
               description
                 "Rx tunnel token forwarding element";
             }
             leaf rx-nhid {
               type string;
               description
                 "Rx tunnel token next hop index";
             }
             leaf tx-fe {
               type string;
               description
                 "Tx tunnel token forwarding element";
             }
             leaf tx-nhid {
               type string;
               description
                 "Tx tunnel token next hop index";
             }
           }
         }
         container mac-database {
         }
         container queue-counters {
           description
             "Queue counter statistics";
           leaf queue-counters-error-message {
             type string;
             description
               "Queue statistics not available for this interface";
           }
           list queue {
             description
               "Counters for a single queue";
             leaf queue-number {
               type int32;
               description
                 "Queue number";
             }
             leaf queue-counters-queued-packets {
               type uint64;
               description
                 "Queued packet count";
             }
             leaf queue-counters-trans-packets {
               type uint64;
               description
                 "Total number of transmitted packets";
             }
             leaf queue-counters-total-drop-packets {
               type uint64;
               description
                 "Number of total packets dropped at the queue";
             }
             leaf forwarding-class-name {
               type string;
               description
                 "Forwarding class name associated with queue";
             }
             leaf queue-counters-queued-packets-rate {
               type uint64;
               description
                 "Rate at which packets are queued";
             }
             leaf queue-counters-queued-bytes {
               type uint64;
               description
                 "Queued bytes count";
             }
             leaf queue-counters-queued-bytes-rate {
               type uint64;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets-rate {
               type uint64;
               description
                 "Rate at which packets are transmitted";
             }
             leaf queue-counters-trans-bytes {
               type uint64;
               description
                 "Total number of transmitted bytes";
             }
             leaf queue-counters-trans-bytes-rate {
               type uint64;
               description
                 "Rate at which bytes are transmitted";
             }
             leaf queue-counters-tail-drop-packets-na {
               type string;
               description
                 "Number of packets dropped due to tail drop not available";
             }
             leaf queue-counters-tail-drop-packets {
               type uint64;
               description
                 "Number of packets dropped at the tail of the queue";
             }
             leaf queue-counters-tail-drop-packets-rate {
               type uint64;
               description
                 "Rate at which packets are dropped at tail of queue";
             }
             leaf queue-counters-tail-drop-bytes {
               type uint64;
               description
                 "Number of packets dropped at tail drop of the queue";
             }
             leaf queue-counters-tail-drop-bytes-rate {
               type uint64;
               description
                 "Number of packets dropped at tail drop of the queue";
             }
             leaf queue-counters-rate-limit-drop-packets-na {
               type string;
               description
                 "Number of packets dropped due to rate-limit drop not 
                 available";
             }
             leaf queue-counters-rate-limit-drop-packets {
               type uint64;
               description
                 "Number of packets dropped by rate-limit for the queue";
             }
             leaf queue-counters-rate-limit-drop-packets-rate {
               type uint64;
               description
                 "Rate at which packets are dropped by rate-limit for the 
                 queue";
             }
             leaf queue-counters-rate-limit-drop-bytes-na {
               type string;
               description
                 "Number of bytes dropped due to tail drop not available";
             }
             leaf queue-counters-rate-limit-drop-bytes {
               type uint64;
               description
                 "Number of bytes dropped at the tail of the queue";
             }
             leaf queue-counters-rate-limit-drop-bytes-rate {
               type uint64;
               description
                 "Rate at which bytes are dropped at the tail of the queue";
             }
             leaf queue-counters-red-packets-na {
               type string;
               description
                 "Number of packets dropped due to RED not available";
             }
             leaf queue-counters-red-packets {
               type uint64;
               description
                 "Number of packets dropped due to RED";
             }
             leaf queue-counters-red-packets-rate {
               type uint64;
               description
                 "Rate at which packets are dropped due to RED";
             }
             leaf queue-counters-red-packets-ln {
               type uint64;
               description
                 "Number of RED dropped low-loss, non-TCP packets";
             }
             leaf queue-counters-red-packets-rate-ln {
               type uint64;
               description
                 "RED drop rate for low-loss, non-TCP packets";
             }
             leaf queue-counters-red-packets-lt {
               type uint64;
               description
                 "Number of RED dropped of low-loss, TCP packets";
             }
             leaf queue-counters-red-packets-rate-lt {
               type uint64;
               description
                 "RED drop rate for low-loss, TCP packets";
             }
             leaf queue-counters-red-packets-hn {
               type uint64;
               description
                 "Number of RED dropped high-loss, non-TCP packets";
             }
             leaf queue-counters-red-packets-rate-hn {
               type uint64;
               description
                 "RED drop rate for high-loss, non-TCP packets";
             }
             leaf queue-counters-red-packets-ht {
               type uint64;
               description
                 "Number of RED dropped high-loss, TCP packets";
             }
             leaf queue-counters-red-packets-rate-ht {
               type uint64;
               description
                 "RED drop rate for high-loss, TCP packets";
             }
             leaf queue-counters-red-packets-low {
               type uint64;
               description
                 "Number of RED dropped low-loss packets";
             }
             leaf queue-counters-red-packets-rate-low {
               type uint64;
               description
                 "RED drop rate for low-loss packets";
             }
             leaf queue-counters-red-packets-medium-low {
               type uint64;
               description
                 "Number of RED dropped medium-low-loss packets";
             }
             leaf queue-counters-red-packets-rate-medium-low {
               type uint64;
               description
                 "RED drop rate for medium-low-loss packets";
             }
             leaf queue-counters-red-packets-medium-high {
               type uint64;
               description
                 "Number of RED dropped medium-high-loss packets";
             }
             leaf queue-counters-red-packets-rate-medium-high {
               type uint64;
               description
                 "RED drop rate for medium-high-loss packets";
             }
             leaf queue-counters-red-packets-medium {
               type uint64;
               description
                 "Number of RED dropped medium-loss packets";
             }
             leaf queue-counters-red-packets-rate-medium {
               type uint64;
               description
                 "RED drop rate for medium-loss packets";
             }
             leaf queue-counters-red-packets-high {
               type uint64;
               description
                 "Number of RED dropped high-loss packets";
             }
             leaf queue-counters-red-packets-rate-high {
               type uint64;
               description
                 "RED drop rate for high-loss packets";
             }
             leaf queue-counters-red-bytes-na {
               type string;
               description
                 "Number of bytes dropped due to RED not available";
             }
             leaf queue-counters-red-bytes {
               type uint64;
               description
                 "Number of bytes dropped due to RED";
             }
             leaf queue-counters-red-bytes-rate {
               type uint64;
               description
                 "Rate at which bytes are dropped due to RED";
             }
             leaf queue-counters-red-bytes-ln {
               type uint64;
               description
                 "Number of RED dropped low-loss, non-TCP bytes";
             }
             leaf queue-counters-red-bytes-rate-ln {
               type uint64;
               description
                 "RED drop rate for low-loss, non-TCP bytes";
             }
             leaf queue-counters-red-bytes-lt {
               type uint64;
               description
                 "Number of RED dropped low-loss, TCP bytes";
             }
             leaf queue-counters-red-bytes-rate-lt {
               type uint64;
               description
                 "RED drop rate for low-loss, TCP bytes";
             }
             leaf queue-counters-red-bytes-hn {
               type uint64;
               description
                 "Number of RED dropped high-loss, non-TCP bytes";
             }
             leaf queue-counters-red-bytes-rate-hn {
               type uint64;
               description
                 "RED drop rate for high-loss, non-TCP bytes";
             }
             leaf queue-counters-red-bytes-ht {
               type uint64;
               description
                 "Number of RED dropped high-loss, TCP bytes";
             }
             leaf queue-counters-red-bytes-rate-ht {
               type uint64;
               description
                 "RED drop rate for high-loss, TCP bytes";
             }
             leaf queue-counters-red-bytes-low {
               type uint64;
               description
                 "Number of RED dropped low-loss bytes";
             }
             leaf queue-counters-red-bytes-rate-low {
               type uint64;
               description
                 "RED drop rate for low-loss bytes";
             }
             leaf queue-counters-red-bytes-medium-low {
               type uint64;
               description
                 "Number of RED dropped medium-low-loss bytes";
             }
             leaf queue-counters-red-bytes-rate-medium-low {
               type uint64;
               description
                 "RED drop rate for medium-low-loss bytes";
             }
             leaf queue-counters-red-bytes-medium-high {
               type uint64;
               description
                 "Number of RED dropped medium-high-loss bytes";
             }
             leaf queue-counters-red-bytes-rate-medium-high {
               type uint64;
               description
                 "RED drop rate for medium-high-loss bytes";
             }
             leaf queue-counters-red-bytes-medium {
               type uint64;
               description
                 "Number of RED dropped medium-loss bytes";
             }
             leaf queue-counters-red-bytes-rate-medium {
               type uint64;
               description
                 "RED drop rate for medium-loss bytes";
             }
             leaf queue-counters-red-bytes-high {
               type uint64;
               description
                 "Number of RED dropped high-loss bytes";
             }
             leaf queue-counters-red-bytes-rate-high {
               type uint64;
               description
                 "RED drop rate for high-loss bytes";
             }
             leaf queue-counters-timestamp {
               type uint64;
               description
                 "Last packet enqueued timestamp";
             }
             leaf queue-counters-total-drop-packets-rate {
               type uint64;
               description
                 "Number of total packets dropped at the queue";
             }
             leaf queue-counters-total-drop-bytes {
               type uint64;
               description
                 "Number of total packets dropped at the queue";
             }
             leaf queue-counters-total-drop-bytes-rate {
               type uint64;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-short-summary {
             description
               "Summary of queue information on an interface";
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
         }
         container ingress-queue-counters {
           description
             "Ingress queue counter statistics";
           list queue {
             description
               "Counters for a single queue";
             leaf queue-number {
               type int32;
               description
                 "Queue number";
             }
             leaf forwarding-class-name {
               type string;
               description
                 "Forwarding class name associated with queue";
             }
             leaf queue-counters-queued-packets {
               type uint64;
               description
                 "Queued packet count";
             }
             leaf queue-counters-queued-packets-rate {
               type uint64;
               description
                 "Rate at which packets are queued";
             }
             leaf queue-counters-queued-bytes {
               type uint64;
               description
                 "Queued bytes count";
             }
             leaf queue-counters-queued-bytes-rate {
               type uint64;
               description
                 "Rate at which bytes are queued";
             }
             leaf queue-counters-queued-packets-na {
               type string;
               description
                 "Queued packets not available";
             }
             leaf queue-counters-queued-bytes-na {
               type string;
               description
                 "Queued bytes not available";
             }
             leaf queue-counters-trans-packets {
               type uint64;
               description
                 "Total number of transmitted packets";
             }
             leaf queue-counters-trans-packets-rate {
               type uint64;
               description
                 "Rate at which packets are transmitted";
             }
             leaf queue-counters-trans-bytes {
               type uint64;
               description
                 "Total number of transmitted bytes";
             }
             leaf queue-counters-trans-bytes-rate {
               type uint64;
               description
                 "Rate at which bytes are transmitted";
             }
             leaf queue-counters-tail-drop-packets-na {
               type string;
               description
                 "Number of packets dropped due to tail drop not available";
             }
             leaf queue-counters-tail-drop-packets {
               type uint64;
               description
                 "Number of packets dropped at the tail of the queue";
             }
             leaf queue-counters-tail-drop-packets-rate {
               type uint64;
               description
                 "Rate at which packets are dropped at tail of queue";
             }
             leaf queue-counters-tail-drop-bytes {
               type uint64;
               description
                 "Number of packets dropped at tail drop of the queue";
             }
             leaf queue-counters-tail-drop-bytes-rate {
               type uint64;
               description
                 "Number of packets dropped at tail drop of the queue";
             }
             leaf queue-counters-rate-limit-drop-packets-na {
               type string;
               description
                 "Number of packets dropped due to rate-limit drop not 
                 available";
             }
             leaf queue-counters-rate-limit-drop-packets {
               type uint64;
               description
                 "Number of packets dropped by rate-limit for the queue";
             }
             leaf queue-counters-rate-limit-drop-packets-rate {
               type uint64;
               description
                 "Rate at which packets are dropped by rate-limit for the 
                 queue";
             }
             leaf queue-counters-rate-limit-drop-bytes-na {
               type string;
               description
                 "Number of bytes dropped due to tail drop not available";
             }
             leaf queue-counters-rate-limit-drop-bytes {
               type uint64;
               description
                 "Number of bytes dropped at the tail of the queue";
             }
             leaf queue-counters-rate-limit-drop-bytes-rate {
               type uint64;
               description
                 "Rate at which bytes are dropped at the tail of the queue";
             }
             leaf queue-counters-red-packets-na {
               type string;
               description
                 "Number of packets dropped due to RED not available";
             }
             leaf queue-counters-red-packets {
               type uint64;
               description
                 "Number of packets dropped due to RED";
             }
             leaf queue-counters-red-packets-rate {
               type uint64;
               description
                 "Rate at which packets are dropped due to RED";
             }
             leaf queue-counters-red-packets-ln {
               type uint64;
               description
                 "Number of RED dropped low-loss, non-TCP packets";
             }
             leaf queue-counters-red-packets-rate-ln {
               type uint64;
               description
                 "RED drop rate for low-loss, non-TCP packets";
             }
             leaf queue-counters-red-packets-lt {
               type uint64;
               description
                 "Number of RED dropped of low-loss, TCP packets";
             }
             leaf queue-counters-red-packets-rate-lt {
               type uint64;
               description
                 "RED drop rate for low-loss, TCP packets";
             }
             leaf queue-counters-red-packets-hn {
               type uint64;
               description
                 "Number of RED dropped high-loss, non-TCP packets";
             }
             leaf queue-counters-red-packets-rate-hn {
               type uint64;
               description
                 "RED drop rate for high-loss, non-TCP packets";
             }
             leaf queue-counters-red-packets-ht {
               type uint64;
               description
                 "Number of RED dropped high-loss, TCP packets";
             }
             leaf queue-counters-red-packets-rate-ht {
               type uint64;
               description
                 "RED drop rate for high-loss, TCP packets";
             }
             leaf queue-counters-red-packets-low {
               type uint64;
               description
                 "Number of RED dropped low-loss packets";
             }
             leaf queue-counters-red-packets-rate-low {
               type uint64;
               description
                 "RED drop rate for low-loss packets";
             }
             leaf queue-counters-red-packets-medium-low {
               type uint64;
               description
                 "Number of RED dropped medium-low-loss packets";
             }
             leaf queue-counters-red-packets-rate-medium-low {
               type uint64;
               description
                 "RED drop rate for medium-low-loss packets";
             }
             leaf queue-counters-red-packets-medium-high {
               type uint64;
               description
                 "Number of RED dropped medium-high-loss packets";
             }
             leaf queue-counters-red-packets-rate-medium-high {
               type uint64;
               description
                 "RED drop rate for medium-high-loss packets";
             }
             leaf queue-counters-red-packets-medium {
               type uint64;
               description
                 "Number of RED dropped medium-loss packets";
             }
             leaf queue-counters-red-packets-rate-medium {
               type uint64;
               description
                 "RED drop rate for medium-loss packets";
             }
             leaf queue-counters-red-packets-high {
               type uint64;
               description
                 "Number of RED dropped high-loss packets";
             }
             leaf queue-counters-red-packets-rate-high {
               type uint64;
               description
                 "RED drop rate for high-loss packets";
             }
             leaf queue-counters-red-bytes-na {
               type string;
               description
                 "Number of bytes dropped due to RED not available";
             }
             leaf queue-counters-red-bytes {
               type uint64;
               description
                 "Number of bytes dropped due to RED";
             }
             leaf queue-counters-red-bytes-rate {
               type uint64;
               description
                 "Rate at which bytes are dropped due to RED";
             }
             leaf queue-counters-red-bytes-ln {
               type uint64;
               description
                 "Number of RED dropped low-loss, non-TCP bytes";
             }
             leaf queue-counters-red-bytes-rate-ln {
               type uint64;
               description
                 "RED drop rate for low-loss, non-TCP bytes";
             }
             leaf queue-counters-red-bytes-lt {
               type uint64;
               description
                 "Number of RED dropped low-loss, TCP bytes";
             }
             leaf queue-counters-red-bytes-rate-lt {
               type uint64;
               description
                 "RED drop rate for low-loss, TCP bytes";
             }
             leaf queue-counters-red-bytes-hn {
               type uint64;
               description
                 "Number of RED dropped high-loss, non-TCP bytes";
             }
             leaf queue-counters-red-bytes-rate-hn {
               type uint64;
               description
                 "RED drop rate for high-loss, non-TCP bytes";
             }
             leaf queue-counters-red-bytes-ht {
               type uint64;
               description
                 "Number of RED dropped high-loss, TCP bytes";
             }
             leaf queue-counters-red-bytes-rate-ht {
               type uint64;
               description
                 "RED drop rate for high-loss, TCP bytes";
             }
             leaf queue-counters-red-bytes-low {
               type uint64;
               description
                 "Number of RED dropped low-loss bytes";
             }
             leaf queue-counters-red-bytes-rate-low {
               type uint64;
               description
                 "RED drop rate for low-loss bytes";
             }
             leaf queue-counters-red-bytes-medium-low {
               type uint64;
               description
                 "Number of RED dropped medium-low-loss bytes";
             }
             leaf queue-counters-red-bytes-rate-medium-low {
               type uint64;
               description
                 "RED drop rate for medium-low-loss bytes";
             }
             leaf queue-counters-red-bytes-medium-high {
               type uint64;
               description
                 "Number of RED dropped medium-high-loss bytes";
             }
             leaf queue-counters-red-bytes-rate-medium-high {
               type uint64;
               description
                 "RED drop rate for medium-high-loss bytes";
             }
             leaf queue-counters-red-bytes-medium {
               type uint64;
               description
                 "Number of RED dropped medium-loss bytes";
             }
             leaf queue-counters-red-bytes-rate-medium {
               type uint64;
               description
                 "RED drop rate for medium-loss bytes";
             }
             leaf queue-counters-red-bytes-high {
               type uint64;
               description
                 "Number of RED dropped high-loss bytes";
             }
             leaf queue-counters-red-bytes-rate-high {
               type uint64;
               description
                 "RED drop rate for high-loss bytes";
             }
             leaf queue-counters-timestamp {
               type uint64;
               description
                 "Last packet enqueued timestamp";
             }
             leaf queue-counters-total-drop-packets {
               type uint64;
               description
                 "Number of total packets dropped at the queue";
             }
             leaf queue-counters-total-drop-packets-rate {
               type uint64;
               description
                 "Number of total packets dropped at the queue";
             }
             leaf queue-counters-total-drop-bytes {
               type uint64;
               description
                 "Number of total packets dropped at the queue";
             }
             leaf queue-counters-total-drop-bytes-rate {
               type uint64;
               description
                 "Number of total packets dropped at the queue";
             }
             leaf queue-counters-reserved-buffer-packets {
               type int32;
               description
                 "Queues's usage of reserved buffer pool in pkts";
             }
             leaf queue-counters-reserved-buffer-bytes {
               type int32;
               description
                 "Queues's usage of reserved buffer pool in bytes";
             }
             leaf queue-counters-shared-buffer-packets {
               type int32;
               description
                 "Queues's usage of shared buffer pool in pkts";
             }
             leaf queue-counters-shared-buffer-bytes {
               type int32;
               description
                 "Queues's usage of shared buffer pool in bytes";
             }
             leaf queue-counters-depth-average {
               type int32;
               description
                 "Time averaged queue depth";
             }
             leaf queue-counters-depth-current {
               type int32;
               description
                 "Current instantaneous queue depth";
             }
             leaf queue-counters-depth-peak {
               type int32;
               description
                 "Peak queue depth";
             }
             leaf queue-counters-depth-max {
               type int32;
               description
                 "Maximum queue depth attained";
             }
             leaf queue-counters-srx-reserved-buffer-bytes {
               type int32;
               description
                 "Queues's usage of reserved buffer pool in bytes";
             }
             leaf queue-counters-srx-depth-current {
               type int32;
               description
                 "Current instantaneous queue depth";
             }
           }
           container interface-cos-summary {
             description
               "Summary of forwarding class and queue information on an 
               interface";
             leaf intf-cos-forwarding-classes-supported {
               type int32;
               description
                 "Number of forwarding classes supported on this interface";
             }
             leaf intf-cos-forwarding-classes-in-use {
               type int32;
               description
                 "Number of forwarding classes currently in use on this 
                 interface";
             }
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
             leaf intf-cos-burst-size-for-ifl {
               type int32;
               description
                 "Burst size for the logical interface";
             }
           }
           container interface-cos-short-summary {
             description
               "Summary of queue information on an interface";
             leaf intf-cos-queue-type {
               type string;
               description
                 "Interface queue type";
             }
             leaf intf-cos-num-queues-supported {
               type int32;
               description
                 "Number of queues supported on this interface";
             }
             leaf intf-cos-num-queues-in-use {
               type int32;
               description
                 "Number of queues currently in use on this interface";
             }
             leaf intf-cos-queue-dedicated-or-shared {
               type string;
               description
                 "Interface has dedicated or shared queues";
             }
             leaf intf-cos-sched-resource-type {
               type string;
               description
                 "Interface scheduling resource type";
             }
             leaf intf-cos-sched-resource-usage-mic-limit {
               type int32;
               description
                 "MIC/PIC scheduling resource usage limit";
             }
             leaf intf-cos-sched-resource-usage-mic-count {
               type int32;
               description
                 "MIC/PIC scheduling resource usage count";
             }
             leaf intf-cos-sched-resource-usage-port-limit {
               type int32;
               description
                 "Interface scheduling resource limit";
             }
             leaf intf-cos-sched-resource-usage-port-count {
               type int32;
               description
                 "Interface scheduling resource usage";
             }
           }
           container queue-num-forwarding-class-name-map {
             leaf queue-number {
               type int32;
               description
                 "Queue number";
             }
             leaf forwarding-class-name {
               type string;
               description
                 "Forwarding class name associated with queue";
             }
           }
         }
         container forwarding-class-counters {
           description
             "Forwarding-class counter statistics";
           leaf forwarding-class-counters-error-message {
             type string;
             description
               "Forwarding-class statistics not available for this interface";
           }
           container ipv4-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container ipv6-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container mpls-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container layer2-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container other-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container protocol-aggregate-forwarding-class-counters {
             leaf forwarding-class-stats-type {
               type string;
             }
             container per-forwarding-class-counters {
               leaf fc_name_header {
                 type string;
               }
               leaf forwarding-class-name {
                 type string;
                 description
                   "Forwarding class name associated with queue";
               }
               leaf fc-input-bytes {
                 type int32;
               }
               leaf fc-input-bytes-rate {
                 type int32;
                 description
                   "Input bytes rate";
               }
               leaf fc-output-bytes {
                 type int32;
               }
               leaf fc-output-bytes-rate {
                 type int32;
                 description
                   "Output bytes rate";
               }
               leaf fc-input-packets {
                 type int32;
               }
               leaf fc-input-packets-rate {
                 type int32;
                 description
                   "Input packets rate";
               }
               leaf fc-output-packets {
                 type int32;
               }
               leaf fc-output-packets-rate {
                 type int32;
                 description
                   "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container forwarding-class-statistics {
             container protocol-aggregate-forwarding-class-counters {
             }
             container ipv4-forwarding-class-counters {
             }
             container ipv6-forwarding-class-counters {
             }
             container mpls-forwarding-class-counters {
             }
             container layer2-forwarding-class-counters {
             }
             container other-forwarding-class-counters {
             }
           }
           container forwarding-class-accounting-parameters {
             leaf forwarding-class-accounting-for-protocol {
               type string;
             }
             leaf forwarding-class-accounting-for-traffic-direction {
               type string;
             }
             leaf forwarding-class-accounting-for-traffic-type {
               type string;
             }
             leaf forwarding-class-accounting-overhead-bytes {
               type uint32;
             }
           }
           container per-forwarding-class-counters {
             leaf fc_name_header {
               type string;
             }
             leaf forwarding-class-name {
               type string;
               description
                 "Forwarding class name associated with queue";
             }
             leaf fc-input-bytes {
               type int32;
             }
             leaf fc-input-bytes-rate {
               type int32;
               description
                 "Input bytes rate";
             }
             leaf fc-output-bytes {
               type int32;
             }
             leaf fc-output-bytes-rate {
               type int32;
               description
                 "Output bytes rate";
             }
             leaf fc-input-packets {
               type int32;
             }
             leaf fc-input-packets-rate {
               type int32;
               description
                 "Input packets rate";
             }
             leaf fc-output-packets {
               type int32;
             }
             leaf fc-output-packets-rate {
               type int32;
               description
                 "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container multilink-bundle-options {
           leaf filler-packet-interval {
             type int32;
           }
         }
         container multilink-traffic-statistics {
           container bundle {
           }
           container class {
             description
               "Multilink class traffic statistics";
           }
           container multilink-detail-statistics {
             container bundle-detail {
             }
             container class-detail {
             }
           }
           container crtp {
             container crtp-sessions {
               leaf input-frames {
                 type int32;
               }
               leaf output-frames {
                 type int32;
               }
             }
             list crtp-statistics {
               key "name";
               leaf name {
                 type string;
                 description
                   "Name of this item";
               }
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
           }
         }
         container traffic-statistics {
           leaf input-bps {
             type int32;
           }
           leaf input-pps {
             type int32;
           }
           leaf output-bps {
             type int32;
           }
           leaf output-pps {
             type int32;
           }
           leaf input-packets {
             type int32;
           }
           leaf output-packets {
             type int32;
           }
           leaf input-bytes {
             type int32;
           }
           leaf output-bytes {
             type int32;
           }
           container ipv6-transit-statistics {
             leaf input-bytes {
               type int32;
             }
             leaf output-bytes {
               type int32;
             }
             leaf input-packets {
               type int32;
             }
             leaf output-packets {
               type int32;
             }
           }
           container ipv6-total-statistics {
             leaf input-bytes {
               type int32;
             }
             leaf output-bytes {
               type int32;
             }
             leaf input-packets {
               type int32;
             }
             leaf output-packets {
               type int32;
             }
           }
         }
         container multicast-statistics {
           description
             "Multicast statistics for interface";
           leaf multicast-statistics-header {
             type empty;
           }
           container ipv4-multicast-statistics {
             description
               "IPV4 multicast statistics for interface";
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
           container ipv6-multicast-statistics {
             description
               "IPV6 multicast statistics for interface";
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
         }
         container ingress-traffic-statistics {
           description
             "Traffic statistics at ingress before entering Packet 
             Forwarding Engine";
           leaf input-bps {
             type int32;
           }
           leaf input-pps {
             type int32;
           }
           leaf input-drop-bps {
             type int32;
             description
               "Drop rate at ingress in bits per second ";
           }
           leaf input-drop-pps {
             type int32;
             description
               "Drop rate at ingress in packets per second ";
           }
           leaf input-bytes {
             type int32;
           }
           leaf input-packets {
             type int32;
           }
           leaf input-drop-bytes {
             type int32;
             description
               "Drop statistics at ingress in bytes";
           }
           leaf input-drop-packets {
             type int32;
             description
               "Drop statistics at ingress in packets";
           }
         }
         container transit-traffic-statistics {
           description
             "Statistics for traffic passing through the Packet Forwarding 
             Engine";
         }
         container keepalive-statistics {
           description
             "Keepalive statistics for this interface";
           leaf keepalive-lmi-descriptor {
             type string;
           }
           leaf keepalive-input-count {
             type int32;
           }
           leaf keepalive-input-time {
             type string;
           }
           leaf keepalive-output-count {
             type int32;
           }
           leaf keepalive-output-time {
             type string;
           }
         }
         container virtual-circuit-information {
           description
             "Operational information and statistics for a virtual circuit";
           container traffic-statistics {
             leaf input-bps {
               type int32;
             }
             leaf input-pps {
               type int32;
             }
             leaf output-bps {
               type int32;
             }
             leaf output-pps {
               type int32;
             }
             leaf input-packets {
               type int32;
             }
             leaf output-packets {
               type int32;
             }
             leaf input-bytes {
               type int32;
             }
             leaf output-bytes {
               type int32;
             }
             container ipv6-transit-statistics {
               leaf input-bytes {
                 type int32;
               }
               leaf output-bytes {
                 type int32;
               }
               leaf input-packets {
                 type int32;
               }
               leaf output-packets {
                 type int32;
               }
             }
             container ipv6-total-statistics {
               leaf input-bytes {
                 type int32;
               }
               leaf output-bytes {
                 type int32;
               }
               leaf input-packets {
                 type int32;
               }
               leaf output-packets {
                 type int32;
               }
             }
           }
           container atm-cos-information {
             leaf vc-cos-mode {
               type string;
               description
                 "Virtual circuit CoS scheduling mode";
             }
             list atm-cos-queue {
               container atm-cos-queue-parameters {
                 leaf cos-forwarding-class-name {
                   type string;
                   description
                     "Forwarding class name associated with queue";
                 }
                 leaf cos-queue-number {
                   type int32;
                   description
                     "Queue number";
                 }
                 leaf scheduling-priority {
                   type string;
                   description
                     "Scheduling priority";
                 }
                 leaf transmit-weight-cells {
                   type int32;
                   description
                     "Weight to apply to scheduling as number of cells";
                 }
                 leaf transmit-weight-percent {
                   type int32;
                   description
                     "Weight to apply to scheduling as fill percentage";
                 }
                 leaf epd-threshold {
                   type int32;
                   description
                     "Early packet drop threshold";
                 }
                 leaf epd-threshold-plp0 {
                   type int32;
                   description
                     "Early packet drop threshold for PLP 0";
                 }
                 leaf epd-threshold-plp1 {
                   type int32;
                   description
                     "Early packet drop threshold for PLP 1";
                 }
                 container linear-red-drop-profile {
                   leaf queue-depth {
                     type uint32;
                     description
                       "Instantaneous queue depth";
                   }
                   leaf low-red {
                     type int32;
                     description
                       "Fill level percentage when linear RED is applied for
                       low PLP";
                   }
                   leaf high-red {
                     type int32;
                     description
                       "Fill level percentage when linear RED is applied for
                       high PLP";
                   }
                   leaf max-low-red {
                     type int32;
                     description
                       "Fill level percentage with 100% packet drop for low 
                       PLP";
                   }
                   leaf max-high-red {
                     type int32;
                     description
                       "Fill level percentage with 100% packet drop for high
                       PLP";
                   }
                 }
               }
               container atm-cos-queue-statistics {
                 leaf atm-output-bytes {
                   type int32;
                 }
                 leaf atm-output-packets {
                   type int32;
                 }
                 leaf atm-packet-drops {
                   type int32;
                 }
               }
               container atm-cos-plp-statistics {
                 leaf atm-plp0-output-bytes {
                   type int32;
                 }
                 leaf atm-plp1-output-bytes {
                   type int32;
                 }
                 leaf atm-plp0-output-packets {
                   type int32;
                 }
                 leaf atm-plp1-output-packets {
                   type int32;
                 }
                 leaf atm-plp0-byte-drops {
                   type int32;
                 }
                 leaf atm-plp1-byte-drops {
                   type int32;
                 }
                 leaf atm-plp0-packet-drops {
                   type int32;
                 }
                 leaf atm-plp1-packet-drops {
                   type int32;
                 }
               }
             }
           }
         }
         list policer-information {
           description
             "Interface policer information";
           leaf policer-family {
             type string;
             description
               "Protocol family of the policer";
           }
           leaf policer-input {
             type string;
             description
               "Name of the input policer";
           }
           leaf policer-output {
             type string;
             description
               "Name of the output policer";
           }
         }
         list address-family {
           leaf local-bias-information {
             type string;
           }
           leaf ft-iff-dest-port {
             type uint32;
             description
               "Destination UDP port to be used for this family";
           }
           container pppoe-underlying-information {
             description
               "PPPoE Underlying information";
             list pppoe-underlying-interface {
               leaf dynamic-profile {
                 type string;
                 description
                   "Dynamic Profile name";
               }
               leaf service-name-table {
                 type string;
                 description
                   "Name of Service Name Table";
               }
               leaf max-sessions {
                 type int32;
                 description
                   "Maximum number of PPPoE sessions";
               }
               leaf max-sessions-vsa-ignore {
                 type string;
                 description
                   "Ignore max-sessions VSA";
               }
               leaf duplicate-protection {
                 type string;
                 description
                   "Duplicate protection mode";
               }
               leaf short-cycle-protection {
                 type string;
                 description
                   "Short cycle protection mode";
               }
               leaf direct-connect {
                 type string;
                 description
                   "Direct connect mode";
               }
               leaf ac-name {
                 type string;
                 description
                   "Access Concentrator name";
               }
               leaf underlying-interface-name {
                 type string;
                 description
                   "Underlying interface name";
               }
               leaf underlying-interface-index {
                 type string;
                 description
                   "Underlying interface index";
               }
               leaf encapsulation-type-identifier {
                 type string;
                 description
                   "Encapsulation type identifier";
               }
               leaf state {
                 type string;
                 description
                   "State";
               }
               leaf active-sessions {
                 type int32;
                 description
                   "Number of active PPPoE sessions";
               }
               leaf aci-autosensing {
                 type string;
                 description
                   "ACI VLAN Autosensing mode";
               }
               leaf line-identity-autosensing {
                 type string;
                 description
                   "Line Identity Autosensing mode";
               }
             }
           }
           list interface-address {
           }
           container destination-class-statistics {
             description
               "Destination class usage (DCU) statistics";
           }
           container source-class-statistics {
             description
               "Source class usage (SCU) statistics";
           }
         }
         list bridge-iff-properties {
           description
             "Information about Ethernet-switching address family";
         }
         container l2circuit-info {
           leaf out-of-sequence {
             type int32;
           }
           leaf denied-packets {
             type int32;
           }
           leaf cell-bundle-size {
             type int32;
           }
           leaf cell-bundle-timeout {
             type int32;
           }
           leaf cell-timeout-count {
             type int32;
           }
         }
         container media-information {
           description
             "Information about media alarms";
           leaf media-type {
             type string;
             description
               "Type of media this information is for";
           }
           list media-alarm {
             leaf media-alarm-name {
               type string;
             }
             leaf media-alarm-count {
               type int32;
             }
             leaf media-alarm-seconds {
               type int32;
             }
             leaf media-alarm-state {
               type string;
             }
             leaf ce-counter-name {
               type string;
               description
                 "Circuit Emulation counter information";
             }
             leaf ce-counter-packets {
               type int32;
               description
                 "Circuit Emulation number of packets";
             }
             leaf ce-counter-bytes {
               type int32;
               description
                 "Circuit Emulation number of bytes";
             }
             leaf ce-counter-count {
               type int32;
               description
                 "Circuit Emulation number of event occurrences";
             }
           }
           leaf ds1-timeslots {
             type string;
           }
           leaf ds1-line-encoding {
             type string;
           }
           leaf ds1-byte-encoding {
             type string;
           }
           leaf ds1-data-inversion {
             type string;
           }
           leaf idle-cycle-flag {
             type string;
           }
           leaf start-end-flag {
             type string;
           }
           leaf ds0-byte-encoding {
             type string;
           }
           leaf ds0-data-inversion {
             type string;
           }
           leaf e3-data-inversion {
             type string;
           }
           leaf ds1-buildout {
             type string;
             description
               "Number of feet";
           }
         }
         list macsec-statistics {
           description
             "Information about MAC Security statistics details";
           leaf interface-name {
             type string;
             description
               "Class-of-service interface name";
           }
           leaf encrypted-packets {
             type uint64;
             description
               "Macsec encrypted packets sent";
           }
           leaf encrypted-bytes {
             type uint64;
             description
               "Macsec encrypted bytes sent";
           }
           leaf protected-packets {
             type uint64;
             description
               "Macsec packets sent with only integrity protection";
           }
           leaf protected-bytes {
             type uint64;
             description
               "Macsec bytes sent with only integrity protection";
           }
           leaf ok-packets {
             type uint64;
             description
               "Macsec packets accepted";
           }
           leaf decrypted-bytes {
             type uint64;
             description
               "Macsec received bytes decrypted";
           }
           leaf decrypted-packets {
             type uint64;
             description
               "Macsec received packets decrypted";
           }
           leaf validated-packets {
             type uint64;
             description
               "Macsec received packets validated";
           }
           leaf validated-bytes {
             type uint64;
             description
               "Macsec received bytes validated";
           }
           leaf untagged-packets {
             type uint64;
             description
               "Macsec untagged packets";
           }
           leaf toolong-packets {
             type uint64;
             description
               "Macsec too long packets transmitted on a secure channel";
           }
           leaf control-packets {
             type uint64;
             description
               "Macsec control packets received on a secure channel";
           }
           leaf tagged-miss-packets {
             type uint64;
             description
               "Macsec tagged miss packets received on a secure channel";
           }
           leaf untagged-hit-packets {
             type uint64;
             description
               "Macsec untagged hit packets received on a secure channel";
           }
           leaf notag-packets {
             type uint64;
             description
               "Macsec no tag packets received on a secure channel";
           }
           leaf badtag-packets {
             type uint64;
             description
               "Macsec bad tag packets received on a secure channel";
           }
           leaf unknown-sci-packets {
             type uint64;
             description
               "Macsec unknown sci packets received on a secure channel";
           }
           leaf no-sci-packets {
             type uint64;
             description
               "Macsec no sci packets received on a secure channel";
           }
           leaf control-pass-packets {
             type uint64;
             description
               "Macsec allowed control packets received on a secure channel";
           }
           leaf uncontrol-pass-packets {
             type uint64;
             description
               "Macsec allowed uncontrol packets received on a secure 
               channel";
           }
           leaf control-fail-packets {
             type uint64;
             description
               "Macsec dropped control packets received on a secure channel";
           }
           leaf uncontrol-fail-packets {
             type uint64;
             description
               "Macsec dropped uncontrol packets received on a secure 
               channel";
           }
           leaf hit-dropped-packets {
             type uint64;
             description
               "Macsec hit dropped packets received on a security channel";
           }
           leaf notusing-sa-packets {
             type uint64;
             description
               "Macsec not using sa packets received on a security channel";
           }
           leaf unused-sa-packets {
             type uint64;
             description
               "Macsec unused sa packets received on a security channel";
           }
           leaf late-packets {
             type uint64;
             description
               "Macsec late packets dropped on a security channel";
           }
           leaf delayed-packets {
             type uint64;
             description
               "Macsec delayed packets accepted on a security channel";
           }
           leaf unchecked-packets {
             type uint64;
             description
               "Macsec unchecked packets accepted on a security channel";
           }
           leaf notvalid-packets {
             type uint64;
             description
               "Macsec not valid packets dropped on a security channel";
           }
           leaf invalid-packets {
             type uint64;
             description
               "Macsec invalid packets accepted on a security channel";
           }
           list secure-channel-sent {
             leaf encrypted-packets {
               type uint64;
               description
                 "Macsec encrypted packets sent";
             }
             leaf encrypted-bytes {
               type uint64;
               description
                 "Macsec encrypted bytes sent";
             }
             leaf protected-packets {
               type uint64;
               description
                 "Macsec packets sent with only integrity protection";
             }
             leaf protected-bytes {
               type uint64;
               description
                 "Macsec bytes sent with only integrity protection";
             }
           }
           list secure-association-sent {
             leaf encrypted-packets {
               type uint64;
               description
                 "Macsec encrypted packets sent";
             }
             leaf encrypted-bytes {
               type uint64;
               description
                 "Macsec encrypted bytes sent";
             }
             leaf protected-packets {
               type uint64;
               description
                 "Macsec packets sent with only integrity protection";
             }
             leaf protected-bytes {
               type uint64;
               description
                 "Macsec bytes sent with only integrity protection";
             }
           }
           list secure-channel-received {
             leaf ok-packets {
               type uint64;
               description
                 "Macsec packets accepted";
             }
             leaf decrypted-packets {
               type uint64;
               description
                 "Macsec received packets decrypted";
             }
             leaf decrypted-bytes {
               type uint64;
               description
                 "Macsec received bytes decrypted";
             }
             leaf validated-packets {
               type uint64;
               description
                 "Macsec received packets validated";
             }
             leaf validated-bytes {
               type uint64;
               description
                 "Macsec received bytes validated";
             }
           }
           list secure-association-received {
             leaf ok-packets {
               type uint64;
               description
                 "Macsec packets accepted";
             }
             leaf decrypted-packets {
               type uint64;
               description
                 "Macsec received packets decrypted";
             }
             leaf decrypted-bytes {
               type uint64;
               description
                 "Macsec received bytes decrypted";
             }
             leaf validated-packets {
               type uint64;
               description
                 "Macsec received packets validated";
             }
             leaf validated-bytes {
               type uint64;
               description
                 "Macsec received bytes validated";
             }
           }
           list macsec-error-information {
             list secure-channel-sent-errors {
               leaf untagged-packets {
                 type uint64;
                 description
                   "Macsec untagged packets";
               }
               leaf toolong-packets {
                 type uint64;
                 description
                   "Macsec too long packets transmitted on a secure channel";
               }
             }
             list secure-channel-received-errors {
               leaf control-packets {
                 type uint64;
                 description
                   "Macsec control packets received on a secure channel";
               }
               leaf tagged-miss-packets {
                 type uint64;
                 description
                   "Macsec tagged miss packets received on a secure channel";
               }
               leaf untagged-hit-packets {
                 type uint64;
                 description
                   "Macsec untagged hit packets received on a secure channel";
               }
               leaf untagged-packets {
                 type uint64;
                 description
                   "Macsec untagged packets";
               }
               leaf notag-packets {
                 type uint64;
                 description
                   "Macsec no tag packets received on a secure channel";
               }
               leaf badtag-packets {
                 type uint64;
                 description
                   "Macsec bad tag packets received on a secure channel";
               }
               leaf unknown-sci-packets {
                 type uint64;
                 description
                   "Macsec unknown sci packets received on a secure channel";
               }
               leaf no-sci-packets {
                 type uint64;
                 description
                   "Macsec no sci packets received on a secure channel";
               }
               leaf control-pass-packets {
                 type uint64;
                 description
                   "Macsec allowed control packets received on a secure 
                   channel";
               }
               leaf control-fail-packets {
                 type uint64;
                 description
                   "Macsec dropped control packets received on a secure 
                   channel";
               }
               leaf uncontrol-pass-packets {
                 type uint64;
                 description
                   "Macsec allowed uncontrol packets received on a secure 
                   channel";
               }
               leaf uncontrol-fail-packets {
                 type uint64;
                 description
                   "Macsec dropped uncontrol packets received on a secure 
                   channel";
               }
             }
             list secure-channel-received-extended {
               leaf hit-dropped-packets {
                 type uint64;
                 description
                   "Macsec hit dropped packets received on a security 
                   channel";
               }
               leaf invalid-packets {
                 type uint64;
                 description
                   "Macsec invalid packets accepted on a security channel";
               }
               leaf late-packets {
                 type uint64;
                 description
                   "Macsec late packets dropped on a security channel";
               }
               leaf delayed-packets {
                 type uint64;
                 description
                   "Macsec delayed packets accepted on a security channel";
               }
               leaf unchecked-packets {
                 type uint64;
                 description
                   "Macsec unchecked packets accepted on a security channel";
               }
               leaf notvalid-packets {
                 type uint64;
                 description
                   "Macsec not valid packets dropped on a security channel";
               }
               leaf notusing-sa-packets {
                 type uint64;
                 description
                   "Macsec not using sa packets received on a security 
                   channel";
               }
               leaf unused-sa-packets {
                 type uint64;
                 description
                   "Macsec unused sa packets received on a security channel";
               }
               leaf untagged-hit-packets {
                 type uint64;
                 description
                   "Macsec untagged hit packets received on a secure channel";
               }
             }
           }
         }
         container lag-traffic-statistics {
           container lag-multicast-statistics {
             leaf lag-multicast-statistics-header {
               type empty;
             }
             container lag-ipv4-multicast-statistics {
               leaf input-packets {
                 type int32;
               }
               leaf input-pps {
                 type int32;
               }
               leaf input-bytes {
                 type int32;
               }
               leaf input-bps {
                 type int32;
               }
               leaf output-packets {
                 type int32;
               }
               leaf output-pps {
                 type int32;
               }
               leaf output-bytes {
                 type int32;
               }
               leaf output-bps {
                 type int32;
               }
             }
             container lag-ipv6-multicast-statistics {
               leaf input-packets {
                 type int32;
               }
               leaf input-pps {
                 type int32;
               }
               leaf input-bytes {
                 type int32;
               }
               leaf input-bps {
                 type int32;
               }
               leaf output-packets {
                 type int32;
               }
               leaf output-pps {
                 type int32;
               }
               leaf output-bytes {
                 type int32;
               }
               leaf output-bps {
                 type int32;
               }
             }
           }
           list if-distribution-list-information {
           }
         }
         container layer2-input-policer-statistics {
           description
             "Layer 2 input policer statistics for interface";
           leaf policer-medium-low-frames {
             type int32;
             description
               "Number of loss priority medium low frames";
           }
           leaf policer-medium-low-bytes {
             type int32;
             description
               "Number of loss priority medium low bytes";
           }
           leaf policer-medium-low-rate {
             type int32;
             description
               "Rate of loss priority medium low pkts";
           }
         }
         container layer2-output-policer-statistics {
           description
             "Layer 2 output policer statistics for interface";
           leaf policer-medium-low-frames {
             type int32;
             description
               "Number of loss priority medium low frames";
           }
           leaf policer-medium-low-bytes {
             type int32;
             description
               "Number of loss priority medium low bytes";
           }
           leaf policer-medium-low-rate {
             type int32;
             description
               "Rate of loss priority medium low pkts";
           }
         }
         container mac-policer-information {
           container ether-policer-list {
           }
         }
       }
     }
     list interface-map {
       description
         "Class-of-service interface mappings";
       leaf interface-name {
         type string;
         description
           "Class-of-service interface name";
       }
       leaf interface-index {
         type uint32;
         description
           "Class-of-service interface index";
       }
       leaf interface-queues-supported {
         type uint32;
         description
           "Number of queues supported on this interface";
       }
       leaf interface-queues-in-use {
         type uint32;
         description
           "Number of queues in use on this interface";
       }
       leaf interface-total-egress-queues-created {
         type uint32;
         description
           "Total number of non-default egress queues in use on this 
           interface";
       }
       leaf interface-total-ingress-queues-created {
         type uint32;
         description
           "Total number of non-default ingress queues in use on this 
           interface";
       }
       leaf interface-exclude-queue-overhead-bytes {
         type string;
         description
           "Setting for excluding queue overhead bytes for aggregate 
           statistics";
       }
       leaf interface-logical-interface-aggregate-statistics {
         type string;
         description
           "Whether interface statistics for a logical interface are enabled
           or disabled";
       }
       leaf interface-shaping-rate {
         type string;
         description
           "Class-of-service interface shaping rate";
       }
       leaf scheduler-map-name {
         type string;
         description
           "Class-of-service scheduler map name";
       }
       leaf scheduler-map-index {
         type uint64;
         description
           "Class-of-service scheduler map index";
       }
       leaf interface-input-shaping-rate {
         type string;
         description
           "Class-of-service interface input shaping rate";
       }
       leaf input-scheduler-map-name {
         type string;
         description
           "Class-of-service input scheduler map name";
       }
       leaf input-scheduler-map-index {
         type uint32;
         description
           "Index number for Class-of-service input scheduler map";
       }
       leaf chassis-scheduler-map-name {
         type string;
         description
           "Class-of-service chassis scheduler map name";
       }
       leaf chassis-scheduler-map-index {
         type uint32;
         description
           "Index number for Class-of-service chassis scheduler map";
       }
       leaf input-traffic-control-profile-name {
         type string;
         description
           "Class-of-service input traffic control profile name";
       }
       leaf input-traffic-control-profile-index {
         type uint64;
         description
           "Index number for Class-of-service input traffic control profile";
       }
       leaf input-traffic-control-profile-remaining-name {
         type string;
         description
           "Class-of-service input traffic control profile remaining name";
       }
       leaf input-traffic-control-profile-remaining-index {
         type uint64;
         description
           "Index number for Class-of-service input traffic control profile 
           remaining";
       }
       leaf output-traffic-control-profile-name {
         type string;
         description
           "Class-of-service output traffic control profile name";
       }
       leaf output-traffic-control-profile-index {
         type uint64;
         description
           "Index number for Class-of-service output traffic control profile";
       }
       leaf output-traffic-control-profile-remaining-name {
         type string;
         description
           "Class-of-service output traffic control profile remaining name";
       }
       leaf output-traffic-control-profile-remaining-index {
         type uint64;
         description
           "Index number for Class-of-service output traffic control profile
           remaining";
       }
       leaf forwarding-class-map-name {
         type string;
         description
           "Class-of-service forwarding class map name";
       }
       leaf forwarding-class-map-index {
         type uint32;
         description
           "Index number for Class-of-service forwarding class map";
       }
       leaf interface-congestion-notification-map {
         type string;
         description
           "Congestion notification enabled/disabled on interface";
       }
       leaf interface-congestion-notification-map-name {
         type string;
         description
           "Congestion notification Profile Name";
       }
       leaf interface-congestion-notification-map-index {
         type uint32;
         description
           "Congestion notification Profile Index";
       }
       leaf dcbx-congestion-notification-map {
         type string;
         description
           "Congestion notification enabled/disabled by DCBX on interface";
       }
       leaf monitoring-profile-map-name {
         type string;
         description
           "Monitoring Profile Name";
       }
       leaf monitoring-profile-map-index {
         type uint32;
         description
           "Monitoring Profile Index";
       }
       leaf interface-rewrite-value {
         type string;
         description
           "Interface rewrite value input / output";
       }
       leaf code-point-type {
         type string;
         description
           "Class-of-service code point type";
       }
       leaf code-point-bits {
         type string;
         description
           "Class-of-service code point bit sequence";
       }
       leaf scheduler-map-forwarding-class-set-name {
         type string;
         description
           "Class-of-service scheduler map forwarding-class-set name";
       }
       leaf scheduler-map-forwarding-class-set-index {
         type uint32;
         description
           "Class-of-service scheduler map forwarding class set index";
       }
       leaf interface-drop-congestion-notification {
         type string;
         description
           "Drop Congestion notification on interface";
       }
       leaf interface-dedicated-buffer-profile-name {
         type string;
         description
           "Dedicated Buffer Profile Name";
       }
       leaf interface-decn-profile-name {
         type string;
         description
           "DECN Profile Name";
       }
       leaf interface-dynamic-threshold-profile-name {
         type string;
         description
           "Dynamic Threshold Profile Name";
       }
       leaf interface-lecn-profile-name {
         type string;
         description
           "LECN Profile Name";
       }
       list forwarding-class-set-attachment {
         description
           "Class-of-service forwarding class set interface attachment ";
         leaf forwarding-class-set-name {
           type string;
           description
             "Class-of-service forwarding class set name";
         }
         leaf table-index {
           type uint32;
           description
             "Table index";
         }
         leaf output-traffic-control-profile-name {
           type string;
           description
             "Class-of-service output traffic control profile name";
         }
         leaf output-traffic-control-profile-index {
           type uint64;
           description
             "Index number for Class-of-service output traffic control 
             profile";
         }
       }
       list cos-objects {
         description
           "Class-of-service object  mappings";
         leaf cos-object-type {
           type string;
           description
             "Class-of-service object type";
         }
         leaf cos-object-name {
           type string;
           description
             "Class-of-service object name";
         }
         leaf cos-object-subtype {
           type string;
           description
             "Class-of-service object subtype";
         }
         leaf cos-object-index {
           type uint64;
           description
             "Class-of-service object index";
         }
       }
       list i-logical-map {
         leaf i-logical-name {
           type string;
           description
             "Class-of-service logical interface name";
         }
         leaf i-logical-index {
           type uint32;
           description
             "Class-of-service logical interface index";
         }
         leaf policy-map-marking {
           type string;
           description
             "Class-of-service logical interface policy map";
         }
         leaf interface-has-dedicated-queues {
           type string;
           description
             "Whether interface has dedicated queues";
         }
         leaf user-plane-name {
           type string;
           description
             "Class-of-service user-plane name for XDA";
         }
         leaf policer-bandwidth {
           type uint32;
           description
             "Class-of-service logical interface policer bandwidth";
         }
         leaf policer-burst {
           type uint32;
           description
             "Class-of-service logical interface policer burst";
         }
         leaf shaper-bandwidth {
           type uint32;
           description
             "Class-of-service logical interface shaper bandwidth";
         }
         leaf shaper-burst {
           type uint32;
           description
             "Class-of-service logical interface shaper burst";
         }
         leaf shaping-rate {
           type uint64;
           description
             "Class-of-service shaping rate";
         }
         leaf burst-size {
           type string;
           description
             "Class-of-service logical interface burst size";
         }
         leaf input-shaping-rate {
           type uint64;
           description
             "Class-of-service input shaping rate";
         }
         leaf input-burst-size {
           type string;
           description
             "Class-of-service logical interface input burst size";
         }
         leaf adjusting-application-name {
           type string;
           description
             "The name of the application performing the rate adjustment";
         }
         leaf adjustment-type {
           type string;
           description
             "Class-of-service rate adjustment type";
         }
         leaf configured-shaping-rate {
           type string;
           description
             "Class-of-service configured shaping rate";
         }
         leaf adjustment-value {
           type string;
           description
             "Class-of-service adjusted shaping rate value";
         }
         leaf adjustment-overhead-accounting-mode {
           type string;
           description
             "Class-of-service adjusted overhead-accounting mode";
         }
         leaf adjustment-overhead-bytes {
           type int32;
           description
             "Class-of-service adjusted overhead bytes";
         }
         leaf adjustment-target {
           type string;
           description
             "Class-of-service rate adjustment target";
         }
         leaf adjustment-priority {
           type uint32;
           description
             "Class-of-service rate adjustment priority";
         }
         leaf monitoring-profile-map-name {
           type string;
           description
             "Monitoring Profile Name";
         }
         list cos-objects {
           description
             "Class-of-service object  mappings";
           leaf cos-object-type {
             type string;
             description
               "Class-of-service object type";
           }
           leaf cos-object-name {
             type string;
             description
               "Class-of-service object name";
           }
           leaf cos-object-subtype {
             type string;
             description
               "Class-of-service object subtype";
           }
           leaf cos-object-index {
             type uint64;
             description
               "Class-of-service object index";
           }
         }
       }
     }
   }
   grouping cos-interface-set-information-block {
     list interface-set-map {
       leaf interface-set-name {
         type string;
         description
           "Class-of-service interface-set name";
       }
       leaf interface-set-index {
         type uint64;
         description
           "Class-of-service logical interface index";
       }
       leaf interface-name {
         type string;
         description
           "Class-of-service interface name";
       }
       leaf interface-index {
         type uint32;
         description
           "Class-of-service interface index";
       }
       leaf user-plane-name {
         type string;
         description
           "Class-of-service user-plane name for XDA";
       }
       leaf interface-queues-supported {
         type uint32;
         description
           "Number of queues supported on this interface";
       }
       leaf interface-queues-in-use {
         type uint32;
         description
           "Number of queues in use on this interface";
       }
       leaf input-traffic-control-profile-name {
         type string;
         description
           "Class-of-service input traffic control profile name";
       }
       leaf input-traffic-control-profile-index {
         type uint64;
         description
           "Index number for Class-of-service input traffic control profile";
       }
       leaf input-traffic-control-profile-remaining-name {
         type string;
         description
           "Class-of-service input traffic control profile remaining name";
       }
       leaf input-traffic-control-profile-remaining-index {
         type uint64;
         description
           "Index number for Class-of-service input traffic control profile 
           remaining";
       }
       leaf output-traffic-control-profile-name {
         type string;
         description
           "Class-of-service output traffic control profile name";
       }
       leaf output-traffic-control-profile-index {
         type uint64;
         description
           "Index number for Class-of-service output traffic control profile";
       }
       leaf output-traffic-control-profile-remaining-name {
         type string;
         description
           "Class-of-service output traffic control profile remaining name";
       }
       leaf output-traffic-control-profile-remaining-index {
         type uint64;
         description
           "Index number for Class-of-service output traffic control profile
           remaining";
       }
       leaf monitoring-profile-map-name {
         type string;
         description
           "Monitoring Profile Name";
       }
       leaf monitoring-profile-map-index {
         type uint32;
         description
           "Monitoring Profile Index";
       }
       leaf adjusting-application-name {
         type string;
         description
           "The name of the application performing the rate adjustment";
       }
       leaf adjustment-type {
         type string;
         description
           "Class-of-service rate adjustment type";
       }
       leaf configured-shaping-rate {
         type string;
         description
           "Class-of-service configured shaping rate";
       }
       leaf adjustment-value {
         type string;
         description
           "Class-of-service adjusted shaping rate value";
       }
       leaf adjustment-overhead-accounting-mode {
         type string;
         description
           "Class-of-service adjusted overhead-accounting mode";
       }
       leaf adjustment-overhead-bytes {
         type int32;
         description
           "Class-of-service adjusted overhead bytes";
       }
       leaf adjustment-target {
         type string;
         description
           "Class-of-service rate adjustment target";
       }
       leaf adjustment-priority {
         type uint32;
         description
           "Class-of-service rate adjustment priority";
       }
     }
   }
   grouping subscribers-physical-interfaces-information-block {
     list logical-interface {
       key "name address-family-name";
       description
         "Information about a single logical interface";
       leaf name {
         type string;
         description
           "Name of this item";
       }
       leaf subunit {
         type int32;
         description
           "Subunit for this interface";
       }
       leaf admin-status {
         type string;
       }
       leaf oper-status {
         type string;
       }
       leaf address-family-name {
         type string;
       }
       leaf ifa-local {
         type string;
         description
           "Protocol address on this interface";
       }
       leaf ifa-destination {
         type string;
         description
           "Protocol address of the remote side of this connection";
       }
       leaf state {
         type string;
       }
       leaf session-id {
         type int32;
       }
       leaf ac-name-session {
         type string;
       }
       leaf remote-mac {
         type string;
       }
       leaf underlying-interface-name {
         type string;
       }
       leaf underlying-interface-index {
         type int32;
       }
       leaf ignore-eol-tag {
         type string;
       }
       leaf intf-cos-queue-type {
         type string;
         description
           "Interface queue type";
       }
       leaf intf-cos-num-queues-supported {
         type int32;
         description
           "Number of queues supported on this interface";
       }
       leaf intf-cos-num-queues-in-use {
         type int32;
         description
           "Number of queues currently in use on this interface";
       }
       leaf input-bytes {
         type int32;
       }
       leaf output-bytes {
         type int32;
       }
       leaf input-packets {
         type int32;
       }
       leaf output-packets {
         type int32;
       }
       leaf input-bps {
         type int32;
       }
       leaf output-bps {
         type int32;
       }
       leaf input-pps {
         type int32;
       }
       leaf output-pps {
         type int32;
       }
       leaf hardware-token {
         type int32;
         description
           "Hardware token for layer 3 ifl";
       }
       container queue-counters {
         description
           "Queue counter statistics";
         leaf queue-number {
           type int32;
           description
             "Queue number";
         }
         leaf queue-counters-queued-packets {
           type int32;
           description
             "Queued packet count";
         }
         leaf queue-counters-trans-packets {
           type int32;
           description
             "Total number of transmitted packets";
         }
         leaf queue-counters-trans-packets-rate {
           type int32;
           description
             "Rate at which packets are transmitted";
         }
         leaf queue-counters-trans-bytes {
           type int32;
           description
             "Total number of transmitted bytes";
         }
         leaf queue-counters-trans-bytes-rate {
           type int32;
           description
             "Rate at which bytes are transmitted";
         }
         leaf queue-counters-total-drop-packets {
           type int32;
           description
             "Number of total packets dropped at the queue";
         }
         leaf queue-counters-total-drop-packets-rate {
           type int32;
           description
             "Rate at which number of total packets dropped at the queue";
         }
         leaf queue-counters-total-drop-bytes {
           type int32;
           description
             "Number of total bytes dropped at the queue";
         }
         leaf forwarding-class-name {
           type string;
           description
             "Forwarding class name associated with queue";
         }
         leaf queue-counters-queued-packets-rate {
           type int32;
           description
             "Rate at which packets are queued";
         }
         leaf queue-counters-queued-bytes {
           type int32;
           description
             "Queued bytes count";
         }
         leaf queue-counters-queued-bytes-rate {
           type int32;
           description
             "Rate at which bytes are queued";
         }
         leaf queue-counters-tail-drop-packets {
           type int32;
           description
             "Number of packets dropped at the tail of the queue";
         }
         leaf queue-counters-tail-drop-packets-rate {
           type int32;
           description
             "Rate at which packets are dropped at tail of queue";
         }
         leaf queue-counters-tail-drop-bytes {
           type int32;
           description
             "Number of bytes dropped at tail drop of the queue";
         }
         leaf queue-counters-tail-drop-bytes-rate {
           type int32;
           description
             "Rate at which number of bytes dropped at tail drop of the 
             queue";
         }
         leaf queue-counters-red-packets {
           type int32;
           description
             "Number of packets dropped due to RED";
         }
         leaf queue-counters-red-bytes {
           type int32;
           description
             "Number of bytes dropped due to RED";
         }
         leaf queue-counters-red-packets-rate {
           type int32;
           description
             "Rate at which packets are dropped due to RED";
         }
         leaf queue-counters-red-bytes-rate {
           type int32;
           description
             "Rate at which bytes are dropped due to RED";
         }
         leaf queue-counters-red-packets-low {
           type int32;
           description
             "Number of RED dropped low-loss packets";
         }
         leaf queue-counters-red-bytes-low {
           type int32;
           description
             "Number of RED dropped low-loss bytes";
         }
         leaf queue-counters-red-packets-rate-low {
           type int32;
           description
             "RED drop rate for low-loss packets";
         }
         leaf queue-counters-red-bytes-rate-low {
           type int32;
           description
             "RED drop rate for low-loss bytes";
         }
         leaf queue-counters-red-packets-medium-low {
           type int32;
           description
             "Number of RED dropped medium-low-loss packets";
         }
         leaf queue-counters-red-bytes-medium-low {
           type int32;
           description
             "Number of RED dropped medium-low-loss bytes";
         }
         leaf queue-counters-red-packets-rate-medium-low {
           type int32;
           description
             "RED drop rate for medium-low-loss packets";
         }
         leaf queue-counters-red-bytes-rate-medium-low {
           type int32;
           description
             "RED drop rate for medium-low-loss bytes";
         }
         leaf queue-counters-red-packets-medium-high {
           type int32;
           description
             "Number of RED dropped medium-high-loss packets";
         }
         leaf queue-counters-red-bytes-medium-high {
           type int32;
           description
             "Number of RED dropped medium-high-loss bytes";
         }
         leaf queue-counters-red-packets-rate-medium-high {
           type int32;
           description
             "RED drop rate for medium-high-loss packets";
         }
         leaf queue-counters-red-bytes-rate-medium-high {
           type int32;
           description
             "RED drop rate for medium-high-loss bytes";
         }
         leaf queue-counters-red-packets-medium {
           type int32;
           description
             "Number of RED dropped medium-loss packets";
         }
         leaf queue-counters-red-bytes-medium {
           type int32;
           description
             "Number of RED dropped medium-loss bytes";
         }
         leaf queue-counters-red-packets-rate-medium {
           type int32;
           description
             "RED drop rate for medium-loss packets";
         }
         leaf queue-counters-red-bytes-rate-medium {
           type int32;
           description
             "RED drop rate for medium-loss bytes";
         }
         leaf queue-counters-red-packets-high {
           type int32;
           description
             "Number of RED dropped high-loss packets";
         }
         leaf queue-counters-red-bytes-high {
           type int32;
           description
             "Number of RED dropped high-loss bytes";
         }
         leaf queue-counters-red-packets-rate-high {
           type int32;
           description
             "RED drop rate for high-loss packets";
         }
         leaf queue-counters-red-bytes-rate-high {
           type int32;
           description
             "RED drop rate for high-loss bytes";
         }
         leaf queue-counters-rate-limit-drop-packets {
           type int32;
           description
             "Number of packets dropped by rate-limit for the queue";
         }
         leaf queue-counters-rate-limit-drop-packets-rate {
           type int32;
           description
             "Rate at which packets are dropped by rate-limit for the queue";
         }
         leaf queue-counters-rate-limit-drop-bytes {
           type int32;
           description
             "Number of bytes dropped at the tail of the queue";
         }
         leaf queue-counters-rate-limit-drop-bytes-rate {
           type int32;
           description
             "Rate at which bytes are dropped at the tail of the queue";
         }
         container queue {
           leaf queue-number {
             type int32;
             description
               "Queue number";
           }
           leaf forwarding-class-name {
             type string;
             description
               "Forwarding class name associated with queue";
           }
           leaf queue-counters-queued-packets {
             type int32;
             description
               "Queued packet count";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-trans-packets {
             type int32;
             description
               "Total number of transmitted packets";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of bytes dropped at tail drop of the queue";
           }
           leaf queue-counters-tail-drop-bytes-rate {
             type int32;
             description
               "Rate at which number of bytes dropped at tail drop of the 
               queue";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets {
             type int32;
             description
               "Number of packets dropped due to RED";
           }
           leaf queue-counters-red-packets-rate {
             type int32;
             description
               "Rate at which packets are dropped due to RED";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-high {
             type int32;
             description
               "Number of RED dropped high-loss packets";
           }
           leaf queue-counters-red-packets-rate-high {
             type int32;
             description
               "RED drop rate for high-loss packets";
           }
           leaf queue-counters-red-bytes {
             type int32;
             description
               "Number of bytes dropped due to RED";
           }
           leaf queue-counters-red-bytes-rate {
             type int32;
             description
               "Rate at which bytes are dropped due to RED";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-high {
             type int32;
             description
               "Number of RED dropped high-loss bytes";
           }
           leaf queue-counters-red-bytes-rate-high {
             type int32;
             description
               "RED drop rate for high-loss bytes";
           }
           leaf queue-counters-red-packets-medium {
             type int32;
             description
               "Number of RED dropped medium-loss packets";
           }
           leaf queue-counters-red-bytes-medium {
             type int32;
             description
               "Number of RED dropped medium-loss bytes";
           }
           leaf queue-counters-red-packets-rate-medium {
             type int32;
             description
               "RED drop rate for medium-loss packets";
           }
           leaf queue-counters-red-bytes-rate-medium {
             type int32;
             description
               "RED drop rate for medium-loss bytes";
           }
         }
         container interface-cos-summary {
           description
             "Summary of queue information on an interface";
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
         }
       }
       list addr-family {
         container address-family-unnumbered {
           leaf unnumbered-family-donor-interface-name {
             type string;
             description
               "Donor interface name";
           }
           leaf unnumbered-family-donor-interface-index {
             type int32;
             description
               "Donor interface index";
           }
         }
         container interface-address {
           leaf name {
             type string;
             description
               "Name of this item";
           }
           leaf subunit {
             type int32;
             description
               "Subunit for this interface";
           }
           leaf admin-status {
             type string;
           }
           leaf oper-status {
             type string;
           }
           container ifa-flags {
             leaf ifaf-current-primary {
               type empty;
             }
             leaf ifaf-none {
               type empty;
             }
           }
         }
         container address-family-flags {
           leaf ifff-down {
             type empty;
           }
           leaf ifff-up {
             type empty;
           }
           leaf ifff-unnumbered {
             type empty;
           }
         }
         container pppoe-underlying-information {
           description
             "PPPoE underlying information";
           container pppoe-underlying-interface {
             leaf dynamic-profile {
               type string;
             }
             leaf service-name-table {
               type string;
             }
             leaf max-sessions {
               type int32;
             }
             leaf max-sessions-vsa-ignore {
               type string;
             }
             leaf duplicate-protection {
               type string;
             }
             leaf short-cycle-protection {
               type string;
             }
             leaf direct-connect {
               type string;
             }
             leaf ac-name {
               type string;
             }
           }
         }
       }
       container queue {
         leaf queue-counters-red-packets-medium {
           type int32;
           description
             "Number of RED dropped medium-loss packets";
         }
         leaf queue-counters-red-bytes-medium {
           type int32;
           description
             "Number of RED dropped medium-loss bytes";
         }
         leaf queue-counters-red-packets-rate-medium {
           type int32;
           description
             "RED drop rate for medium-loss packets";
         }
         leaf queue-counters-red-bytes-rate-medium {
           type int32;
           description
             "RED drop rate for medium-loss bytes";
         }
       }
       container pppoe-information {
         description
           "PPPoE information";
         container pppoe-interface {
           leaf state {
             type string;
           }
           leaf session-id {
             type int32;
           }
           leaf ac-name-session {
             type string;
           }
           leaf remote-mac {
             type string;
           }
           leaf underlying-interface-name {
             type string;
           }
           leaf underlying-interface-index {
             type int32;
           }
           leaf ignore-eol-tag {
             type string;
           }
         }
       }
       container demux-information {
         container demux-interface {
           leaf demux-underlying-interface-name {
             type string;
             description
               "Underlying interface name";
           }
           leaf demux-underlying-interface-index {
             type string;
             description
               "Underlying interface index";
           }
           leaf demux-inet-prefix-type {
             type string;
             description
               "Prefix type";
           }
           leaf demux-inet-prefix-count {
             type string;
             description
               "IPv4 prefix count";
           }
           leaf demux-inet-prefix {
             type string;
             description
               "IPv4 prefix";
           }
           leaf demux-inet6-prefix-type {
             type string;
             description
               "Prefix type";
           }
           leaf demux-inet6-prefix-count {
             type string;
             description
               "IPv6 prefix count";
           }
           leaf demux-inet6-prefix {
             type string;
             description
               "IPv6 prefix";
           }
         }
       }
     }
   }
   grouping subscribers-interfaces-information-block {
     list logical-interface {
       key "name address-family-name";
       description
         "Information about a single logical interface";
       leaf name {
         type string;
         description
           "Name of this item";
       }
       leaf subunit {
         type int32;
         description
           "Subunit for this interface";
       }
       leaf admin-status {
         type string;
       }
       leaf oper-status {
         type string;
       }
       leaf address-family-name {
         type string;
       }
       leaf ifa-local {
         type string;
         description
           "Protocol address on this interface";
       }
       leaf ifa-destination {
         type string;
         description
           "Protocol address of the remote side of this connection";
       }
       leaf state {
         type string;
       }
       leaf session-id {
         type int32;
       }
       leaf ac-name-session {
         type string;
       }
       leaf remote-mac {
         type string;
       }
       leaf underlying-interface-name {
         type string;
       }
       leaf underlying-interface-index {
         type int32;
       }
       leaf ignore-eol-tag {
         type string;
       }
       leaf intf-cos-queue-type {
         type string;
         description
           "Interface queue type";
       }
       leaf intf-cos-num-queues-supported {
         type int32;
         description
           "Number of queues supported on this interface";
       }
       leaf intf-cos-num-queues-in-use {
         type int32;
         description
           "Number of queues currently in use on this interface";
       }
       leaf input-bytes {
         type int32;
       }
       leaf output-bytes {
         type int32;
       }
       leaf input-packets {
         type int32;
       }
       leaf output-packets {
         type int32;
       }
       leaf input-bps {
         type int32;
       }
       leaf output-bps {
         type int32;
       }
       leaf input-pps {
         type int32;
       }
       leaf output-pps {
         type int32;
       }
       leaf hardware-token {
         type int32;
         description
           "Hardware token for layer 3 ifl";
       }
       container queue-counters {
         description
           "Queue counter statistics";
         leaf queue-number {
           type int32;
           description
             "Queue number";
         }
         leaf queue-counters-queued-packets {
           type int32;
           description
             "Queued packet count";
         }
         leaf queue-counters-trans-packets {
           type int32;
           description
             "Total number of transmitted packets";
         }
         leaf queue-counters-trans-packets-rate {
           type int32;
           description
             "Rate at which packets are transmitted";
         }
         leaf queue-counters-trans-bytes {
           type int32;
           description
             "Total number of transmitted bytes";
         }
         leaf queue-counters-trans-bytes-rate {
           type int32;
           description
             "Rate at which bytes are transmitted";
         }
         leaf queue-counters-total-drop-packets {
           type int32;
           description
             "Number of total packets dropped at the queue";
         }
         leaf queue-counters-total-drop-packets-rate {
           type int32;
           description
             "Rate at which number of total packets dropped at the queue";
         }
         leaf queue-counters-total-drop-bytes {
           type int32;
           description
             "Number of total bytes dropped at the queue";
         }
         leaf forwarding-class-name {
           type string;
           description
             "Forwarding class name associated with queue";
         }
         leaf queue-counters-queued-packets-rate {
           type int32;
           description
             "Rate at which packets are queued";
         }
         leaf queue-counters-queued-bytes {
           type int32;
           description
             "Queued bytes count";
         }
         leaf queue-counters-queued-bytes-rate {
           type int32;
           description
             "Rate at which bytes are queued";
         }
         leaf queue-counters-tail-drop-packets {
           type int32;
           description
             "Number of packets dropped at the tail of the queue";
         }
         leaf queue-counters-tail-drop-packets-rate {
           type int32;
           description
             "Rate at which packets are dropped at tail of queue";
         }
         leaf queue-counters-tail-drop-bytes {
           type int32;
           description
             "Number of bytes dropped at tail drop of the queue";
         }
         leaf queue-counters-tail-drop-bytes-rate {
           type int32;
           description
             "Rate at which number of bytes dropped at tail drop of the 
             queue";
         }
         leaf queue-counters-red-packets {
           type int32;
           description
             "Number of packets dropped due to RED";
         }
         leaf queue-counters-red-bytes {
           type int32;
           description
             "Number of bytes dropped due to RED";
         }
         leaf queue-counters-red-packets-rate {
           type int32;
           description
             "Rate at which packets are dropped due to RED";
         }
         leaf queue-counters-red-bytes-rate {
           type int32;
           description
             "Rate at which bytes are dropped due to RED";
         }
         leaf queue-counters-red-packets-low {
           type int32;
           description
             "Number of RED dropped low-loss packets";
         }
         leaf queue-counters-red-bytes-low {
           type int32;
           description
             "Number of RED dropped low-loss bytes";
         }
         leaf queue-counters-red-packets-rate-low {
           type int32;
           description
             "RED drop rate for low-loss packets";
         }
         leaf queue-counters-red-bytes-rate-low {
           type int32;
           description
             "RED drop rate for low-loss bytes";
         }
         leaf queue-counters-red-packets-medium-low {
           type int32;
           description
             "Number of RED dropped medium-low-loss packets";
         }
         leaf queue-counters-red-bytes-medium-low {
           type int32;
           description
             "Number of RED dropped medium-low-loss bytes";
         }
         leaf queue-counters-red-packets-rate-medium-low {
           type int32;
           description
             "RED drop rate for medium-low-loss packets";
         }
         leaf queue-counters-red-bytes-rate-medium-low {
           type int32;
           description
             "RED drop rate for medium-low-loss bytes";
         }
         leaf queue-counters-red-packets-medium-high {
           type int32;
           description
             "Number of RED dropped medium-high-loss packets";
         }
         leaf queue-counters-red-bytes-medium-high {
           type int32;
           description
             "Number of RED dropped medium-high-loss bytes";
         }
         leaf queue-counters-red-packets-rate-medium-high {
           type int32;
           description
             "RED drop rate for medium-high-loss packets";
         }
         leaf queue-counters-red-bytes-rate-medium-high {
           type int32;
           description
             "RED drop rate for medium-high-loss bytes";
         }
         leaf queue-counters-red-packets-medium {
           type int32;
           description
             "Number of RED dropped medium-loss packets";
         }
         leaf queue-counters-red-bytes-medium {
           type int32;
           description
             "Number of RED dropped medium-loss bytes";
         }
         leaf queue-counters-red-packets-rate-medium {
           type int32;
           description
             "RED drop rate for medium-loss packets";
         }
         leaf queue-counters-red-bytes-rate-medium {
           type int32;
           description
             "RED drop rate for medium-loss bytes";
         }
         leaf queue-counters-red-packets-high {
           type int32;
           description
             "Number of RED dropped high-loss packets";
         }
         leaf queue-counters-red-bytes-high {
           type int32;
           description
             "Number of RED dropped high-loss bytes";
         }
         leaf queue-counters-red-packets-rate-high {
           type int32;
           description
             "RED drop rate for high-loss packets";
         }
         leaf queue-counters-red-bytes-rate-high {
           type int32;
           description
             "RED drop rate for high-loss bytes";
         }
         leaf queue-counters-rate-limit-drop-packets {
           type int32;
           description
             "Number of packets dropped by rate-limit for the queue";
         }
         leaf queue-counters-rate-limit-drop-packets-rate {
           type int32;
           description
             "Rate at which packets are dropped by rate-limit for the queue";
         }
         leaf queue-counters-rate-limit-drop-bytes {
           type int32;
           description
             "Number of bytes dropped at the tail of the queue";
         }
         leaf queue-counters-rate-limit-drop-bytes-rate {
           type int32;
           description
             "Rate at which bytes are dropped at the tail of the queue";
         }
         container queue {
           leaf queue-number {
             type int32;
             description
               "Queue number";
           }
           leaf forwarding-class-name {
             type string;
             description
               "Forwarding class name associated with queue";
           }
           leaf queue-counters-queued-packets {
             type int32;
             description
               "Queued packet count";
           }
           leaf queue-counters-queued-packets-rate {
             type int32;
             description
               "Rate at which packets are queued";
           }
           leaf queue-counters-queued-bytes {
             type int32;
             description
               "Queued bytes count";
           }
           leaf queue-counters-queued-bytes-rate {
             type int32;
             description
               "Rate at which bytes are queued";
           }
           leaf queue-counters-trans-packets {
             type int32;
             description
               "Total number of transmitted packets";
           }
           leaf queue-counters-trans-packets-rate {
             type int32;
             description
               "Rate at which packets are transmitted";
           }
           leaf queue-counters-trans-bytes {
             type int32;
             description
               "Total number of transmitted bytes";
           }
           leaf queue-counters-trans-bytes-rate {
             type int32;
             description
               "Rate at which bytes are transmitted";
           }
           leaf queue-counters-tail-drop-packets {
             type int32;
             description
               "Number of packets dropped at the tail of the queue";
           }
           leaf queue-counters-tail-drop-packets-rate {
             type int32;
             description
               "Rate at which packets are dropped at tail of queue";
           }
           leaf queue-counters-tail-drop-bytes {
             type int32;
             description
               "Number of bytes dropped at tail drop of the queue";
           }
           leaf queue-counters-tail-drop-bytes-rate {
             type int32;
             description
               "Rate at which number of bytes dropped at tail drop of the 
               queue";
           }
           leaf queue-counters-rate-limit-drop-packets {
             type int32;
             description
               "Number of packets dropped by rate-limit for the queue";
           }
           leaf queue-counters-rate-limit-drop-packets-rate {
             type int32;
             description
               "Rate at which packets are dropped by rate-limit for the 
               queue";
           }
           leaf queue-counters-rate-limit-drop-bytes {
             type int32;
             description
               "Number of bytes dropped at the tail of the queue";
           }
           leaf queue-counters-rate-limit-drop-bytes-rate {
             type int32;
             description
               "Rate at which bytes are dropped at the tail of the queue";
           }
           leaf queue-counters-red-packets {
             type int32;
             description
               "Number of packets dropped due to RED";
           }
           leaf queue-counters-red-packets-rate {
             type int32;
             description
               "Rate at which packets are dropped due to RED";
           }
           leaf queue-counters-red-packets-low {
             type int32;
             description
               "Number of RED dropped low-loss packets";
           }
           leaf queue-counters-red-packets-rate-low {
             type int32;
             description
               "RED drop rate for low-loss packets";
           }
           leaf queue-counters-red-packets-medium-low {
             type int32;
             description
               "Number of RED dropped medium-low-loss packets";
           }
           leaf queue-counters-red-packets-rate-medium-low {
             type int32;
             description
               "RED drop rate for medium-low-loss packets";
           }
           leaf queue-counters-red-packets-medium-high {
             type int32;
             description
               "Number of RED dropped medium-high-loss packets";
           }
           leaf queue-counters-red-packets-rate-medium-high {
             type int32;
             description
               "RED drop rate for medium-high-loss packets";
           }
           leaf queue-counters-red-packets-high {
             type int32;
             description
               "Number of RED dropped high-loss packets";
           }
           leaf queue-counters-red-packets-rate-high {
             type int32;
             description
               "RED drop rate for high-loss packets";
           }
           leaf queue-counters-red-bytes {
             type int32;
             description
               "Number of bytes dropped due to RED";
           }
           leaf queue-counters-red-bytes-rate {
             type int32;
             description
               "Rate at which bytes are dropped due to RED";
           }
           leaf queue-counters-red-bytes-low {
             type int32;
             description
               "Number of RED dropped low-loss bytes";
           }
           leaf queue-counters-red-bytes-rate-low {
             type int32;
             description
               "RED drop rate for low-loss bytes";
           }
           leaf queue-counters-red-bytes-medium-low {
             type int32;
             description
               "Number of RED dropped medium-low-loss bytes";
           }
           leaf queue-counters-red-bytes-rate-medium-low {
             type int32;
             description
               "RED drop rate for medium-low-loss bytes";
           }
           leaf queue-counters-red-bytes-medium-high {
             type int32;
             description
               "Number of RED dropped medium-high-loss bytes";
           }
           leaf queue-counters-red-bytes-rate-medium-high {
             type int32;
             description
               "RED drop rate for medium-high-loss bytes";
           }
           leaf queue-counters-red-bytes-high {
             type int32;
             description
               "Number of RED dropped high-loss bytes";
           }
           leaf queue-counters-red-bytes-rate-high {
             type int32;
             description
               "RED drop rate for high-loss bytes";
           }
           leaf queue-counters-red-packets-medium {
             type int32;
             description
               "Number of RED dropped medium-loss packets";
           }
           leaf queue-counters-red-bytes-medium {
             type int32;
             description
               "Number of RED dropped medium-loss bytes";
           }
           leaf queue-counters-red-packets-rate-medium {
             type int32;
             description
               "RED drop rate for medium-loss packets";
           }
           leaf queue-counters-red-bytes-rate-medium {
             type int32;
             description
               "RED drop rate for medium-loss bytes";
           }
           leaf queue-counters-total-drop-packets {
             type int32;
             description
               "Number of total packets dropped at the queue";
           }
         }
         container interface-cos-summary {
           description
             "Summary of queue information on an interface";
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
         }
         container interface-cos-short-summary {
           description
             "Shot summary of queue information on an interface";
           leaf intf-cos-queue-type {
             type string;
             description
               "Interface queue type";
           }
           leaf intf-cos-num-queues-supported {
             type int32;
             description
               "Number of queues supported on this interface";
           }
           leaf intf-cos-num-queues-in-use {
             type int32;
             description
               "Number of queues currently in use on this interface";
           }
         }
       }
       list addr-family {
         container address-family-unnumbered {
           leaf unnumbered-family-donor-interface-name {
             type string;
             description
               "Donor interface name";
           }
           leaf unnumbered-family-donor-interface-index {
             type int32;
             description
               "Donor interface index";
           }
         }
         container interface-address {
           leaf name {
             type string;
             description
               "Name of this item";
           }
           leaf subunit {
             type int32;
             description
               "Subunit for this interface";
           }
           leaf admin-status {
             type string;
           }
           leaf oper-status {
             type string;
           }
           container ifa-flags {
             leaf ifaf-current-primary {
               type empty;
             }
             leaf ifaf-none {
               type empty;
             }
           }
           leaf ifa-local {
             type string;
             description
               "Protocol address on this interface";
           }
           leaf ifa-destination {
             type string;
             description
               "Protocol address of the remote side of this connection";
           }
           leaf ifa-broadcast {
             type string;
             description
               "Network broadcast address";
           }
           leaf generation {
             type int32;
             description
               "Generation number used to distinguish between successive 
               instances of this interface";
           }
         }
         container address-family-flags {
           leaf ifff-down {
             type empty;
           }
           leaf ifff-up {
             type empty;
           }
           leaf ifff-unnumbered {
             type empty;
           }
         }
         container pppoe-underlying-information {
           description
             "PPPoE underlying information";
           container pppoe-underlying-interface {
             leaf dynamic-profile {
               type string;
             }
             leaf service-name-table {
               type string;
             }
             leaf max-sessions {
               type int32;
             }
             leaf max-sessions-vsa-ignore {
               type string;
             }
             leaf duplicate-protection {
               type string;
             }
             leaf short-cycle-protection {
               type string;
             }
             leaf direct-connect {
               type string;
             }
             leaf ac-name {
               type string;
             }
           }
         }
         leaf address-family-name {
           type string;
         }
         leaf mtu {
           type int32;
           description
             "MTU size on this interface";
         }
         leaf max-local-cache {
           type uint32;
           description
             "Max local nh cache size";
         }
         leaf new-hold-limit {
           type uint32;
           description
             "Max limit on new unresolved nh";
         }
         leaf intf-curr-cnt {
           type uint32;
           description
             "Current nh total cache size on this interface";
         }
         leaf intf-unresolved-cnt {
           type uint32;
           description
             "Current new unresolved nh cache size on this interface";
         }
         leaf intf-dropcnt {
           type uint32;
           description
             "Current interface nh drop count";
         }
         leaf route-table {
           type int32;
         }
       }
       container queue {
         leaf queue-counters-red-packets-medium {
           type int32;
           description
             "Number of RED dropped medium-loss packets";
         }
         leaf queue-counters-red-bytes-medium {
           type int32;
           description
             "Number of RED dropped medium-loss bytes";
         }
         leaf queue-counters-red-packets-rate-medium {
           type int32;
           description
             "RED drop rate for medium-loss packets";
         }
         leaf queue-counters-red-bytes-rate-medium {
           type int32;
           description
             "RED drop rate for medium-loss bytes";
         }
       }
       container pppoe-information {
         description
           "PPPoE information";
         container pppoe-interface {
           leaf state {
             type string;
           }
           leaf session-id {
             type int32;
           }
           leaf ac-name-session {
             type string;
           }
           leaf remote-mac {
             type string;
           }
           leaf underlying-interface-name {
             type string;
           }
           leaf underlying-interface-index {
             type int32;
           }
           leaf ignore-eol-tag {
             type string;
           }
         }
       }
       container demux-information {
         container demux-interface {
           leaf demux-underlying-interface-name {
             type string;
             description
               "Underlying interface name";
           }
           leaf demux-underlying-interface-index {
             type string;
             description
               "Underlying interface index";
           }
           leaf demux-inet-prefix-type {
             type string;
             description
               "Prefix type";
           }
           leaf demux-inet-prefix-count {
             type string;
             description
               "IPv4 prefix count";
           }
           leaf demux-inet-prefix {
             type string;
             description
               "IPv4 prefix";
           }
           leaf demux-inet6-prefix-type {
             type string;
             description
               "Prefix type";
           }
           leaf demux-inet6-prefix-count {
             type string;
             description
               "IPv6 prefix count";
           }
           leaf demux-inet6-prefix {
             type string;
             description
               "IPv6 prefix";
           }
         }
       }
       leaf link-address {
         type string;
         description
           "Link address on this logical interface";
       }
       leaf encapsulation {
         type string;
         description
           "Encapsulation on the logical interface";
       }
       container if-config-flags {
         leaf iff-down {
           type empty;
         }
         leaf iff-up {
           type empty;
         }
         leaf iff-point-to-point {
           type empty;
         }
       }
       container pppoe-interface {
         leaf state {
           type string;
         }
         leaf session-id {
           type int32;
         }
         leaf ac-name-session {
           type string;
         }
         leaf remote-mac {
           type string;
         }
         leaf underlying-interface-name {
           type string;
         }
         leaf underlying-interface-index {
           type int32;
         }
         leaf ignore-eol-tag {
           type string;
         }
       }
       leaf local-index {
         type int32;
         description
           "Local kernel index for this interface";
       }
       leaf snmp-index {
         type int32;
         description
           "SNMP ifIndex for this interface";
       }
       leaf generation {
         type int32;
         description
           "Generation number used to distinguish between successive 
           instances of this interface";
       }
       container traffic-statistics {
         leaf input-bytes {
           type int32;
         }
         leaf output-bytes {
           type int32;
         }
         leaf input-packets {
           type int32;
         }
         leaf output-packets {
           type int32;
         }
       }
       container local-traffic-statistics {
         leaf input-bytes {
           type int32;
         }
         leaf output-bytes {
           type int32;
         }
         leaf input-packets {
           type int32;
         }
         leaf output-packets {
           type int32;
         }
       }
       container transit-traffic-statistics {
         leaf input-bytes {
           type int32;
         }
         leaf input-bps {
           type int32;
         }
         leaf output-bytes {
           type int32;
         }
         leaf output-bps {
           type int32;
         }
         leaf input-packets {
           type int32;
         }
         leaf input-pps {
           type int32;
         }
         leaf output-packets {
           type int32;
         }
         leaf output-pps {
           type int32;
         }
       }
     }
     container interface-set {
       leaf-list interface-set-member {
         type string;
       }
       leaf name {
         type string;
         description
           "Name of this item";
       }
       leaf interface-set-index {
         type int32;
       }
       leaf snmp-index {
         type int32;
         description
           "SNMP ifIndex for this interface";
       }
       container interface-set-member-list {
         leaf-list interface-set-member {
           type string;
         }
       }
     }
   }
   grouping subscribers-interfaces-queue-information-block {
     container queue-counters {
       description
         "Queue counter statistics";
       leaf queue-number {
         type int32;
         description
           "Queue number";
       }
       leaf queue-counters-queued-packets {
         type int32;
         description
           "Queued packet count";
       }
       leaf queue-counters-trans-packets {
         type int32;
         description
           "Total number of transmitted packets";
       }
       leaf queue-counters-trans-packets-rate {
         type int32;
         description
           "Rate at which packets are transmitted";
       }
       leaf queue-counters-trans-bytes {
         type int32;
         description
           "Total number of transmitted bytes";
       }
       leaf queue-counters-trans-bytes-rate {
         type int32;
         description
           "Rate at which bytes are transmitted";
       }
       leaf queue-counters-total-drop-packets {
         type int32;
         description
           "Number of total packets dropped at the queue";
       }
       leaf queue-counters-total-drop-packets-rate {
         type int32;
         description
           "Rate at which number of total packets dropped at the queue";
       }
       leaf queue-counters-total-drop-bytes {
         type int32;
         description
           "Number of total bytes dropped at the queue";
       }
       leaf forwarding-class-name {
         type string;
         description
           "Forwarding class name associated with queue";
       }
       leaf queue-counters-queued-packets-rate {
         type int32;
         description
           "Rate at which packets are queued";
       }
       leaf queue-counters-queued-bytes {
         type int32;
         description
           "Queued bytes count";
       }
       leaf queue-counters-queued-bytes-rate {
         type int32;
         description
           "Rate at which bytes are queued";
       }
       leaf queue-counters-tail-drop-packets {
         type int32;
         description
           "Number of packets dropped at the tail of the queue";
       }
       leaf queue-counters-tail-drop-packets-rate {
         type int32;
         description
           "Rate at which packets are dropped at tail of queue";
       }
       leaf queue-counters-tail-drop-bytes {
         type int32;
         description
           "Number of bytes dropped at tail drop of the queue";
       }
       leaf queue-counters-tail-drop-bytes-rate {
         type int32;
         description
           "Rate at which number of bytes dropped at tail drop of the queue";
       }
       leaf queue-counters-red-packets {
         type int32;
         description
           "Number of packets dropped due to RED";
       }
       leaf queue-counters-red-bytes {
         type int32;
         description
           "Number of bytes dropped due to RED";
       }
       leaf queue-counters-red-packets-rate {
         type int32;
         description
           "Rate at which packets are dropped due to RED";
       }
       leaf queue-counters-red-bytes-rate {
         type int32;
         description
           "Rate at which bytes are dropped due to RED";
       }
       leaf queue-counters-red-packets-low {
         type int32;
         description
           "Number of RED dropped low-loss packets";
       }
       leaf queue-counters-red-bytes-low {
         type int32;
         description
           "Number of RED dropped low-loss bytes";
       }
       leaf queue-counters-red-packets-rate-low {
         type int32;
         description
           "RED drop rate for low-loss packets";
       }
       leaf queue-counters-red-bytes-rate-low {
         type int32;
         description
           "RED drop rate for low-loss bytes";
       }
       leaf queue-counters-red-packets-medium-low {
         type int32;
         description
           "Number of RED dropped medium-low-loss packets";
       }
       leaf queue-counters-red-bytes-medium-low {
         type int32;
         description
           "Number of RED dropped medium-low-loss bytes";
       }
       leaf queue-counters-red-packets-rate-medium-low {
         type int32;
         description
           "RED drop rate for medium-low-loss packets";
       }
       leaf queue-counters-red-bytes-rate-medium-low {
         type int32;
         description
           "RED drop rate for medium-low-loss bytes";
       }
       leaf queue-counters-red-packets-medium-high {
         type int32;
         description
           "Number of RED dropped medium-high-loss packets";
       }
       leaf queue-counters-red-bytes-medium-high {
         type int32;
         description
           "Number of RED dropped medium-high-loss bytes";
       }
       leaf queue-counters-red-packets-rate-medium-high {
         type int32;
         description
           "RED drop rate for medium-high-loss packets";
       }
       leaf queue-counters-red-bytes-rate-medium-high {
         type int32;
         description
           "RED drop rate for medium-high-loss bytes";
       }
       leaf queue-counters-red-packets-medium {
         type int32;
         description
           "Number of RED dropped medium-loss packets";
       }
       leaf queue-counters-red-bytes-medium {
         type int32;
         description
           "Number of RED dropped medium-loss bytes";
       }
       leaf queue-counters-red-packets-rate-medium {
         type int32;
         description
           "RED drop rate for medium-loss packets";
       }
       leaf queue-counters-red-bytes-rate-medium {
         type int32;
         description
           "RED drop rate for medium-loss bytes";
       }
       leaf queue-counters-red-packets-high {
         type int32;
         description
           "Number of RED dropped high-loss packets";
       }
       leaf queue-counters-red-bytes-high {
         type int32;
         description
           "Number of RED dropped high-loss bytes";
       }
       leaf queue-counters-red-packets-rate-high {
         type int32;
         description
           "RED drop rate for high-loss packets";
       }
       leaf queue-counters-red-bytes-rate-high {
         type int32;
         description
           "RED drop rate for high-loss bytes";
       }
       leaf queue-counters-rate-limit-drop-packets {
         type int32;
         description
           "Number of packets dropped by rate-limit for the queue";
       }
       leaf queue-counters-rate-limit-drop-packets-rate {
         type int32;
         description
           "Rate at which packets are dropped by rate-limit for the queue";
       }
       leaf queue-counters-rate-limit-drop-bytes {
         type int32;
         description
           "Number of bytes dropped at the tail of the queue";
       }
       leaf queue-counters-rate-limit-drop-bytes-rate {
         type int32;
         description
           "Rate at which bytes are dropped at the tail of the queue";
       }
       container queue {
         leaf queue-number {
           type int32;
           description
             "Queue number";
         }
         leaf forwarding-class-name {
           type string;
           description
             "Forwarding class name associated with queue";
         }
         leaf queue-counters-queued-packets {
           type int32;
           description
             "Queued packet count";
         }
         leaf queue-counters-queued-packets-rate {
           type int32;
           description
             "Rate at which packets are queued";
         }
         leaf queue-counters-queued-bytes {
           type int32;
           description
             "Queued bytes count";
         }
         leaf queue-counters-queued-bytes-rate {
           type int32;
           description
             "Rate at which bytes are queued";
         }
         leaf queue-counters-trans-packets {
           type int32;
           description
             "Total number of transmitted packets";
         }
         leaf queue-counters-trans-packets-rate {
           type int32;
           description
             "Rate at which packets are transmitted";
         }
         leaf queue-counters-trans-bytes {
           type int32;
           description
             "Total number of transmitted bytes";
         }
         leaf queue-counters-trans-bytes-rate {
           type int32;
           description
             "Rate at which bytes are transmitted";
         }
         leaf queue-counters-tail-drop-packets {
           type int32;
           description
             "Number of packets dropped at the tail of the queue";
         }
         leaf queue-counters-tail-drop-packets-rate {
           type int32;
           description
             "Rate at which packets are dropped at tail of queue";
         }
         leaf queue-counters-tail-drop-bytes {
           type int32;
           description
             "Number of bytes dropped at tail drop of the queue";
         }
         leaf queue-counters-tail-drop-bytes-rate {
           type int32;
           description
             "Rate at which number of bytes dropped at tail drop of the 
             queue";
         }
         leaf queue-counters-rate-limit-drop-packets {
           type int32;
           description
             "Number of packets dropped by rate-limit for the queue";
         }
         leaf queue-counters-rate-limit-drop-packets-rate {
           type int32;
           description
             "Rate at which packets are dropped by rate-limit for the queue";
         }
         leaf queue-counters-rate-limit-drop-bytes {
           type int32;
           description
             "Number of bytes dropped at the tail of the queue";
         }
         leaf queue-counters-rate-limit-drop-bytes-rate {
           type int32;
           description
             "Rate at which bytes are dropped at the tail of the queue";
         }
         leaf queue-counters-red-packets {
           type int32;
           description
             "Number of packets dropped due to RED";
         }
         leaf queue-counters-red-packets-rate {
           type int32;
           description
             "Rate at which packets are dropped due to RED";
         }
         leaf queue-counters-red-packets-low {
           type int32;
           description
             "Number of RED dropped low-loss packets";
         }
         leaf queue-counters-red-packets-rate-low {
           type int32;
           description
             "RED drop rate for low-loss packets";
         }
         leaf queue-counters-red-packets-medium-low {
           type int32;
           description
             "Number of RED dropped medium-low-loss packets";
         }
         leaf queue-counters-red-packets-rate-medium-low {
           type int32;
           description
             "RED drop rate for medium-low-loss packets";
         }
         leaf queue-counters-red-packets-medium-high {
           type int32;
           description
             "Number of RED dropped medium-high-loss packets";
         }
         leaf queue-counters-red-packets-rate-medium-high {
           type int32;
           description
             "RED drop rate for medium-high-loss packets";
         }
         leaf queue-counters-red-packets-high {
           type int32;
           description
             "Number of RED dropped high-loss packets";
         }
         leaf queue-counters-red-packets-rate-high {
           type int32;
           description
             "RED drop rate for high-loss packets";
         }
         leaf queue-counters-red-bytes {
           type int32;
           description
             "Number of bytes dropped due to RED";
         }
         leaf queue-counters-red-bytes-rate {
           type int32;
           description
             "Rate at which bytes are dropped due to RED";
         }
         leaf queue-counters-red-bytes-low {
           type int32;
           description
             "Number of RED dropped low-loss bytes";
         }
         leaf queue-counters-red-bytes-rate-low {
           type int32;
           description
             "RED drop rate for low-loss bytes";
         }
         leaf queue-counters-red-bytes-medium-low {
           type int32;
           description
             "Number of RED dropped medium-low-loss bytes";
         }
         leaf queue-counters-red-bytes-rate-medium-low {
           type int32;
           description
             "RED drop rate for medium-low-loss bytes";
         }
         leaf queue-counters-red-bytes-medium-high {
           type int32;
           description
             "Number of RED dropped medium-high-loss bytes";
         }
         leaf queue-counters-red-bytes-rate-medium-high {
           type int32;
           description
             "RED drop rate for medium-high-loss bytes";
         }
         leaf queue-counters-red-bytes-high {
           type int32;
           description
             "Number of RED dropped high-loss bytes";
         }
         leaf queue-counters-red-bytes-rate-high {
           type int32;
           description
             "RED drop rate for high-loss bytes";
         }
         leaf queue-counters-red-packets-medium {
           type int32;
           description
             "Number of RED dropped medium-loss packets";
         }
         leaf queue-counters-red-bytes-medium {
           type int32;
           description
             "Number of RED dropped medium-loss bytes";
         }
         leaf queue-counters-red-packets-rate-medium {
           type int32;
           description
             "RED drop rate for medium-loss packets";
         }
         leaf queue-counters-red-bytes-rate-medium {
           type int32;
           description
             "RED drop rate for medium-loss bytes";
         }
       }
       container interface-cos-summary {
         description
           "Summary of queue information on an interface";
         leaf intf-cos-queue-type {
           type string;
           description
             "Interface queue type";
         }
         leaf intf-cos-num-queues-supported {
           type int32;
           description
             "Number of queues supported on this interface";
         }
         leaf intf-cos-num-queues-in-use {
           type int32;
           description
             "Number of queues currently in use on this interface";
         }
       }
     }
   }
   grouping subscribers-interface-set-queue-information-block {
     container queue-counters {
       description
         "Queue counter statistics";
       leaf queue-number {
         type int32;
         description
           "Queue number";
       }
       leaf queue-counters-queued-packets {
         type int32;
         description
           "Queued packet count";
       }
       leaf queue-counters-trans-packets {
         type int32;
         description
           "Total number of transmitted packets";
       }
       leaf queue-counters-trans-packets-rate {
         type int32;
         description
           "Rate at which packets are transmitted";
       }
       leaf queue-counters-trans-bytes {
         type int32;
         description
           "Total number of transmitted bytes";
       }
       leaf queue-counters-trans-bytes-rate {
         type int32;
         description
           "Rate at which bytes are transmitted";
       }
       leaf queue-counters-total-drop-packets {
         type int32;
         description
           "Number of total packets dropped at the queue";
       }
       leaf queue-counters-total-drop-packets-rate {
         type int32;
         description
           "Rate at which number of total packets dropped at the queue";
       }
       leaf queue-counters-total-drop-bytes {
         type int32;
         description
           "Number of total bytes dropped at the queue";
       }
       leaf forwarding-class-name {
         type string;
         description
           "Forwarding class name associated with queue";
       }
       leaf queue-counters-queued-packets-rate {
         type int32;
         description
           "Rate at which packets are queued";
       }
       leaf queue-counters-queued-bytes {
         type int32;
         description
           "Queued bytes count";
       }
       leaf queue-counters-queued-bytes-rate {
         type int32;
         description
           "Rate at which bytes are queued";
       }
       leaf queue-counters-tail-drop-packets {
         type int32;
         description
           "Number of packets dropped at the tail of the queue";
       }
       leaf queue-counters-tail-drop-packets-rate {
         type int32;
         description
           "Rate at which packets are dropped at tail of queue";
       }
       leaf queue-counters-tail-drop-bytes {
         type int32;
         description
           "Number of bytes dropped at tail drop of the queue";
       }
       leaf queue-counters-tail-drop-bytes-rate {
         type int32;
         description
           "Rate at which number of bytes dropped at tail drop of the queue";
       }
       leaf queue-counters-red-packets {
         type int32;
         description
           "Number of packets dropped due to RED";
       }
       leaf queue-counters-red-bytes {
         type int32;
         description
           "Number of bytes dropped due to RED";
       }
       leaf queue-counters-red-packets-rate {
         type int32;
         description
           "Rate at which packets are dropped due to RED";
       }
       leaf queue-counters-red-bytes-rate {
         type int32;
         description
           "Rate at which bytes are dropped due to RED";
       }
       leaf queue-counters-red-packets-low {
         type int32;
         description
           "Number of RED dropped low-loss packets";
       }
       leaf queue-counters-red-bytes-low {
         type int32;
         description
           "Number of RED dropped low-loss bytes";
       }
       leaf queue-counters-red-packets-rate-low {
         type int32;
         description
           "RED drop rate for low-loss packets";
       }
       leaf queue-counters-red-bytes-rate-low {
         type int32;
         description
           "RED drop rate for low-loss bytes";
       }
       leaf queue-counters-red-packets-medium-low {
         type int32;
         description
           "Number of RED dropped medium-low-loss packets";
       }
       leaf queue-counters-red-bytes-medium-low {
         type int32;
         description
           "Number of RED dropped medium-low-loss bytes";
       }
       leaf queue-counters-red-packets-rate-medium-low {
         type int32;
         description
           "RED drop rate for medium-low-loss packets";
       }
       leaf queue-counters-red-bytes-rate-medium-low {
         type int32;
         description
           "RED drop rate for medium-low-loss bytes";
       }
       leaf queue-counters-red-packets-medium-high {
         type int32;
         description
           "Number of RED dropped medium-high-loss packets";
       }
       leaf queue-counters-red-bytes-medium-high {
         type int32;
         description
           "Number of RED dropped medium-high-loss bytes";
       }
       leaf queue-counters-red-packets-rate-medium-high {
         type int32;
         description
           "RED drop rate for medium-high-loss packets";
       }
       leaf queue-counters-red-bytes-rate-medium-high {
         type int32;
         description
           "RED drop rate for medium-high-loss bytes";
       }
       leaf queue-counters-red-packets-medium {
         type int32;
         description
           "Number of RED dropped medium-loss packets";
       }
       leaf queue-counters-red-bytes-medium {
         type int32;
         description
           "Number of RED dropped medium-loss bytes";
       }
       leaf queue-counters-red-packets-rate-medium {
         type int32;
         description
           "RED drop rate for medium-loss packets";
       }
       leaf queue-counters-red-bytes-rate-medium {
         type int32;
         description
           "RED drop rate for medium-loss bytes";
       }
       leaf queue-counters-red-packets-high {
         type int32;
         description
           "Number of RED dropped high-loss packets";
       }
       leaf queue-counters-red-bytes-high {
         type int32;
         description
           "Number of RED dropped high-loss bytes";
       }
       leaf queue-counters-red-packets-rate-high {
         type int32;
         description
           "RED drop rate for high-loss packets";
       }
       leaf queue-counters-red-bytes-rate-high {
         type int32;
         description
           "RED drop rate for high-loss bytes";
       }
       leaf queue-counters-rate-limit-drop-packets {
         type int32;
         description
           "Number of packets dropped by rate-limit for the queue";
       }
       leaf queue-counters-rate-limit-drop-packets-rate {
         type int32;
         description
           "Rate at which packets are dropped by rate-limit for the queue";
       }
       leaf queue-counters-rate-limit-drop-bytes {
         type int32;
         description
           "Number of bytes dropped at the tail of the queue";
       }
       leaf queue-counters-rate-limit-drop-bytes-rate {
         type int32;
         description
           "Rate at which bytes are dropped at the tail of the queue";
       }
       container queue {
         leaf queue-number {
           type int32;
           description
             "Queue number";
         }
         leaf forwarding-class-name {
           type string;
           description
             "Forwarding class name associated with queue";
         }
         leaf queue-counters-queued-packets {
           type int32;
           description
             "Queued packet count";
         }
         leaf queue-counters-queued-packets-rate {
           type int32;
           description
             "Rate at which packets are queued";
         }
         leaf queue-counters-queued-bytes {
           type int32;
           description
             "Queued bytes count";
         }
         leaf queue-counters-queued-bytes-rate {
           type int32;
           description
             "Rate at which bytes are queued";
         }
         leaf queue-counters-trans-packets {
           type int32;
           description
             "Total number of transmitted packets";
         }
         leaf queue-counters-trans-packets-rate {
           type int32;
           description
             "Rate at which packets are transmitted";
         }
         leaf queue-counters-trans-bytes {
           type int32;
           description
             "Total number of transmitted bytes";
         }
         leaf queue-counters-trans-bytes-rate {
           type int32;
           description
             "Rate at which bytes are transmitted";
         }
         leaf queue-counters-tail-drop-packets {
           type int32;
           description
             "Number of packets dropped at the tail of the queue";
         }
         leaf queue-counters-tail-drop-packets-rate {
           type int32;
           description
             "Rate at which packets are dropped at tail of queue";
         }
         leaf queue-counters-tail-drop-bytes {
           type int32;
           description
             "Number of bytes dropped at tail drop of the queue";
         }
         leaf queue-counters-tail-drop-bytes-rate {
           type int32;
           description
             "Rate at which number of bytes dropped at tail drop of the 
             queue";
         }
         leaf queue-counters-rate-limit-drop-packets {
           type int32;
           description
             "Number of packets dropped by rate-limit for the queue";
         }
         leaf queue-counters-rate-limit-drop-packets-rate {
           type int32;
           description
             "Rate at which packets are dropped by rate-limit for the queue";
         }
         leaf queue-counters-rate-limit-drop-bytes {
           type int32;
           description
             "Number of bytes dropped at the tail of the queue";
         }
         leaf queue-counters-rate-limit-drop-bytes-rate {
           type int32;
           description
             "Rate at which bytes are dropped at the tail of the queue";
         }
         leaf queue-counters-red-packets {
           type int32;
           description
             "Number of packets dropped due to RED";
         }
         leaf queue-counters-red-packets-rate {
           type int32;
           description
             "Rate at which packets are dropped due to RED";
         }
         leaf queue-counters-red-packets-low {
           type int32;
           description
             "Number of RED dropped low-loss packets";
         }
         leaf queue-counters-red-packets-rate-low {
           type int32;
           description
             "RED drop rate for low-loss packets";
         }
         leaf queue-counters-red-packets-medium-low {
           type int32;
           description
             "Number of RED dropped medium-low-loss packets";
         }
         leaf queue-counters-red-packets-rate-medium-low {
           type int32;
           description
             "RED drop rate for medium-low-loss packets";
         }
         leaf queue-counters-red-packets-medium-high {
           type int32;
           description
             "Number of RED dropped medium-high-loss packets";
         }
         leaf queue-counters-red-packets-rate-medium-high {
           type int32;
           description
             "RED drop rate for medium-high-loss packets";
         }
         leaf queue-counters-red-packets-high {
           type int32;
           description
             "Number of RED dropped high-loss packets";
         }
         leaf queue-counters-red-packets-rate-high {
           type int32;
           description
             "RED drop rate for high-loss packets";
         }
         leaf queue-counters-red-bytes {
           type int32;
           description
             "Number of bytes dropped due to RED";
         }
         leaf queue-counters-red-bytes-rate {
           type int32;
           description
             "Rate at which bytes are dropped due to RED";
         }
         leaf queue-counters-red-bytes-low {
           type int32;
           description
             "Number of RED dropped low-loss bytes";
         }
         leaf queue-counters-red-bytes-rate-low {
           type int32;
           description
             "RED drop rate for low-loss bytes";
         }
         leaf queue-counters-red-bytes-medium-low {
           type int32;
           description
             "Number of RED dropped medium-low-loss bytes";
         }
         leaf queue-counters-red-bytes-rate-medium-low {
           type int32;
           description
             "RED drop rate for medium-low-loss bytes";
         }
         leaf queue-counters-red-bytes-medium-high {
           type int32;
           description
             "Number of RED dropped medium-high-loss bytes";
         }
         leaf queue-counters-red-bytes-rate-medium-high {
           type int32;
           description
             "RED drop rate for medium-high-loss bytes";
         }
         leaf queue-counters-red-bytes-high {
           type int32;
           description
             "Number of RED dropped high-loss bytes";
         }
         leaf queue-counters-red-bytes-rate-high {
           type int32;
           description
             "RED drop rate for high-loss bytes";
         }
         leaf queue-counters-red-packets-medium {
           type int32;
           description
             "Number of RED dropped medium-loss packets";
         }
         leaf queue-counters-red-bytes-medium {
           type int32;
           description
             "Number of RED dropped medium-loss bytes";
         }
         leaf queue-counters-red-packets-rate-medium {
           type int32;
           description
             "RED drop rate for medium-loss packets";
         }
         leaf queue-counters-red-bytes-rate-medium {
           type int32;
           description
             "RED drop rate for medium-loss bytes";
         }
       }
       container interface-cos-summary {
         description
           "Summary of queue information on an interface";
         leaf intf-cos-queue-type {
           type string;
           description
             "Interface queue type";
         }
         leaf intf-cos-num-queues-supported {
           type int32;
           description
             "Number of queues supported on this interface";
         }
         leaf intf-cos-num-queues-in-use {
           type int32;
           description
             "Number of queues currently in use on this interface";
         }
       }
     }
   }
   grouping firewall-information-block {
     list filter-information {
       key "filter-name";
       description
         "Details of a firewall filter";
       leaf filter-name {
         type string;
         description
           "Name of filter";
       }
       leaf user-plane-name {
         type string;
         description
           "Name of the User Plane";
       }
       container error-status {
         leaf status {
           type string;
           description
             "Error status of the filter";
         }
       }
       list bind-error-status {
         leaf-list bind-name {
           type string;
           description
             "Error status of the filter bind point";
         }
       }
       list counter {
         key "counter-name";
         description
           "Counter information";
         leaf counter-name {
           type string;
           description
             "Counter name";
         }
         leaf byte-count {
           type uint64;
           description
             "Bytes counted";
         }
         leaf packet-count {
           type uint64;
           description
             "Packets counted";
         }
       }
       list policer {
         key "policer-name";
         description
           "Policer information";
         leaf policer-name {
           type string;
           description
             "Name of this policer";
         }
         leaf byte-count {
           type uint64;
           description
             "Bytes counted";
         }
         leaf packet-count {
           type uint64;
           description
             "Packets counted";
         }
       }
       list enhanced-hierarchical-policer {
         description
           "Hierarchical Policer information";
         leaf policer-name {
           type string;
           description
             "Name of this policer";
         }
         leaf byte-count-high {
           type uint64;
           description
             "Bytes counted";
         }
         leaf packet-count-high {
           type uint64;
           description
             "Packets counted";
         }
         leaf byte-count-medium-high {
           type uint64;
           description
             "Bytes counted";
         }
         leaf packet-count-medium-high {
           type uint64;
           description
             "Packets counted";
         }
         leaf byte-count-medium-low {
           type uint64;
           description
             "Bytes counted";
         }
         leaf packet-count-medium-low {
           type uint64;
           description
             "Packets counted";
         }
         leaf byte-count-low {
           type uint64;
           description
             "Bytes counted";
         }
         leaf packet-count-low {
           type uint64;
           description
             "Packets counted";
         }
         leaf packet-count {
           type uint64;
           description
             "Packets counted";
         }
         leaf byte-count {
           type uint64;
           description
             "Bytes counted";
         }
       }
       list filter-version {
         key "filter-name";
         description
           "Filter version information";
         leaf filter-name {
           type string;
           description
             "Name of filter";
         }
         leaf version {
           type uint32;
           description
             "Filter version";
         }
       }
     }
     list user-plane-filter-information {
       key "filter-name";
       description
         "Details of a user-plane firewall filter";
       leaf filter-name {
         type string;
         description
           "Name of filter";
       }
       leaf user-plane-name {
         type string;
         description
           "Name of the User Plane";
       }
       list counter {
         key "counter-name";
         description
           "Counter information";
         leaf counter-name {
           type string;
           description
             "Counter name";
         }
         leaf byte-count {
           type uint64;
           description
             "Bytes counted";
         }
         leaf packet-count {
           type uint64;
           description
             "Packets counted";
         }
       }
       list enhanced-hierarchical-policer-userplane {
         description
           "Enhanced Hierarchical Policer information";
         leaf policer-name {
           type string;
           description
             "Name of this policer";
         }
         leaf byte-count-high {
           type uint64;
           description
             "Bytes counted";
         }
         leaf packet-count-high {
           type uint64;
           description
             "Packets counted";
         }
         leaf byte-count-medium-high {
           type uint64;
           description
             "Bytes counted";
         }
         leaf packet-count-medium-high {
           type uint64;
           description
             "Packets counted";
         }
         leaf byte-count-medium-low {
           type uint64;
           description
             "Bytes counted";
         }
         leaf packet-count-medium-low {
           type uint64;
           description
             "Packets counted";
         }
         leaf byte-count-low {
           type uint64;
           description
             "Bytes counted";
         }
         leaf packet-count-low {
           type uint64;
           description
             "Packets counted";
         }
         leaf packet-count {
           type uint64;
           description
             "Packets counted";
         }
         leaf byte-count {
           type uint64;
           description
             "Bytes counted";
         }
       }
       list filter-version {
         key "filter-name";
         description
           "Filter version information";
         leaf filter-name {
           type string;
           description
             "Name of filter";
         }
         leaf version {
           type uint32;
           description
             "Filter version";
         }
       }
     }
     list subscribers-filter-information {
       key "filter-name";
       description
         "Details of subscribers firewall filter";
       leaf filter-name {
         type string;
         description
           "Name of filter";
       }
       leaf user-plane-name {
         type string;
         description
           "Name of the User Plane";
       }
       list counter {
         key "counter-name";
         description
           "Counter information";
         leaf counter-name {
           type string;
           description
             "Counter name";
         }
         leaf byte-count {
           type uint64;
           description
             "Bytes counted";
         }
         leaf packet-count {
           type uint64;
           description
             "Packets counted";
         }
       }
       list enhanced-hierarchical-policer-userplane {
         description
           "Enhanced Hierarchical Policer information";
         leaf policer-name {
           type string;
           description
             "Name of this policer";
         }
         leaf byte-count-high {
           type uint64;
           description
             "Bytes counted";
         }
         leaf packet-count-high {
           type uint64;
           description
             "Packets counted";
         }
         leaf byte-count-medium-high {
           type uint64;
           description
             "Bytes counted";
         }
         leaf packet-count-medium-high {
           type uint64;
           description
             "Packets counted";
         }
         leaf byte-count-medium-low {
           type uint64;
           description
             "Bytes counted";
         }
         leaf packet-count-medium-low {
           type uint64;
           description
             "Packets counted";
         }
         leaf byte-count-low {
           type uint64;
           description
             "Bytes counted";
         }
         leaf packet-count-low {
           type uint64;
           description
             "Packets counted";
         }
         leaf packet-count {
           type uint64;
           description
             "Packets counted";
         }
         leaf byte-count {
           type uint64;
           description
             "Bytes counted";
         }
       }
       list filter-version {
         key "filter-name";
         description
           "Filter version information";
         leaf filter-name {
           type string;
           description
             "Name of filter";
         }
         leaf version {
           type uint32;
           description
             "Filter version";
         }
       }
     }
   }
   grouping firewall-log-information-block {
     list log-information {
       key "filter-name";
       description
         "Details of a single firewall log entry";
       leaf time {
         type string;
         description
           "Time of log";
       }
       leaf filter-name {
         type string;
         description
           "Name of filter";
       }
       leaf action-name {
         type string;
         description
           "Filter action";
       }
       leaf interface-name {
         type string;
         description
           "Name of interface";
       }
       leaf protocol-name {
         type string;
         description
           "Name of protocol";
       }
       leaf source-address {
         type string;
         description
           "Source address";
       }
       leaf destination-address {
         type string;
         description
           "Destination address";
       }
       leaf packet-length {
         type int32;
         description
           "Packet length";
       }
       leaf icmp-type {
         type int32;
         description
           "ICMP type";
       }
       leaf icmp-code {
         type int32;
         description
           "ICMP code";
       }
       leaf hex-dump-line {
         type string;
         description
           "Packet in Hex format";
       }
       leaf hex-dump-line1 {
         type string;
         description
           "Packet in Hex format";
       }
       leaf hex-dump-line2 {
         type string;
         description
           "Packet in Hex format";
       }
       leaf hex-dump-line3 {
         type string;
         description
           "Packet in Hex format";
       }
       leaf hex-dump-line4 {
         type string;
         description
           "Packet in Hex format";
       }
       leaf hex-dump-line5 {
         type string;
         description
           "Packet in Hex format";
       }
       leaf hex-dump-line6 {
         type string;
         description
           "Packet in Hex format";
       }
       leaf hex-dump-line7 {
         type string;
         description
           "Packet in Hex format";
       }
     }
   }
   grouping firewall-prefix-action-information-block {
     leaf filter-name {
       type string;
       description
         "Name of filter";
     }
     list counter {
       key "counter-name";
       description
         "Counter information";
       leaf counter-name {
         type string;
         description
           "Counter name";
       }
       leaf byte-count {
         type uint64;
         description
           "Bytes counted";
       }
       leaf packet-count {
         type uint64;
         description
           "Packets counted";
       }
     }
     list policer {
       key "policer-name";
       description
         "Policer information";
       leaf policer-name {
         type string;
         description
           "Name of this policer";
       }
       leaf byte-count {
         type uint64;
         description
           "Bytes counted";
       }
       leaf packet-count {
         type uint64;
         description
           "Packets counted";
       }
     }
   }
 }
