/*
 * Copyright (c) 2026 Juniper Networks, Inc.
 * All rights reserved.
 */
 module junos-rpc-ppp {
   namespace "http://yang.juniper.net/junos/rpc/ppp";

   prefix ppp;

   import junos-common-types {
     prefix jt;
     revision-date 2026-01-01;
   }

   organization "Juniper Networks, Inc.";

   contact "yang-support@juniper.net";

   description "Junos RPC YANG module for ppp command(s)";

   revision 2026-01-01 {
     description "Junos: 26.2R1.7-EVO";
   }

   rpc get-ppp-address-pool-inforamation {
     description "Show PPP address pool information";
     input {
       leaf control-plane-instance {
         description "Control plane instance name";
         type string;
         mandatory true;
       }
       leaf detail {
         description "Display detailed information";
         type empty;
       }
       leaf pool-name {
         description "Address pool name";
         type string;
         mandatory true;
       }
     }
     output {
       choice output-tags {
         case actual-tag {
           container ppp-address-pool-information {
             uses ppp-address-pool-information-block;
           }
         }
         case multichassis-tag {
           container multi-routing-engine-results {
             list multi-routing-engine-item {
               leaf re-name {
                 type string;
               }
               choice output-tags {
                 case actual-tag {
                   container ppp-address-pool-information {
                     uses ppp-address-pool-information-block;
                   }
                 }
               }
             }
           }
         }
       }
     }
   }
   rpc get-ppp-interface-information {
     description "Show PPP interface information";
     input {
       leaf control-plane-instance {
         description "Control plane instance name";
         type string;
         mandatory true;
       }
       leaf interface-name {
         description "Interface name";
         type string;
         mandatory true;
       }
       leaf display-style {
         description "Display style";
         type enumeration {
           enum "extensive" {
             description "Display detailed output";
           }
           enum "terse" {
             description "Display terse output";
           }
         }
       }
     }
     output {
       choice output-tags {
         case actual-tag {
           container ppp-interface-information {
             uses ppp-interface-information-block;
           }
         }
         case multichassis-tag {
           container multi-routing-engine-results {
             list multi-routing-engine-item {
               leaf re-name {
                 type string;
               }
               choice output-tags {
                 case actual-tag {
                   container ppp-interface-information {
                     uses ppp-interface-information-block;
                   }
                 }
               }
             }
           }
         }
       }
     }
   }
   rpc get-ppp-statistics-information {
     description "Show PPP statistics";
     input {
       leaf control-plane-instance {
         description "Control plane instance name";
         type string;
         mandatory true;
       }
       leaf level {
         description "Level of detail to display";
         type enumeration {
           enum "detail" {
             description "Display detailed statistics";
           }
           enum "memory" {
             description "Display PPP process memory statistics";
           }
           enum "recovery" {
             description "Display PPP process recovery statistics";
           }
           enum "extensive" {
             description "Display extensive statistics";
           }
         }
       }
     }
     output {
       choice output-tags {
         case actual-tag {
           container ppp-statistics-information {
             uses ppp-statistics-information-block;
           }
         }
         case multichassis-tag {
           container multi-routing-engine-results {
             list multi-routing-engine-item {
               leaf re-name {
                 type string;
               }
               choice output-tags {
                 case actual-tag {
                   container ppp-statistics-information {
                     uses ppp-statistics-information-block;
                   }
                 }
               }
             }
           }
         }
       }
     }
   }
   rpc get-ppp-summary-information {
     description "Show PPP summary information";
     input {
       leaf control-plane-instance {
         description "Control plane instance name";
         type string;
         mandatory true;
       }
     }
     output {
       choice output-tags {
         case actual-tag {
           container ppp-summary-information {
             uses ppp-summary-information-block;
           }
         }
         case multichassis-tag {
           container multi-routing-engine-results {
             list multi-routing-engine-item {
               leaf re-name {
                 type string;
               }
               choice output-tags {
                 case actual-tag {
                   container ppp-summary-information {
                     uses ppp-summary-information-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping ppp-address-pool-information-block {
     leaf pool-name {
       type string;
       description
         "Name of pool from which addresses are assigned";
     }
     leaf configured-addresses {
       type uint32;
       description
         "Number of configured addresses";
     }
     leaf assigned-addresses {
       type uint32;
       description
         "Number of assigned addresses";
     }
     container pool-range {
       description
         "Range of addresses in pool";
       leaf low-address {
         type jt:ipaddr;
         description
           "Low range of address pool";
       }
       leaf high-address {
         type jt:ipaddr;
         description
           "High range of address pool";
       }
     }
     container pool-address-list {
       description
         "List of addresses in pool";
       leaf pool-address {
         type jt:ipaddr;
         description
           "Address in pool";
       }
     }
     container assigned-address-list {
       description
         "List of addresses assigned in pool";
       list pool-address-assignment {
         description
           "Assignment information for one address in the pool";
         leaf pool-address {
           type jt:ipaddr;
           description
             "Address in pool";
         }
         leaf session-name {
           type string;
           description
             "PPP session name";
         }
         leaf pool-address-blocked {
           type empty;
           description
             "Address is already in use by a local interface";
         }
       }
     }
   }
   grouping ppp-interface-information-block {
     list ppp-session {
       description
         "PPP session";
       leaf session-name {
         type string;
         description
           "PPP session name";
       }
       leaf session-type {
         type string;
         description
           "PPP session type";
       }
       leaf session-phase {
         type string;
         description
           "PPP session phase";
       }
       leaf ppp-last-started {
         type string;
         description
           "Time when negotiation of the protocol last started, in theformat
           YYYY-MM-DD hh:mm:ss TZ (year, month, date, hour in24-hour 
           format, minute second, time zone)";
       }
       leaf ppp-last-completed {
         type string;
         description
           "Time when negotiation of the protocol last 
           completedsuccessfully, in the format YYYY-MM-DD hh:mm:ss TZ 
           (year,month, date, hour in 24-hour format, minute second, 
           timezone)";
       }
       leaf ppp-last-updated {
         type string;
         description
           "Time when negotiation of the protocol last updatedsuccessfully, 
           in the format YYYY-MM-DD hh:mm:ss TZ (year,month, date, hour in 
           24-hour format, minute second, timezone)";
       }
       container session-flags {
         description
           "PPP session flags";
         leaf session-bundled {
           type empty;
           description
             "Session is part of a multilink bundle";
         }
         leaf session-ncp-only {
           type empty;
           description
             "Session only negotiates Network Control Protocol";
         }
         leaf session-always-up {
           type empty;
           description
             "Session is always up";
         }
         leaf session-tcc {
           type empty;
           description
             "Session is a translational cross-connect";
         }
         leaf session-looped {
           type empty;
           description
             "Session has detected a loop";
         }
         leaf session-monitored {
           type empty;
           description
             "Session packet exchange is being monitored";
         }
       }
       container ppp-auth-protocol-information {
         description
           "Authentication protocol information for PPP session";
         leaf ppp-auth-proto {
           type string;
         }
         leaf ppp-state {
           type string;
           description
             "Protocol state";
         }
         leaf ppp-last-started {
           type string;
           description
             "Time when negotiation of the protocol last started, in 
             theformat YYYY-MM-DD hh:mm:ss TZ (year, month, date, hour 
             in24-hour format, minute second, time zone)";
         }
         leaf ppp-last-completed {
           type string;
           description
             "Time when negotiation of the protocol last 
             completedsuccessfully, in the format YYYY-MM-DD hh:mm:ss TZ 
             (year,month, date, hour in 24-hour format, minute second, 
             timezone)";
         }
       }
       list ppp-session-protocol-information {
         description
           "LCP/NCP protocol information for PPP session";
         leaf ppp-protocol {
           type string;
           description
             "Protocol value";
         }
         leaf ppp-state {
           type string;
           description
             "Protocol state";
         }
         container ppp-destination-profile {
           description
             "Destination profile information";
           leaf pool-name {
             type string;
             description
               "Name of pool from which addresses are assigned";
           }
         }
         container ppp-negotiated-options {
           description
             "PPP options negotiated with the remote peer";
           leaf ipcp-compression-protocol {
             type empty;
             description
               "Compression protocol Internet Protocol Control Protocol 
               option";
           }
           leaf ipcp-primary-dns {
             type jt:ipaddr;
             description
               "Internet Protocol Control Protocol primary domain name 
               server option";
           }
           leaf ipcp-primary-wins {
             type jt:ipaddr;
             description
               "Internet Protocol Control Protocol primary WINS option";
           }
           leaf ipcp-secondary-dns {
             type jt:ipaddr;
             description
               "Internet Protocol Control Protocol secondary domain name 
               server option";
           }
           leaf ipcp-secondary-wins {
             type jt:ipaddr;
             description
               "Internet Protocol Control Protocol secondary WINS option";
           }
           leaf bcp-mac-support {
             type string;
             description
               "Supported MAC type information conveyed to the remote peer";
           }
           leaf bcp-tagged-frame {
             type string;
             description
               "BCP tagging support information conveyed to the remote peer";
           }
           leaf lcp-address-compression-field-compression {
             type empty;
             description
               "Link Control Protocol address compression/field compression 
               option";
           }
           leaf lcp-protocol-field-compression {
             type empty;
             description
               "Link Control Protocol protocol/field compression option";
           }
           leaf lcp-async-map {
             type empty;
             description
               "Link Control Protocol asynchronous map option";
           }
           leaf lcp-short-sequence {
             type empty;
             description
               "Link Control Protocol short sequence option";
           }
           leaf lcp-magic-number {
             type uint32;
             description
               "Link Control Protocol magic number option";
           }
           leaf lcp-mrru {
             type uint32;
             description
               "Link Control Protocol maximum reconstructed receive unit 
               option";
           }
           leaf lcp-initial-advertised-mru {
             type uint32;
             description
               "Initial Advertised Link Control Protocol maximum receive 
               unit option";
           }
           leaf lcp-mru {
             type uint32;
             description
               "Link Control Protocol maximum receive unit option";
           }
           leaf lcp-peer-mrru {
             type uint32;
             description
               "Peer Link Control Protocol maximum reconstructed receive 
               unit option";
           }
           leaf lcp-peer-mru {
             type uint32;
             description
               "Peer Link Control Protocol maximum receive unit option";
           }
           leaf lcp-connection-status-msg {
             type string;
             description
               " Juniper Lcp connection status message ";
           }
           leaf lcp-connection-update-reqctr {
             type uint32;
             description
               "Indicates number of discrete events when lcp connection 
               update request was attempted";
           }
           container ipcp-address {
             description
               "Negotiated IP address Internet Protocol Control Protocol 
               option";
             leaf local-address {
               type jt:ipaddr;
               description
                 "Local interface address negotiated with remote peer";
             }
             leaf remote-address {
               type jt:ipaddr;
               description
                 "Destination address negotiated with remote peer";
             }
           }
           container ipv6cp-interface-identifier {
             description
               "Negotiated Internet Protocol Version 6 Control Protocol 
               interface identifier option";
             leaf local-interface-identifier {
               type string;
               description
                 "Local interface identifier negotiated with remote peer";
             }
             leaf remote-interface-identifier {
               type string;
               description
                 "Remote interface identifier negotiated with remote peer";
             }
           }
           container lcp-authentication-protocol {
             description
               "Link Control Protocol authentication protocol option";
             leaf authentication-protocol-name {
               type string;
               description
                 "Name of authentication protocol";
             }
             leaf authentication-algorithm {
               type string;
               description
                 "Authentication algorithm identifier";
             }
           }
           container lcp-endpoint-discriminator {
             description
               "Link Control Protocol endpoint discriminator option";
             leaf endpoint-discriminator-class {
               type string;
               description
                 "Endpoint discriminator class";
             }
             leaf endpoint-discriminator-identifier {
               type string;
               description
                 "Endpoint discriminator identifier";
             }
           }
           container lcp-multilink-header {
             description
               "Link Control Protocol multilink header format option";
             leaf multilink-header-code {
               type uint32;
               description
                 "Multilink header format code";
             }
             leaf multilink-header-suspendable-classes {
               type uint32;
               description
                 "Number of suspendable classes";
             }
           }
         }
         leaf ppp-last-started {
           type string;
           description
             "Time when negotiation of the protocol last started, in 
             theformat YYYY-MM-DD hh:mm:ss TZ (year, month, date, hour 
             in24-hour format, minute second, time zone)";
         }
         leaf ppp-last-completed {
           type string;
           description
             "Time when negotiation of the protocol last 
             completedsuccessfully, in the format YYYY-MM-DD hh:mm:ss TZ 
             (year,month, date, hour in 24-hour format, minute second, 
             timezone)";
         }
         leaf ppp-last-updated {
           type string;
           description
             "Time when negotiation of the protocol last 
             updatedsuccessfully, in the format YYYY-MM-DD hh:mm:ss TZ 
             (year,month, date, hour in 24-hour format, minute second, 
             timezone)";
         }
         leaf ppp-negotiation-mode {
           type string;
           description
             "PPP options negotiatiation mode with the remote peer";
         }
       }
     }
     leaf interface-name {
       type string;
       description
         "Interface name";
     }
   }
   grouping ppp-statistics-information-block {
     container ppp-session-statistics {
       description
         "PPP session statistics";
       leaf sessions-total {
         type uint32;
         description
           "Total number of sessions";
       }
       leaf sessions-disabled {
         type uint32;
         description
           "Number of sessions in disabled phase";
       }
       leaf sessions-establish {
         type uint32;
         description
           "Number of sessions in establishment phase";
       }
       leaf sessions-authenticate {
         type uint32;
         description
           "Number of session in authenticate phase";
       }
       leaf sessions-network {
         type uint32;
         description
           "Number of session in network phase";
       }
       leaf bundles-pending {
         type uint32;
         description
           "Number of multilink bundles with links waiting";
       }
       leaf sessions-ppp {
         type uint32;
         description
           "Total number of PPP sessions";
       }
       leaf sessions-ciscohdlc {
         type uint32;
         description
           "Total number of Cisco-HDLC sessions";
       }
     }
     container ppp-memory-statistics {
       description
         "PPP process memory statistics";
       list ppp-memory-tag {
         description
           "Tag associated with memory blocks";
         leaf ppp-memory-tag-name {
           type string;
           description
             "Name of memory tag";
         }
         leaf ppp-memory-tag-size {
           type uint32;
           description
             "Number of bytes of tagged memory allocated";
         }
         leaf ppp-memory-tag-active {
           type uint32;
           description
             "Number of active memory blocks";
         }
         leaf ppp-memory-tag-free {
           type uint32;
           description
             "Number of memory blocks on the free list";
         }
         leaf ppp-memory-tag-maximum-free {
           type uint32;
           description
             "Maximum number of memory blocks allowed on the free list";
         }
         leaf ppp-memory-tag-total {
           type uint32;
           description
             "Total number of bytes of memory allocated by the memory tag";
         }
         leaf ppp-memory-tag-requests {
           type uint32;
           description
             "Number of successful memory allocation requests";
         }
         leaf ppp-memory-tag-failures {
           type uint32;
           description
             "Number of failed memory allocation requests";
         }
       }
     }
     container ppp-subscriber-statistics {
       description
         "PPP subscriber statistics";
       container ppp-subscriber-session-statistics {
         description
           "PPP subscriber session statistics";
         leaf subscriber-sessions-total {
           type uint32;
           description
             "Total number of subscriber sessions";
         }
         leaf subscriber-sessions-disabled {
           type uint32;
           description
             "Number of subscriber sessions in disabled phase";
         }
         leaf subscriber-sessions-establish {
           type uint32;
           description
             "Number of subscriber sessions in establishment phase";
         }
         leaf subscriber-sessions-authenticate {
           type uint32;
           description
             "Number of subscriber sessions in authenticate phase";
         }
         leaf subscriber-sessions-network {
           type uint32;
           description
             "Number of subscriber sessions in network phase";
         }
       }
       container ppp-subscriber-recovery-statistics {
         description
           "PPP subscriber recovery statistics";
         leaf subscriber-recovery-state {
           type string;
           description
             "Current recovery state of PPP universal edge process";
         }
         leaf subscriber-sessions-recovery-pending-retention {
           type uint32;
           description
             "Number of subscriber sessions for which retention is pending";
         }
         leaf subscriber-sessions-recovery-pending-removal {
           type uint32;
           description
             "Number of subscriber sessions for which removal is pending";
         }
         leaf subscriber-sessions-recovery-ok {
           type uint32;
           description
             "Number of subscriber sessions for which recovery succeeded";
         }
         leaf subscriber-sessions-recovery-failed {
           type uint32;
           description
             "Number of subscriber sessions for which recovery failed";
         }
       }
       container ppp-subscriber-memory-statistics {
         description
           "PPP universal edge process memory statistics";
         list ppp-subscriber-memory-pool {
           description
             "Tag associated with memory blocks";
           leaf ppp-subscriber-memory-pool-name {
             type string;
             description
               "Name of memory tag";
           }
           leaf ppp-subscriber-memory-pool-entry-size {
             type uint32;
             description
               "Number of bytes of tagged memory allocated";
           }
           leaf ppp-subscriber-memory-pool-entries {
             type uint32;
             description
               "Number of active memory blocks";
           }
           leaf ppp-subscriber-memory-pool-free {
             type uint32;
             description
               "Number of memory blocks on the free list";
           }
           leaf ppp-subscriber-memory-pool-maximum-free {
             type uint32;
             description
               "Maximum number of memory blocks allowed on the free list";
           }
           leaf ppp-subscriber-memory-pool-total {
             type uint32;
             description
               "Total number of bytes allocated by the memory tag";
           }
           leaf ppp-subscriber-memory-pool-requests {
             type uint32;
             description
               "Number of successful memory allocation requests";
           }
           leaf ppp-subscriber-memory-pool-failures {
             type uint32;
             description
               "Number of failed memory allocation requests";
           }
         }
       }
     }
   }
   grouping ppp-summary-information-block {
     list ppp-session {
       description
         "PPP session";
       leaf session-name {
         type string;
         description
           "PPP session name";
       }
       leaf session-type {
         type string;
         description
           "PPP session type";
       }
       leaf session-phase {
         type string;
         description
           "PPP session phase";
       }
       leaf ppp-last-started {
         type string;
         description
           "Time when negotiation of the protocol last started, in theformat
           YYYY-MM-DD hh:mm:ss TZ (year, month, date, hour in24-hour 
           format, minute second, time zone)";
       }
       leaf ppp-last-completed {
         type string;
         description
           "Time when negotiation of the protocol last 
           completedsuccessfully, in the format YYYY-MM-DD hh:mm:ss TZ 
           (year,month, date, hour in 24-hour format, minute second, 
           timezone)";
       }
       leaf ppp-last-updated {
         type string;
         description
           "Time when negotiation of the protocol last updatedsuccessfully, 
           in the format YYYY-MM-DD hh:mm:ss TZ (year,month, date, hour in 
           24-hour format, minute second, timezone)";
       }
       container session-flags {
         description
           "PPP session flags";
         leaf session-bundled {
           type empty;
           description
             "Session is part of a multilink bundle";
         }
         leaf session-ncp-only {
           type empty;
           description
             "Session only negotiates Network Control Protocol";
         }
         leaf session-always-up {
           type empty;
           description
             "Session is always up";
         }
         leaf session-tcc {
           type empty;
           description
             "Session is a translational cross-connect";
         }
         leaf session-looped {
           type empty;
           description
             "Session has detected a loop";
         }
         leaf session-monitored {
           type empty;
           description
             "Session packet exchange is being monitored";
         }
       }
       container ppp-auth-protocol-information {
         description
           "Authentication protocol information for PPP session";
         leaf ppp-auth-proto {
           type string;
         }
         leaf ppp-state {
           type string;
           description
             "Protocol state";
         }
         leaf ppp-last-started {
           type string;
           description
             "Time when negotiation of the protocol last started, in 
             theformat YYYY-MM-DD hh:mm:ss TZ (year, month, date, hour 
             in24-hour format, minute second, time zone)";
         }
         leaf ppp-last-completed {
           type string;
           description
             "Time when negotiation of the protocol last 
             completedsuccessfully, in the format YYYY-MM-DD hh:mm:ss TZ 
             (year,month, date, hour in 24-hour format, minute second, 
             timezone)";
         }
       }
       list ppp-session-protocol-information {
         description
           "LCP/NCP protocol information for PPP session";
         leaf ppp-protocol {
           type string;
           description
             "Protocol value";
         }
         leaf ppp-state {
           type string;
           description
             "Protocol state";
         }
         container ppp-destination-profile {
           description
             "Destination profile information";
           leaf pool-name {
             type string;
             description
               "Name of pool from which addresses are assigned";
           }
         }
         container ppp-negotiated-options {
           description
             "PPP options negotiated with the remote peer";
           leaf ipcp-compression-protocol {
             type empty;
             description
               "Compression protocol Internet Protocol Control Protocol 
               option";
           }
           leaf ipcp-primary-dns {
             type jt:ipaddr;
             description
               "Internet Protocol Control Protocol primary domain name 
               server option";
           }
           leaf ipcp-primary-wins {
             type jt:ipaddr;
             description
               "Internet Protocol Control Protocol primary WINS option";
           }
           leaf ipcp-secondary-dns {
             type jt:ipaddr;
             description
               "Internet Protocol Control Protocol secondary domain name 
               server option";
           }
           leaf ipcp-secondary-wins {
             type jt:ipaddr;
             description
               "Internet Protocol Control Protocol secondary WINS option";
           }
           leaf bcp-mac-support {
             type string;
             description
               "Supported MAC type information conveyed to the remote peer";
           }
           leaf bcp-tagged-frame {
             type string;
             description
               "BCP tagging support information conveyed to the remote peer";
           }
           leaf lcp-address-compression-field-compression {
             type empty;
             description
               "Link Control Protocol address compression/field compression 
               option";
           }
           leaf lcp-protocol-field-compression {
             type empty;
             description
               "Link Control Protocol protocol/field compression option";
           }
           leaf lcp-async-map {
             type empty;
             description
               "Link Control Protocol asynchronous map option";
           }
           leaf lcp-short-sequence {
             type empty;
             description
               "Link Control Protocol short sequence option";
           }
           leaf lcp-magic-number {
             type uint32;
             description
               "Link Control Protocol magic number option";
           }
           leaf lcp-mrru {
             type uint32;
             description
               "Link Control Protocol maximum reconstructed receive unit 
               option";
           }
           leaf lcp-initial-advertised-mru {
             type uint32;
             description
               "Initial Advertised Link Control Protocol maximum receive 
               unit option";
           }
           leaf lcp-mru {
             type uint32;
             description
               "Link Control Protocol maximum receive unit option";
           }
           leaf lcp-peer-mrru {
             type uint32;
             description
               "Peer Link Control Protocol maximum reconstructed receive 
               unit option";
           }
           leaf lcp-peer-mru {
             type uint32;
             description
               "Peer Link Control Protocol maximum receive unit option";
           }
           leaf lcp-connection-status-msg {
             type string;
             description
               " Juniper Lcp connection status message ";
           }
           leaf lcp-connection-update-reqctr {
             type uint32;
             description
               "Indicates number of discrete events when lcp connection 
               update request was attempted";
           }
           container ipcp-address {
             description
               "Negotiated IP address Internet Protocol Control Protocol 
               option";
             leaf local-address {
               type jt:ipaddr;
               description
                 "Local interface address negotiated with remote peer";
             }
             leaf remote-address {
               type jt:ipaddr;
               description
                 "Destination address negotiated with remote peer";
             }
           }
           container ipv6cp-interface-identifier {
             description
               "Negotiated Internet Protocol Version 6 Control Protocol 
               interface identifier option";
             leaf local-interface-identifier {
               type string;
               description
                 "Local interface identifier negotiated with remote peer";
             }
             leaf remote-interface-identifier {
               type string;
               description
                 "Remote interface identifier negotiated with remote peer";
             }
           }
           container lcp-authentication-protocol {
             description
               "Link Control Protocol authentication protocol option";
             leaf authentication-protocol-name {
               type string;
               description
                 "Name of authentication protocol";
             }
             leaf authentication-algorithm {
               type string;
               description
                 "Authentication algorithm identifier";
             }
           }
           container lcp-endpoint-discriminator {
             description
               "Link Control Protocol endpoint discriminator option";
             leaf endpoint-discriminator-class {
               type string;
               description
                 "Endpoint discriminator class";
             }
             leaf endpoint-discriminator-identifier {
               type string;
               description
                 "Endpoint discriminator identifier";
             }
           }
           container lcp-multilink-header {
             description
               "Link Control Protocol multilink header format option";
             leaf multilink-header-code {
               type uint32;
               description
                 "Multilink header format code";
             }
             leaf multilink-header-suspendable-classes {
               type uint32;
               description
                 "Number of suspendable classes";
             }
           }
         }
         leaf ppp-last-started {
           type string;
           description
             "Time when negotiation of the protocol last started, in 
             theformat YYYY-MM-DD hh:mm:ss TZ (year, month, date, hour 
             in24-hour format, minute second, time zone)";
         }
         leaf ppp-last-completed {
           type string;
           description
             "Time when negotiation of the protocol last 
             completedsuccessfully, in the format YYYY-MM-DD hh:mm:ss TZ 
             (year,month, date, hour in 24-hour format, minute second, 
             timezone)";
         }
         leaf ppp-last-updated {
           type string;
           description
             "Time when negotiation of the protocol last 
             updatedsuccessfully, in the format YYYY-MM-DD hh:mm:ss TZ 
             (year,month, date, hour in 24-hour format, minute second, 
             timezone)";
         }
         leaf ppp-negotiation-mode {
           type string;
           description
             "PPP options negotiatiation mode with the remote peer";
         }
       }
     }
   }
 }
