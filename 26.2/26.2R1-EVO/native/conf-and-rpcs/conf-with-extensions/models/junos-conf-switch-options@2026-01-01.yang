/*
 * Copyright (c) 2026 Juniper Networks, Inc.
 * All rights reserved.
 */
 module junos-conf-switch-options {
   namespace "http://yang.juniper.net/junos/conf/switch-options";

   prefix jc-switch-options;

   import junos-common-ddl-extensions {
     prefix junos;
     revision-date 2026-01-01;
   }

   import junos-common-types {
     prefix jt;
     revision-date 2026-01-01;
   }

   import junos-conf-root {
     prefix jc;
     revision-date 2026-01-01;
   }

   organization "Juniper Networks, Inc.";

   contact "yang-support@juniper.net";

   description "Junos switch-options configuration module";

   revision 2026-01-01 {
     description "Junos: 26.2R1.7-EVO";
   }

   augment /jc:configuration {
     uses switch-options-group;
   }
   augment /jc:configuration/jc:groups {
     uses switch-options-group;
   }
   grouping switch-options-group {
     container switch-options {
       description "Options for default routing-instance of type virtual-switch";
       uses juniper-def-rtb-switch-options;
     }
   }
   grouping juniper-def-rtb-switch-options {
     description "Bridge option configuration";
     uses apply-advanced;
     container mac-table-size {
       junos:must "(!(((\".. .. .. protocols vpls\" || \".. .. .. protocols evpn\") && (\".. .. ..  instance-type virtual-switch\" || \".. .. ..  instance-type mac-vrf\"))))";
       junos:must-message "mac-table-size needs to be specified under switch-options for a virtual-switch or mac-vrf instance";
       description "Size of MAC address forwarding table";
       uses apply-advanced;
       leaf limit {
         description "Maximum number of MAC addresses";
         junos:cli-feature "nokeyword";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
         }
       }
     }
     container mac-ip-table-size {
       junos:must "(!(((\".. .. .. protocols vpls\" || \".. .. .. protocols evpn\") && (\".. .. ..  instance-type virtual-switch\" || \".. .. ..  instance-type mac-vrf\"))))";
       junos:must-message "mac-ip-table-size needs to be specified under switch-options for a virtual-switch or mac-vrf instance";
       description "Size of MAC+IP bindings table";
       uses apply-advanced;
       leaf limit {
         description "Maximum number of MAC+IP bindings";
         junos:cli-feature "nokeyword";
         type union {
           type string {
             pattern "<.*>|$.*";
           }
           type uint32;
         }
       }
     }
     container interface-mac-limit {
       junos:must "(!(((\".. .. .. protocols vpls\" || \".. .. .. protocols evpn\") && (\".. .. ..  instance-type virtual-switch\" || \".. .. ..  instance-type mac-vrf\"))))";
       junos:must-message "interface-mac-limit needs to be specified under switch-options for a virtual-switch or mac-vrf instance";
       description "Maximum MAC address learned per interface";
       uses apply-advanced;
       leaf limit {
         description "Maximum number of MAC addresses per interface";
         junos:cli-feature "nokeyword";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
           enum "log" {
             description "Do not drop the packet but generate an alarm, an SNMP trap or a system log entry";
           }
           enum "shutdown" {
             description "Disable the interface and generate an alarm, an SNMP trap or a system log entry";
           }
           enum "drop-and-log" {
             description "Drop the packet and generate an alarm, an SNMP trap or a system log entry";
           }
         }
       }
     }
     container interface-mac-ip-limit {
       junos:must "(!(((\".. .. .. protocols vpls\" || \".. .. .. protocols evpn\") && (\".. .. ..  instance-type virtual-switch\" || \".. .. ..  instance-type mac-vrf\"))))";
       junos:must-message "interface-mac-ip-limit needs to be specified under switch-options for a virtual-switch or mac-vrf instance";
       description "Maximum MAC+IP bindings learned per interface";
       uses apply-advanced;
       leaf limit {
         description "Maximum number of MAC+IP bindings per interface";
         junos:cli-feature "nokeyword";
         type union {
           type string {
             pattern "<.*>|$.*";
           }
           type uint32;
         }
       }
     }
     container mac-move-limit {
       presence "enable mac-move-limit";
       junos:must "(!(\".. .. .. .. vlans ${vlan} private-vlan\"))";
       junos:must-message "Switch-options configuration is not allowed on secondary VLANs";
       description "Number of MAC movements allowed on this VLAN";
       uses apply-advanced;
       choice limit-choice {
         case case_1 {
           leaf none {
             description "Disable mac-move-limit for this VLAN";
             type empty;
           }
         }
         case case_2 {
           leaf limit {
             description "Number of MAC movements allowed on this VLAN";
             junos:cli-feature "nokeyword";
             type union {
               type string {
                 pattern "<.*>|$.*";
               }
               type uint32 {
                 range "1 .. 4294967295";
               }
             }
           }
         }
       }
       leaf packet-action {
         description "Action to be taken in case the MAC movement limit is exceeded";
         default "drop";
         junos:must "(!(\".. none\"))";
         junos:must-message "Packet-action can not co-exist with mac-move-limit none";
         type enumeration {
           enum "none" {
             description "Take no action";
           }
           enum "drop" {
             description "Drop the packet and do not generate an alarm";
           }
           enum "log" {
             description "Do not drop the packet but generate an alarm, an SNMP trap, or a system log entry.";
           }
           enum "shutdown" {
             description "Disable the interface and generate an alarm, an SNMP trap, or a system log entry.";
           }
           enum "drop-and-log" {
             description "Drop the packet and generate an alarm, an SNMP trap, or a system log entry.";
           }
           enum "vlan-member-shutdown" {
             description "Disable the interface of this VLAN";
           }
         }
       }
       list interface {
         key name;
         description "Interface that connect this site to the VPN";
         junos:must "(!(\".. none\"))";
         junos:must-message "Interface can not co-exist with mac-move-limit none";
         leaf name {
           description "Interface name";
           junos:cli-feature "nokeyword";
           junos:must "((\".. .. .. .. interface $$\" || \"interfaces $$-IFL family ethernet-switching\"))";
           junos:must-message "Interface must be configured for L2";
           type union {
             type jt:interface-name;
             type string {
               pattern "<.*>|$.*";
             }
           }
         }
         uses apply-advanced;
         leaf action-priority {
           description "Blocking priority of this interface on mac move detection";
           junos:must "(!(\".. .. .. .. .. vlans ${vlan} private-vlan\"))";
           junos:must-message "Switch-options configuration is not allowed on interfaces which are part of secondary VLANs";
           type union {
             type string {
               pattern "<.*>|$.*";
             }
             type uint32 {
               range "0 .. 7";
             }
           }
         }
       }
     }
     container mac-notification {
       presence "enable mac-notification";
       description "MAC notification options";
       uses apply-advanced;
       leaf notification-interval {
         description "Interval for sending MAC notifications";
         default "30";
         units "seconds";
         type union {
           type string {
             pattern "<.*>|$.*";
           }
           type uint32 {
             range "1 .. 60";
           }
         }
       }
     }
     leaf mac-table-aging-time {
       description "Delay for discarding MAC address if no updates are received";
       units "seconds";
       type union {
         type string {
           pattern "<.*>|$.*";
         }
         type uint32;
       }
     }
     leaf no-mac-learning {
       description "Disable dynamic MAC address learning";
       junos:must "(!(((\".. .. .. protocols vpls\" || \".. .. .. protocols evpn\") && (\".. .. ..  instance-type virtual-switch\" || \".. .. ..  instance-type mac-vrf\"))))";
       junos:must-message "no-mac-learning needs to be specified under switch-options for a virtual-switch or mac-vrf instance";
       type empty;
     }
     leaf no-mac-ip-learning {
       description "Disable dynamic MAC IP address learning";
       junos:must "(!(\".. .. switch-options\"))";
       junos:must-message "no-mac-ip-learning cannot be configured under switch-options";
       junos:must "((!(\".. .. routing-interface\") && !(\".. .. .. routing-interface\")))";
       junos:must-message "no-mac-ip-learning cannot be configured with routing-interface";
       junos:must "((\".. no-arp-suppression\" || \".. .. no-arp-suppression\"))";
       junos:must-message "no-arp-suppression must be configured";
       type empty;
     }
     container port-extender {
       presence "enable port-extender";
       description "Configure port-extender";
       uses apply-advanced;
       leaf mode {
         description "Configure port-extender mode";
         type enumeration {
           enum "aggregation-device" {
             description "Aggregation Device";
           }
           enum "satellite-device" {
             description "Satellite Device";
           }
         }
       }
     }
     leaf drop-unknown-mac-ip {
       description "Drop unknown MAC-IP traffic";
       type empty;
     }
     container mib {
       presence "enable mib";
       description "Snmp mib options";
       uses apply-advanced;
       container dot1q-mib {
         presence "enable dot1q-mib";
         description "Dot1q MIB configuration options";
         uses apply-advanced;
         leaf port-list {
           description "Port list for staticegressports and staticuntaggedports MIB";
           type enumeration {
             enum "bit-map" {
               description "Port list is represented in bit-map format";
             }
             enum "string" {
               description "Port list is represented in string format";
             }
           }
         }
       }
     }
     container static-rvtep-mac {
       description "Configure Static MAC and remote VxLAN tunnel endpoint entries";
       uses apply-advanced;
       list mac {
         key "mac_addr remote-vtep";
         junos:cli-feature "oneliner";
         description "Unicast MAC address";
         leaf mac_addr {
           junos:cli-feature "nokeyword";
           type jt:mac-unicast;
         }
         leaf remote-vtep {
           description "Configure static remote VXLAN tunnel endpoints";
           type jt:ipaddr;
         }
       }
     }
     leaf service-id {
       description "Service ID required if multi-chassis AE is part of a bridge-domain";
       type union {
         type string {
           pattern "<.*>|$.*";
         }
         type uint32 {
           range "1 .. 65535";
         }
       }
     }
     container network-isolation-profile {
       description "Network isolation configuration";
       uses apply-advanced;
       list group {
         key name;
         description "Network isolation group";
         leaf name {
           description "Group name";
           junos:cli-feature "nokeyword";
           type string;
         }
         uses apply-advanced;
       }
     }
     container fabric-esi {
       junos:must "(\".. .. protocols evpn encapsulation vxlan\")";
       junos:must-message "Supported for EVPN-VXLAN encapsulation";
       description "Fabric ESI";
       uses apply-advanced;
       leaf identifier {
         description "ESI value";
         junos:cli-feature "nokeyword";
         type jt:esi;
       }
       choice fabric-esi-action {
         case case_1 {
           leaf no-install-host-route {
             description "Don't install MAC-IP host route";
             type empty;
           }
         }
       }
     }
     container vtep-source-interface {
       junos:cli-feature "oneliner";
       description "Source layer-3 IFL for VXLAN";
       leaf interface-name {
         junos:cli-feature "nokeyword";
         junos:must "(\"interfaces $$\")";
         junos:must-message "Interface must be defined";
         type union {
           type jt:interface-name;
           type string {
             pattern "<.*>|$.*";
           }
         }
       }
       choice family {
         case case_1 {
           container inet {
             presence "enable inet";
             description "IPv4 source";
             uses apply-advanced;
           }
         }
         case case_2 {
           container inet6 {
             presence "enable inet6";
             description "IPv6 source";
             uses apply-advanced;
           }
         }
       }
     }
     container vtep-remote-interface {
       description "Remote VTEP interface";
       uses apply-advanced;
       list remote-ip {
         key name;
         ordered-by user;
         description "Remote VTEP IP address";
         leaf name {
           description "IP address";
           junos:cli-feature "nokeyword";
           type jt:ipv4addr;
         }
         uses apply-advanced;
         leaf dynamic-profile {
           description "Define associate dynamic profile";
           junos:must "(\"dynamic-profiles $$\")";
           junos:must-message "Dynamic profile must be defined";
           type string;
         }
       }
       container default {
         description "To all remote vtep interface";
         uses apply-advanced;
         leaf dynamic-profile {
           description "Define associate dynamic profile";
           junos:must "(\"dynamic-profiles $$\")";
           junos:must-message "Dynamic profile must be defined";
           type string;
         }
       }
     }
     list interface {
       key name;
       ordered-by user;
       description "Interface for configuring bridge-options";
       leaf name {
         description "Interface name";
         junos:cli-feature "nokeyword";
         junos:must "((\"interfaces $$-IFL family bridge interface-mode\" || \"interfaces $$-IFL family ethernet-switching\"))";
         junos:must-message "Only interface with 'interface-mode' are allowed in a default routing-instance";
         junos:must "(\"interfaces $$\")";
         junos:must-message "Interface must be part of this routing instance";
         type union {
           type jt:interface-name;
           type string {
             pattern "<.*>|$.*";
           }
         }
       }
       uses apply-advanced;
       container mac-learning-priority {
         description "MAC learning priority for the interface";
         uses apply-advanced;
         leaf priority {
           description "Mac learning priority for the interface";
           junos:cli-feature "nokeyword";
           type union {
             type string {
               pattern "<.*>|$.*";
             }
             type uint32 {
               range "1 .. 65535";
             }
           }
         }
         leaf packet-action {
           default "discard";
           type enumeration {
             enum "discard" {
               description "Discard the packets and do not learn. Default is forward";
             }
             enum "forward" {
               description "Forward the packet";
               junos:must "(!(any \".. .. .. .. vlans <*> switch-options interface ${interface} interface-mac-limit\"))";
               junos:must-message "IFBD mac limit cannot be configured with mac learn priority with forward action";
               junos:must "(!(\".. .. interface-mac-limit\"))";
               junos:must-message "IFL mac limit cannot be configured with mac learn priority with forward action";
             }
           }
         }
       }
       container interface-mac-limit {
         description "Maximum number of MAC addresses learned on the interface";
         uses apply-advanced;
         leaf limit {
           description "Maximum number of MAC addresses per interface";
           junos:cli-feature "nokeyword";
           type union {
             type string {
               pattern "<.*>|$.*";
             }
             type uint32;
           }
         }
         leaf disable {
           description "Disable interface for interface-mac-limit";
           type empty;
         }
         leaf packet-action {
           description "Action when MAC limit is reached";
           type enumeration {
             enum "none" {
               description "Forward the packet";
             }
             enum "drop" {
               description "Drop packets and do not learn. Default is forward";
             }
             enum "log" {
               description "Do not drop the packet but generate an alarm, an SNMP trap or a system log entry";
             }
             enum "shutdown" {
               description "Disable the interface and generate an alarm, an SNMP trap or a system log entry";
             }
             enum "drop-and-log" {
               description "Drop the packet and generate an alarm, an SNMP trap or a system log entry";
             }
           }
         }
       }
       container interface-mac-ip-limit {
         description "Maximum number of MAC+IP bindings learned on the interface";
         uses apply-advanced;
         leaf limit {
           description "Maximum number of MAC+IP bindings per interface";
           junos:cli-feature "nokeyword";
           type union {
             type string {
               pattern "<.*>|$.*";
             }
             type uint32;
           }
         }
       }
       leaf no-mac-learning {
         description "Disable dynamic MAC address learning";
         type empty;
       }
       leaf mac-pinning {
         description "Enable MAC pinning";
         type empty;
       }
       leaf persistent-learning {
         description "Enable persistent MAC learning on this interface";
         junos:must "(!(\".. no-mac-learning\"))";
         junos:must-message "Persistent learning can not co-exist with no-mac-learning";
         junos:must "(!(\"switch-options mac-table-aging-time \"))";
         junos:must-message "Persistent learning can not co-exist with mac-table-aging-time";
         type empty;
       }
       leaf no-mac-notification {
         description "Disable mac notification on this interface";
         type empty;
       }
     }
     leaf-list remote-vtep-list {
       description "Configure static remote VXLAN tunnel endpoints";
       type jt:ipaddr;
       max-elements 1024;
     }
     leaf interface-shutdown-action {
       description "Interface shutdown mode for Storm-Control/Mac-Limit/Mac-Move-limit scenario";
       type enumeration {
         enum "soft-shutdown" {
           description "Soft-shutdown restricts data-packets while control-packets are still received";
         }
         enum "hard-shutdown" {
           description "Hard-shutdown restricts all packets, port will not be operational";
         }
       }
     }
     leaf-list remote-vtep-v6-list {
       description "Configurate static IPv6 remote VXLAN tunnel endpoints";
       type jt:ipv6addr;
       max-elements 1024;
     }
     container route-distinguisher {
       junos:must "(\".. .. protocols evpn\")";
       junos:must-message "protocols evpn must be defined";
       junos:cli-feature "oneliner";
       description "Route distinguisher for this instance";
       leaf rd-type {
         description "Number in (16 bit:32 bit) or (32 bit 'L':16 bit) or (IP address:16 bit) format";
         junos:cli-feature "nokeyword";
         type string {
           junos:posix-pattern "^[0-9.]+L?:[0-9]+$";
           junos:pattern-message "Use format \'x:y\' where \'x\' is an AS number followed by an optional \'L\' (To indicate 4 byte AS), or an IP address and \'y\' is a number. e.g. 123456L:100";
         }
       }
     }
     leaf-list vrf-import {
       ordered-by user;
       description "Import policy for VRF instance RIBs";
       junos:must "(\".. route-distinguisher\")";
       junos:must-message "route-distinguisher must be defined";
       type jt:policy-algebra;
     }
     leaf-list vrf-export {
       ordered-by user;
       description "Export policy for VRF instance RIBs";
       junos:must "(\".. route-distinguisher\")";
       junos:must-message "route-distinguisher must be defined";
       type jt:policy-algebra;
     }
     container vrf-target {
       junos:must "(\".. route-distinguisher\")";
       junos:must-message "route-distinguisher must be defined";
       junos:cli-feature "oneliner-plus";
       description "VRF target community configuration";
       uses apply-advanced;
       leaf community {
         description "Target community to use in import and export";
         junos:cli-feature "nokeyword";
         type string {
           junos:posix-pattern "^[a-z6-]+:([0-9.]+L?|(<((([0-9A-Fa-f]{1,4}:){7}([0-9A-Fa-f]{1,4}|:))|(([0-9A-Fa-f]{1,4}:){6}(:[0-9A-Fa-f]{1,4}|([0-9.]{7,15})|:))|(([0-9A-Fa-f]{1,4}:){5}(((:[0-9A-Fa-f]{1,4}){1,2})|:([0-9.]{7,15})|:))|(([0-9A-Fa-f]{1,4}:){4}(((:[0-9A-Fa-f]{1,4}){1,3})|((:[0-9A-Fa-f]{1,4})?:([0-9.]{7,15}))|:))|(([0-9A-Fa-f]{1,4}:){3}(((:[0-9A-Fa-f]{1,4}){1,4})|((:[0-9A-Fa-f]{1,4}){0,2}:([0-9.]{7,15}))|:))|(([0-9A-Fa-f]{1,4}:){2}(((:[0-9A-Fa-f]{1,4}){1,5})|((:[0-9A-Fa-f]{1,4}){0,3}:([0-9.]{7,15}))|:))|(([0-9A-Fa-f]{1,4}:){1}(((:[0-9A-Fa-f]{1,4}){1,6})|((:[0-9A-Fa-f]{1,4}){0,4}:([0-9.]{7,15}))|:))|(:(((:[0-9A-Fa-f]{1,4}){1,7})|((:[0-9A-Fa-f]{1,4}){0,5}:([0-9.]{7,15}))|:)))(%.+)?>)):+[0-9]+$";
           junos:pattern-message "Use format \'target:x:y\' where \'x\' is an AS number followed by an optional \'L\' (To indicate 4 byte AS), or an IP address and \'y\' is a number. e.g. target:123456L:100 or ipv6-target:<x>:y where \'x\' is an IPv6 Address and \'y\' is local administrator number.";
         }
       }
       leaf import {
         description "Target community to use when filtering on import";
         type string {
           junos:posix-pattern "^[a-z6-]+:([0-9.]+L?|(<((([0-9A-Fa-f]{1,4}:){7}([0-9A-Fa-f]{1,4}|:))|(([0-9A-Fa-f]{1,4}:){6}(:[0-9A-Fa-f]{1,4}|([0-9.]{7,15})|:))|(([0-9A-Fa-f]{1,4}:){5}(((:[0-9A-Fa-f]{1,4}){1,2})|:([0-9.]{7,15})|:))|(([0-9A-Fa-f]{1,4}:){4}(((:[0-9A-Fa-f]{1,4}){1,3})|((:[0-9A-Fa-f]{1,4})?:([0-9.]{7,15}))|:))|(([0-9A-Fa-f]{1,4}:){3}(((:[0-9A-Fa-f]{1,4}){1,4})|((:[0-9A-Fa-f]{1,4}){0,2}:([0-9.]{7,15}))|:))|(([0-9A-Fa-f]{1,4}:){2}(((:[0-9A-Fa-f]{1,4}){1,5})|((:[0-9A-Fa-f]{1,4}){0,3}:([0-9.]{7,15}))|:))|(([0-9A-Fa-f]{1,4}:){1}(((:[0-9A-Fa-f]{1,4}){1,6})|((:[0-9A-Fa-f]{1,4}){0,4}:([0-9.]{7,15}))|:))|(:(((:[0-9A-Fa-f]{1,4}){1,7})|((:[0-9A-Fa-f]{1,4}){0,5}:([0-9.]{7,15}))|:)))(%.+)?>)):+[0-9]+$";
           junos:pattern-message "Use format \'target:x:y\' where \'x\' is an AS number followed by an optional \'L\' (To indicate 4 byte AS), or an IP address and \'y\' is a number. e.g. target:123456L:100 or ipv6-target:<x>:y where \'x\' is an IPv6 Address and \'y\' is local administrator number.";
         }
       }
       leaf export {
         description "Target community to use when marking routes on export";
         type string {
           junos:posix-pattern "^[a-z6-]+:([0-9.]+L?|(<((([0-9A-Fa-f]{1,4}:){7}([0-9A-Fa-f]{1,4}|:))|(([0-9A-Fa-f]{1,4}:){6}(:[0-9A-Fa-f]{1,4}|([0-9.]{7,15})|:))|(([0-9A-Fa-f]{1,4}:){5}(((:[0-9A-Fa-f]{1,4}){1,2})|:([0-9.]{7,15})|:))|(([0-9A-Fa-f]{1,4}:){4}(((:[0-9A-Fa-f]{1,4}){1,3})|((:[0-9A-Fa-f]{1,4})?:([0-9.]{7,15}))|:))|(([0-9A-Fa-f]{1,4}:){3}(((:[0-9A-Fa-f]{1,4}){1,4})|((:[0-9A-Fa-f]{1,4}){0,2}:([0-9.]{7,15}))|:))|(([0-9A-Fa-f]{1,4}:){2}(((:[0-9A-Fa-f]{1,4}){1,5})|((:[0-9A-Fa-f]{1,4}){0,3}:([0-9.]{7,15}))|:))|(([0-9A-Fa-f]{1,4}:){1}(((:[0-9A-Fa-f]{1,4}){1,6})|((:[0-9A-Fa-f]{1,4}){0,4}:([0-9.]{7,15}))|:))|(:(((:[0-9A-Fa-f]{1,4}){1,7})|((:[0-9A-Fa-f]{1,4}){0,5}:([0-9.]{7,15}))|:)))(%.+)?>)):+[0-9]+$";
           junos:pattern-message "Use format \'target:x:y\' where \'x\' is an AS number followed by an optional \'L\' (To indicate 4 byte AS), or an IP address and \'y\' is a number. e.g. target:123456L:100 or ipv6-target:<x>:y where \'x\' is an IPv6 Address and \'y\' is local administrator number.";
         }
       }
       container auto {
         description "Auto derive import and export target community from BGP AS & L2";
         presence "enable auto";
         junos:cli-feature "oneliner-plus";
         uses juniper-def-rtb-auto-as;
       }
     }
     container redundant-trunk-group {
       description "Redundant trunk group";
       uses apply-advanced;
       list group {
         key name;
         ordered-by user;
         description "Name of Redundant trunk group";
         leaf name {
           description "RTG name";
           junos:cli-feature "nokeyword";
           type string {
             length "1 .. 63";
             junos:posix-pattern "^[[:alpha:]][[:alnum:]_-]+$";
             junos:pattern-message "Must be a string beginning with a letter and consisting of letters, numbers, dashes, and underscores";
           }
         }
         uses apply-advanced;
         leaf preempt-cutover-timer {
           description "Hold timer for primary interface before preempting secondary interface";
           units "seconds";
           type union {
             type string {
               pattern "<.*>|$.*";
             }
             type uint16 {
               range "1 .. 600";
             }
           }
         }
         leaf description {
           description "Text description of the RTG";
           type string {
             length "1 .. 127";
             junos:posix-pattern "^[[:alpha:]][[:alnum:]_-]+$";
             junos:pattern-message "Must be a string beginning with a letter and consisting of letters, numbers, dashes, and underscores";
           }
         }
         list interface {
           key name;
           description "Interfaces that are part of this redundant trunk group";
           leaf name {
             description "Interface name";
             junos:cli-feature "nokeyword";
             junos:must "(!(\"switch-options interface $$ persistent-learning\"))";
             junos:must-message "Persistent learning can not be configured on an interface which is part of RTG";
             junos:must "(!(any \"forwarding-options analyzer <*> output interface $$\"))";
             junos:must-message "Analyzer output and RTG can not be enabled on the same interface";
             junos:must "(!((any \"protocols protection-group ethernet-ring <*> east-interface control-channel $$\" || any \"protocols protection-group ethernet-ring <*> west-interface control-channel $$\")))";
             junos:must-message "ERP and RTG can not be enabled on the same interface";
             type union {
               type jt:interface-name;
               type string {
                 pattern "<.*>|$.*";
               }
             }
           }
           uses apply-advanced;
           leaf primary {
             description "Set Primary Redundant Trunk Group interface";
             type empty;
           }
         }
       }
     }
     container voip {
       description "Voice-over-IP configuration";
       uses apply-advanced;
       list interface {
         key name;
         ordered-by user;
         description "Enable voice over IP on this port";
         leaf name {
           junos:cli-feature "nokeyword";
           type string;
         }
         uses apply-advanced;
         leaf vlan {
           description "VLAN for voice over IP";
           junos:must "(!(\"vlans $$ vlan-range \"))";
           junos:must-message "Ranged vlan cannot be used by Voice-over-IP";
           type string {
           }
         }
         leaf forwarding-class {
           description "Forwarding class";
           type string {
             junos:posix-pattern "^.{1,64}$";
             junos:pattern-message "Must be string of 64 characters or less";
           }
         }
       }
     }
     list authentication-whitelist {
       key name;
       ordered-by user;
       junos:cli-feature "homogeneous";
       description "MAC authentication-whitelist configuration needed to bypass Authentication";
       leaf name {
         description "MAC addresses to bypass authentication";
         junos:cli-feature "nokeyword";
         junos:must "(any \"services captive-portal interface <*> supplicant multiple\")";
         junos:must-message "At least one interface must be configured with captive portal multiple supplicant mode";
         type jt:mac-addr-prefix;
       }
       uses apply-advanced;
       leaf vlan-assignment {
         description "VLAN name or 802.1q tag for the MAC address";
         junos:must "(!(\"vlans $$ vlan-range\"))";
         junos:must-message "vlan with vlan-range not supported under static MAC vlan-assignment";
         junos:must "((\"vlans $$\" || any \"vlans <*> vlan-id $$\"))";
         junos:must-message "vlan assigned is not configured";
         type string {
         }
       }
       leaf bridge-domain-assignment {
         description "Bridge-domain name or 802.1q tag for the MAC address";
         junos:must "(!(\".. .. .. bridge-domains $$ vlan-id-list\"))";
         junos:must-message "Bridge-domain with vlan-id-list not supported under static MAC bridge-domain-assignment";
         junos:must "((\".. .. .. bridge-domains $$\" || any \".. .. .. bridge-domains <*> vlan-id $$\"))";
         junos:must-message "Bridge-domain assigned is not configured";
         type string {
           junos:posix-pattern "^([[:alpha:]][[:alnum:]_.-]+)|^([1-9][0-9]{0,2}|[1-3][0-9]{3}|40[0-8][0-9]|409[0-4])$";
           junos:pattern-message "Must be a valid Bridge-domain or VLAN tag";
         }
       }
       leaf interface {
         description "Interface on which authentication is bypassed";
         junos:must "((!(\".. .. .. switch-options no-mac-learning\") || !(any \".. .. .. bridge-domain <*> bridge-options interface $$ no-mac-learning\")))";
         junos:must-message "Cannot configure authentication-whitelist on this interface since no-mac-learning is enabled on the same interface";
         junos:must "(!(\"interfaces $$-IFL family bridge interface-mode trunk\"))";
         junos:must-message "Cannot configure whitelist on this interface since the interface-mode is defined as trunk";
         junos:must "(!(\"interfaces $$-IFL family ethernet-switching port-mode trunk\"))";
         junos:must-message "Cannot configure whitelist on this interface since the port-mode is defined as trunk";
         junos:must "((\"services captive-portal interface $$ supplicant multiple\" || \"services captive-portal interface all supplicant multiple\"))";
         junos:must-message "authentication-whitelist MAC can be configured only on interface configured with captive portal multiple supplicant mode";
         junos:must "((\"interfaces $$-IFL family ethernet-switching\" || \"interfaces $$-IFL family bridge\"))";
         junos:must-message "Interface must be defined in the interfaces hierarchy with family ethernet-switching or family bridge";
         type union {
           type jt:interface-name;
           type string {
             pattern "<.*>|$.*";
           }
         }
       }
     }
     choice vstp-flooding-option {
       case case_1 {
         leaf vstp-flooding {
           description "Flood vstp bpdu when vstp is disabled";
           type empty;
         }
       }
     }
     choice arp-trap-option {
     }
     choice mstp-flooding-option {
     }
     choice stp-flooding-option {
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       junos:cli-feature "nokeyword";
       type string;
     }
     list data {
       key name;
       uses macro-data-type;
       junos:cli-feature "nokeyword";
       junos:cli-feature "homogeneous";
       junos:cli-feature "oneliner";
     }
   }
   grouping juniper-def-rtb-auto-as {
     junos:cli-feature "oneliner-plus";
     uses apply-advanced;
     list import-as {
       key name;
       description "AS to auto import for a list of VNI ids";
       junos:must "(!(\".. as-num\"))";
       junos:must-message "Exclusive of 'vrf-target auto as-num' config";
       junos:must "(!((\".. .. .. instance-type evpn\" || \".. .. .. instance-type virtual-switch\")))";
       junos:must-message "import-as is supported only for default-switch instance or mac-vrf";
       leaf name {
         description "Peer autonomous system number";
         junos:cli-feature "nokeyword";
         type string {
           junos:posix-pattern "^[0-9]+(.[0-9]+)?$";
           junos:pattern-message "Use format \'x\' or \'x.y\' to specify number \'x\' (Range 1 .. 4294967295) or number with higher 2 bytes \'x\' (Range 0 .. 65535) and lower 2 bytes \'y\' (Range 0 .. 65535) respectively";
         }
       }
       uses apply-advanced;
       leaf-list vni-list {
         description "List of VNI identifiers or all";
         type string;
       }
     }
     list export-as {
       key name;
       description "AS to auto export for a list of VNI ids";
       junos:must "(!(\".. as-num\"))";
       junos:must-message "Exclusive of 'vrf-target auto as-num' config";
       junos:must "(!((\".. .. .. instance-type evpn\" || \".. .. .. instance-type virtual-switch\")))";
       junos:must-message "export-as is supported only for default-switch instance or mac-vrf";
       leaf name {
         description "Peer autonomous system number";
         junos:cli-feature "nokeyword";
         type string {
           junos:posix-pattern "^[0-9]+(.[0-9]+)?$";
           junos:pattern-message "Use format \'x\' or \'x.y\' to specify number \'x\' (Range 1 .. 4294967295) or number with higher 2 bytes \'x\' (Range 0 .. 65535) and lower 2 bytes \'y\' (Range 0 .. 65535) respectively";
         }
       }
       uses apply-advanced;
       leaf-list vni-list {
         description "List of VNI identifiers or all";
         type string;
       }
     }
     list as-num {
       key name;
       description "AS to auto import and export for a list of VNI ids";
       junos:must "(!((\".. .. .. instance-type evpn\" || \".. .. .. instance-type virtual-switch\")))";
       junos:must-message "as-num is supported only for default-switch instance or mac-vrf";
       junos:must "((!(\".. import-as\") || !(\".. export-as\")))";
       junos:must-message "Exclusive of import-as and export-as config";
       leaf name {
         description "Peer autonomous system number";
         junos:cli-feature "nokeyword";
         type string {
           junos:posix-pattern "^[0-9]+(.[0-9]+)?$";
           junos:pattern-message "Use format \'x\' or \'x.y\' to specify number \'x\' (Range 1 .. 4294967295) or number with higher 2 bytes \'x\' (Range 0 .. 65535) and lower 2 bytes \'y\' (Range 0 .. 65535) respectively";
         }
       }
       uses apply-advanced;
       leaf-list vni-list {
         description "List of VNI identifiers or all";
         type string;
       }
     }
   }
   grouping macro-data-type {
     junos:cli-feature "nokeyword";
     junos:cli-feature "homogeneous";
     junos:cli-feature "oneliner";
     leaf name {
       description "Keyword part of the keyword-value pair";
       junos:cli-feature "nokeyword";
       type string;
     }
     leaf value {
       description "Value part of the keyword-value pair";
       junos:cli-feature "nokeyword";
       type string;
     }
   }
 }
