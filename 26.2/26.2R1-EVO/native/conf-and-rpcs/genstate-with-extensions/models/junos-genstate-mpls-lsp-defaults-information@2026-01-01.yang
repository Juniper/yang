module junos-genstate-mpls-lsp-defaults-information {
   yang-version 1;
   namespace "http://yang.juniper.net/junos/genstate/mpls-lsp-defaults-information";
   prefix jgmldi;

   import junos-genstate {
     prefix jgs;
     revision-date 2026-01-01;
   }

   import junos-common-types {
     prefix jt;
     revision-date 2026-01-01;
   }

   import junos-extension {
     prefix junos;
   }

   organization
     "Juniper Networks, Inc.";

   contact
     "Juniper Networks, Inc.

      1133 Innovation Way
      Sunnyvale, CA 94089

      +1 888 314-5822

      E-mail: yang-support@juniper.net";

   description
      "Junos genstate Yang module for mpls-lsp-defaults-information.

      Copyright (c) 2026 Juniper Networks, Inc.
      All rights reserved.";

   revision 2026-01-01 {
     description "Junos: 26.2R1.7-EVO";
   }

   grouping mpls-lsp-defaults-information-top {
     description
       "Top-level grouping";
     container mpls-lsp-defaults-information {
       description
         "Top-level container";
       junos:product "olive m5 m10 m20 m40 m160 t640 t320 m40e TX Matrix ggsn-c m320 sammy m10i j2300 j4300 j6300 IRM m120 mx960 j4350 j6350 jsr2300 jsr4300 jsr6300 jsr4350 jsr6350 j2320 j2350 jsr2320 jsr2350 mx480 srx5800 sumatra ex3200-24t ex3200-24p ex3200-48t ex3200-48p ex4200-24f ex4200-24t ex4200-24p ex4200-48t ex4200-48p ex8208 ex8216 srx5600 mx240 txp srx3600 srx3400 srx210b srx210h srx210h-poe srx210h-p-m srx240b srx240h srx240h-poe srx240h-p-m srx630 srx650 srx680 sce srx100b srx100h srx110b-va srx110h-va srx110b-vb srx110h-vb srx110b-wl srx220h srx220h-poe srx220h-p-m ex2200-24t-4g ex2200-24p-4g ex2200-48t-4g ex2200-48p-4g ln1000-v fx1600_48 fx2160_48 qfx3500 dc_olive ptx5000 srx1400 ex4500-40f mx80 mx80-48t ptx9000 ex-xre srx240h-dc qfx3008-i fx-jvre qfx3000 qfx3500s mag8600 mag6611 mag6610 ex4200-48px ex4200-24px srx110h-wl srx110h-va-wl srx210be srx210he srx210he-poe ex2200-c-12t-2g qfx5000 ex2200-24t-dc-4g srx110h-vb-wl ex6210 ex3300-24t ex3300-24p ex3300-48t ex3300-48p ex3300-24t-dc ex3300-48t-bf srx210he-p-m ex2200-c-12p-2g mx5-t mx10-t mx40-t mx80-t vjx1000 ex4550-32f ex4550-32t srx550 mx80-p acx1000 acx2000 acx4000 qfx3600-16q qfx3600-i qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4600-40f ex4300-32f qfx5100-96s-8q vmx qfx5100-24q-2pf qfx5100-48s-6qf qfx5100-48t-6qf qfx5100-24q-2p qfx5100-48t-6q srx5400 qfx5100-24q-aa pvi-model vrr ptx1000 qfx10004 qfx10008 qfx10016 vqfx-10000 qfx5100-24q-2pi qfx7100-i qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 qfx10016 acx6160-t ptx10001-27cd ptx10008 qfx10008 qfx5220-32cd qfx5220-128c csrx ptx10003-81cd srx380-poe-ac crpd cmgd ptx10001-36mr acx753 qfx5130-32cd ptx10004 ex4300-48mp QFX7100-48L ACX7100-32C ACX7100-48L r6273 qfx5700 acx753 r6273 mx10008 mx10016 cbng acx7509 wbonl qfx5009 mx304 acx7908 ACX7024 ptx10002-36qdd mx10004 acx7900 cpcepadaptor qfx5230-64cd acx7332 acx7348 acx7340 ACX724 qfx5130-48c qfx5130-48cm ACX7024X qfx5240-64od qfx5240-64qd qfx5130e-32cd qfx5240-64xOSFP qfx5240-64xQSFPDD ptx10002-96c ptx-xxxxxx ptx10001-36mr-k ptx12008 srx4700 ACX7020_AC ACX7020_DC ACX7020X_AC ACX7020X_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5245-128cd qfx5121-32c qfx5121-48y qfx5121-48ym qfx5121-48t qfx5250-64oe qfx5250-64oe-l mx9608 qfx5340-64od qfx5340-64qd ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 EX5807 EX5810 ex4400-24mp ex4400-24p ex4400-24t ex4400-48f ex4400-48mp ex4400-48p ex4400-48t ex4400-24x ex4400-48mxp ex4400-48xp ptx12012 ptx10002-36-od ";
       container mpls-lsp-defaults {
         junos:product "olive m5 m10 m20 m40 m160 t640 t320 m40e TX Matrix ggsn-c m320 sammy m10i j2300 j4300 j6300 IRM m120 mx960 j4350 j6350 jsr2300 jsr4300 jsr6300 jsr4350 jsr6350 j2320 j2350 jsr2320 jsr2350 mx480 srx5800 sumatra ex3200-24t ex3200-24p ex3200-48t ex3200-48p ex4200-24f ex4200-24t ex4200-24p ex4200-48t ex4200-48p ex8208 ex8216 srx5600 mx240 txp srx3600 srx3400 srx210b srx210h srx210h-poe srx210h-p-m srx240b srx240h srx240h-poe srx240h-p-m srx630 srx650 srx680 sce srx100b srx100h srx110b-va srx110h-va srx110b-vb srx110h-vb srx110b-wl srx220h srx220h-poe srx220h-p-m ex2200-24t-4g ex2200-24p-4g ex2200-48t-4g ex2200-48p-4g ln1000-v fx1600_48 fx2160_48 qfx3500 dc_olive ptx5000 srx1400 ex4500-40f mx80 mx80-48t ptx9000 ex-xre srx240h-dc qfx3008-i fx-jvre qfx3000 qfx3500s mag8600 mag6611 mag6610 ex4200-48px ex4200-24px srx110h-wl srx110h-va-wl srx210be srx210he srx210he-poe ex2200-c-12t-2g qfx5000 ex2200-24t-dc-4g srx110h-vb-wl ex6210 ex3300-24t ex3300-24p ex3300-48t ex3300-48p ex3300-24t-dc ex3300-48t-bf srx210he-p-m ex2200-c-12p-2g mx5-t mx10-t mx40-t mx80-t vjx1000 ex4550-32f ex4550-32t srx550 mx80-p acx1000 acx2000 acx4000 qfx3600-16q qfx3600-i qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4600-40f ex4300-32f qfx5100-96s-8q vmx qfx5100-24q-2pf qfx5100-48s-6qf qfx5100-48t-6qf qfx5100-24q-2p qfx5100-48t-6q srx5400 qfx5100-24q-aa pvi-model vrr ptx1000 qfx10004 qfx10008 qfx10016 vqfx-10000 qfx5100-24q-2pi qfx7100-i qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 qfx10016 acx6160-t ptx10001-27cd ptx10008 qfx10008 qfx5220-32cd qfx5220-128c csrx ptx10003-81cd srx380-poe-ac crpd cmgd ptx10001-36mr acx753 qfx5130-32cd ptx10004 ex4300-48mp QFX7100-48L ACX7100-32C ACX7100-48L r6273 qfx5700 acx753 r6273 mx10008 mx10016 cbng acx7509 wbonl qfx5009 mx304 acx7908 ACX7024 ptx10002-36qdd mx10004 acx7900 cpcepadaptor qfx5230-64cd acx7332 acx7348 acx7340 ACX724 qfx5130-48c qfx5130-48cm ACX7024X qfx5240-64od qfx5240-64qd qfx5130e-32cd qfx5240-64xOSFP qfx5240-64xQSFPDD ptx10002-96c ptx-xxxxxx ptx10001-36mr-k ptx12008 srx4700 ACX7020_AC ACX7020_DC ACX7020X_AC ACX7020X_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5245-128cd qfx5121-32c qfx5121-48y qfx5121-48ym qfx5121-48t qfx5250-64oe qfx5250-64oe-l mx9608 qfx5340-64od qfx5340-64qd ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 EX5807 EX5810 ex4400-24mp ex4400-24p ex4400-24t ex4400-48f ex4400-48mp ex4400-48p ex4400-48t ex4400-24x ex4400-48mxp ex4400-48xp ptx12012 ptx10002-36-od ";
         leaf lsp-hold-priority {
           type int32;
           description
             "Default priority for holding resources";
           junos:product "olive m5 m10 m20 m40 m160 t640 t320 m40e TX Matrix ggsn-c m320 sammy m10i j2300 j4300 j6300 IRM m120 mx960 j4350 j6350 jsr2300 jsr4300 jsr6300 jsr4350 jsr6350 j2320 j2350 jsr2320 jsr2350 mx480 srx5800 sumatra ex3200-24t ex3200-24p ex3200-48t ex3200-48p ex4200-24f ex4200-24t ex4200-24p ex4200-48t ex4200-48p ex8208 ex8216 srx5600 mx240 txp srx3600 srx3400 srx210b srx210h srx210h-poe srx210h-p-m srx240b srx240h srx240h-poe srx240h-p-m srx630 srx650 srx680 sce srx100b srx100h srx110b-va srx110h-va srx110b-vb srx110h-vb srx110b-wl srx220h srx220h-poe srx220h-p-m ex2200-24t-4g ex2200-24p-4g ex2200-48t-4g ex2200-48p-4g ln1000-v fx1600_48 fx2160_48 qfx3500 dc_olive ptx5000 srx1400 ex4500-40f mx80 mx80-48t ptx9000 ex-xre srx240h-dc qfx3008-i fx-jvre qfx3000 qfx3500s mag8600 mag6611 mag6610 ex4200-48px ex4200-24px srx110h-wl srx110h-va-wl srx210be srx210he srx210he-poe ex2200-c-12t-2g qfx5000 ex2200-24t-dc-4g srx110h-vb-wl ex6210 ex3300-24t ex3300-24p ex3300-48t ex3300-48p ex3300-24t-dc ex3300-48t-bf srx210he-p-m ex2200-c-12p-2g mx5-t mx10-t mx40-t mx80-t vjx1000 ex4550-32f ex4550-32t srx550 mx80-p acx1000 acx2000 acx4000 qfx3600-16q qfx3600-i qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4600-40f ex4300-32f qfx5100-96s-8q vmx qfx5100-24q-2pf qfx5100-48s-6qf qfx5100-48t-6qf qfx5100-24q-2p qfx5100-48t-6q srx5400 qfx5100-24q-aa pvi-model vrr ptx1000 qfx10004 qfx10008 qfx10016 vqfx-10000 qfx5100-24q-2pi qfx7100-i qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 qfx10016 acx6160-t ptx10001-27cd ptx10008 qfx10008 qfx5220-32cd qfx5220-128c csrx ptx10003-81cd srx380-poe-ac crpd cmgd ptx10001-36mr acx753 qfx5130-32cd ptx10004 ex4300-48mp QFX7100-48L ACX7100-32C ACX7100-48L r6273 qfx5700 acx753 r6273 mx10008 mx10016 cbng acx7509 wbonl qfx5009 mx304 acx7908 ACX7024 ptx10002-36qdd mx10004 acx7900 cpcepadaptor qfx5230-64cd acx7332 acx7348 acx7340 ACX724 qfx5130-48c qfx5130-48cm ACX7024X qfx5240-64od qfx5240-64qd qfx5130e-32cd qfx5240-64xOSFP qfx5240-64xQSFPDD ptx10002-96c ptx-xxxxxx ptx10001-36mr-k ptx12008 srx4700 ACX7020_AC ACX7020_DC ACX7020X_AC ACX7020X_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5245-128cd qfx5121-32c qfx5121-48y qfx5121-48ym qfx5121-48t qfx5250-64oe qfx5250-64oe-l mx9608 qfx5340-64od qfx5340-64qd ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 EX5807 EX5810 ex4400-24mp ex4400-24p ex4400-24t ex4400-48f ex4400-48mp ex4400-48p ex4400-48t ex4400-24x ex4400-48mxp ex4400-48xp ptx12012 ptx10002-36-od ";
         }
         leaf lsp-setup-priority {
           type int32;
           description
             "Default priority for taking resources";
           junos:product "olive m5 m10 m20 m40 m160 t640 t320 m40e TX Matrix ggsn-c m320 sammy m10i j2300 j4300 j6300 IRM m120 mx960 j4350 j6350 jsr2300 jsr4300 jsr6300 jsr4350 jsr6350 j2320 j2350 jsr2320 jsr2350 mx480 srx5800 sumatra ex3200-24t ex3200-24p ex3200-48t ex3200-48p ex4200-24f ex4200-24t ex4200-24p ex4200-48t ex4200-48p ex8208 ex8216 srx5600 mx240 txp srx3600 srx3400 srx210b srx210h srx210h-poe srx210h-p-m srx240b srx240h srx240h-poe srx240h-p-m srx630 srx650 srx680 sce srx100b srx100h srx110b-va srx110h-va srx110b-vb srx110h-vb srx110b-wl srx220h srx220h-poe srx220h-p-m ex2200-24t-4g ex2200-24p-4g ex2200-48t-4g ex2200-48p-4g ln1000-v fx1600_48 fx2160_48 qfx3500 dc_olive ptx5000 srx1400 ex4500-40f mx80 mx80-48t ptx9000 ex-xre srx240h-dc qfx3008-i fx-jvre qfx3000 qfx3500s mag8600 mag6611 mag6610 ex4200-48px ex4200-24px srx110h-wl srx110h-va-wl srx210be srx210he srx210he-poe ex2200-c-12t-2g qfx5000 ex2200-24t-dc-4g srx110h-vb-wl ex6210 ex3300-24t ex3300-24p ex3300-48t ex3300-48p ex3300-24t-dc ex3300-48t-bf srx210he-p-m ex2200-c-12p-2g mx5-t mx10-t mx40-t mx80-t vjx1000 ex4550-32f ex4550-32t srx550 mx80-p acx1000 acx2000 acx4000 qfx3600-16q qfx3600-i qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4600-40f ex4300-32f qfx5100-96s-8q vmx qfx5100-24q-2pf qfx5100-48s-6qf qfx5100-48t-6qf qfx5100-24q-2p qfx5100-48t-6q srx5400 qfx5100-24q-aa pvi-model vrr ptx1000 qfx10004 qfx10008 qfx10016 vqfx-10000 qfx5100-24q-2pi qfx7100-i qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 qfx10016 acx6160-t ptx10001-27cd ptx10008 qfx10008 qfx5220-32cd qfx5220-128c csrx ptx10003-81cd srx380-poe-ac crpd cmgd ptx10001-36mr acx753 qfx5130-32cd ptx10004 ex4300-48mp QFX7100-48L ACX7100-32C ACX7100-48L r6273 qfx5700 acx753 r6273 mx10008 mx10016 cbng acx7509 wbonl qfx5009 mx304 acx7908 ACX7024 ptx10002-36qdd mx10004 acx7900 cpcepadaptor qfx5230-64cd acx7332 acx7348 acx7340 ACX724 qfx5130-48c qfx5130-48cm ACX7024X qfx5240-64od qfx5240-64qd qfx5130e-32cd qfx5240-64xOSFP qfx5240-64xQSFPDD ptx10002-96c ptx-xxxxxx ptx10001-36mr-k ptx12008 srx4700 ACX7020_AC ACX7020_DC ACX7020X_AC ACX7020X_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5245-128cd qfx5121-32c qfx5121-48y qfx5121-48ym qfx5121-48t qfx5250-64oe qfx5250-64oe-l mx9608 qfx5340-64od qfx5340-64qd ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 EX5807 EX5810 ex4400-24mp ex4400-24p ex4400-24t ex4400-48f ex4400-48mp ex4400-48p ex4400-48t ex4400-24x ex4400-48mxp ex4400-48xp ptx12012 ptx10002-36-od ";
         }
         leaf lsp-hoplimit {
           type int32;
           description
             "Maximum number of hops that can be traversed";
           junos:product "olive m5 m10 m20 m40 m160 t640 t320 m40e TX Matrix ggsn-c m320 sammy m10i j2300 j4300 j6300 IRM m120 mx960 j4350 j6350 jsr2300 jsr4300 jsr6300 jsr4350 jsr6350 j2320 j2350 jsr2320 jsr2350 mx480 srx5800 sumatra ex3200-24t ex3200-24p ex3200-48t ex3200-48p ex4200-24f ex4200-24t ex4200-24p ex4200-48t ex4200-48p ex8208 ex8216 srx5600 mx240 txp srx3600 srx3400 srx210b srx210h srx210h-poe srx210h-p-m srx240b srx240h srx240h-poe srx240h-p-m srx630 srx650 srx680 sce srx100b srx100h srx110b-va srx110h-va srx110b-vb srx110h-vb srx110b-wl srx220h srx220h-poe srx220h-p-m ex2200-24t-4g ex2200-24p-4g ex2200-48t-4g ex2200-48p-4g ln1000-v fx1600_48 fx2160_48 qfx3500 dc_olive ptx5000 srx1400 ex4500-40f mx80 mx80-48t ptx9000 ex-xre srx240h-dc qfx3008-i fx-jvre qfx3000 qfx3500s mag8600 mag6611 mag6610 ex4200-48px ex4200-24px srx110h-wl srx110h-va-wl srx210be srx210he srx210he-poe ex2200-c-12t-2g qfx5000 ex2200-24t-dc-4g srx110h-vb-wl ex6210 ex3300-24t ex3300-24p ex3300-48t ex3300-48p ex3300-24t-dc ex3300-48t-bf srx210he-p-m ex2200-c-12p-2g mx5-t mx10-t mx40-t mx80-t vjx1000 ex4550-32f ex4550-32t srx550 mx80-p acx1000 acx2000 acx4000 qfx3600-16q qfx3600-i qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4600-40f ex4300-32f qfx5100-96s-8q vmx qfx5100-24q-2pf qfx5100-48s-6qf qfx5100-48t-6qf qfx5100-24q-2p qfx5100-48t-6q srx5400 qfx5100-24q-aa pvi-model vrr ptx1000 qfx10004 qfx10008 qfx10016 vqfx-10000 qfx5100-24q-2pi qfx7100-i qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 qfx10016 acx6160-t ptx10001-27cd ptx10008 qfx10008 qfx5220-32cd qfx5220-128c csrx ptx10003-81cd srx380-poe-ac crpd cmgd ptx10001-36mr acx753 qfx5130-32cd ptx10004 ex4300-48mp QFX7100-48L ACX7100-32C ACX7100-48L r6273 qfx5700 acx753 r6273 mx10008 mx10016 cbng acx7509 wbonl qfx5009 mx304 acx7908 ACX7024 ptx10002-36qdd mx10004 acx7900 cpcepadaptor qfx5230-64cd acx7332 acx7348 acx7340 ACX724 qfx5130-48c qfx5130-48cm ACX7024X qfx5240-64od qfx5240-64qd qfx5130e-32cd qfx5240-64xOSFP qfx5240-64xQSFPDD ptx10002-96c ptx-xxxxxx ptx10001-36mr-k ptx12008 srx4700 ACX7020_AC ACX7020_DC ACX7020X_AC ACX7020X_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5245-128cd qfx5121-32c qfx5121-48y qfx5121-48ym qfx5121-48t qfx5250-64oe qfx5250-64oe-l mx9608 qfx5340-64od qfx5340-64qd ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 EX5807 EX5810 ex4400-24mp ex4400-24p ex4400-24t ex4400-48f ex4400-48mp ex4400-48p ex4400-48t ex4400-24x ex4400-48mxp ex4400-48xp ptx12012 ptx10002-36-od ";
         }
         leaf lsp-bandwidth {
           type int32;
           description
             "Default LSP Bandwidth";
           junos:product "olive m5 m10 m20 m40 m160 t640 t320 m40e TX Matrix ggsn-c m320 sammy m10i j2300 j4300 j6300 IRM m120 mx960 j4350 j6350 jsr2300 jsr4300 jsr6300 jsr4350 jsr6350 j2320 j2350 jsr2320 jsr2350 mx480 srx5800 sumatra ex3200-24t ex3200-24p ex3200-48t ex3200-48p ex4200-24f ex4200-24t ex4200-24p ex4200-48t ex4200-48p ex8208 ex8216 srx5600 mx240 txp srx3600 srx3400 srx210b srx210h srx210h-poe srx210h-p-m srx240b srx240h srx240h-poe srx240h-p-m srx630 srx650 srx680 sce srx100b srx100h srx110b-va srx110h-va srx110b-vb srx110h-vb srx110b-wl srx220h srx220h-poe srx220h-p-m ex2200-24t-4g ex2200-24p-4g ex2200-48t-4g ex2200-48p-4g ln1000-v fx1600_48 fx2160_48 qfx3500 dc_olive ptx5000 srx1400 ex4500-40f mx80 mx80-48t ptx9000 ex-xre srx240h-dc qfx3008-i fx-jvre qfx3000 qfx3500s mag8600 mag6611 mag6610 ex4200-48px ex4200-24px srx110h-wl srx110h-va-wl srx210be srx210he srx210he-poe ex2200-c-12t-2g qfx5000 ex2200-24t-dc-4g srx110h-vb-wl ex6210 ex3300-24t ex3300-24p ex3300-48t ex3300-48p ex3300-24t-dc ex3300-48t-bf srx210he-p-m ex2200-c-12p-2g mx5-t mx10-t mx40-t mx80-t vjx1000 ex4550-32f ex4550-32t srx550 mx80-p acx1000 acx2000 acx4000 qfx3600-16q qfx3600-i qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4600-40f ex4300-32f qfx5100-96s-8q vmx qfx5100-24q-2pf qfx5100-48s-6qf qfx5100-48t-6qf qfx5100-24q-2p qfx5100-48t-6q srx5400 qfx5100-24q-aa pvi-model vrr ptx1000 qfx10004 qfx10008 qfx10016 vqfx-10000 qfx5100-24q-2pi qfx7100-i qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 qfx10016 acx6160-t ptx10001-27cd ptx10008 qfx10008 qfx5220-32cd qfx5220-128c csrx ptx10003-81cd srx380-poe-ac crpd cmgd ptx10001-36mr acx753 qfx5130-32cd ptx10004 ex4300-48mp QFX7100-48L ACX7100-32C ACX7100-48L r6273 qfx5700 acx753 r6273 mx10008 mx10016 cbng acx7509 wbonl qfx5009 mx304 acx7908 ACX7024 ptx10002-36qdd mx10004 acx7900 cpcepadaptor qfx5230-64cd acx7332 acx7348 acx7340 ACX724 qfx5130-48c qfx5130-48cm ACX7024X qfx5240-64od qfx5240-64qd qfx5130e-32cd qfx5240-64xOSFP qfx5240-64xQSFPDD ptx10002-96c ptx-xxxxxx ptx10001-36mr-k ptx12008 srx4700 ACX7020_AC ACX7020_DC ACX7020X_AC ACX7020X_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5245-128cd qfx5121-32c qfx5121-48y qfx5121-48ym qfx5121-48t qfx5250-64oe qfx5250-64oe-l mx9608 qfx5340-64od qfx5340-64qd ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 EX5807 EX5810 ex4400-24mp ex4400-24p ex4400-24t ex4400-48f ex4400-48mp ex4400-48p ex4400-48t ex4400-24x ex4400-48mxp ex4400-48xp ptx12012 ptx10002-36-od ";
         }
         leaf lsp-retry-timer {
           type int32;
           junos:product "olive m5 m10 m20 m40 m160 t640 t320 m40e TX Matrix ggsn-c m320 sammy m10i j2300 j4300 j6300 IRM m120 mx960 j4350 j6350 jsr2300 jsr4300 jsr6300 jsr4350 jsr6350 j2320 j2350 jsr2320 jsr2350 mx480 srx5800 sumatra ex3200-24t ex3200-24p ex3200-48t ex3200-48p ex4200-24f ex4200-24t ex4200-24p ex4200-48t ex4200-48p ex8208 ex8216 srx5600 mx240 txp srx3600 srx3400 srx210b srx210h srx210h-poe srx210h-p-m srx240b srx240h srx240h-poe srx240h-p-m srx630 srx650 srx680 sce srx100b srx100h srx110b-va srx110h-va srx110b-vb srx110h-vb srx110b-wl srx220h srx220h-poe srx220h-p-m ex2200-24t-4g ex2200-24p-4g ex2200-48t-4g ex2200-48p-4g ln1000-v fx1600_48 fx2160_48 qfx3500 dc_olive ptx5000 srx1400 ex4500-40f mx80 mx80-48t ptx9000 ex-xre srx240h-dc qfx3008-i fx-jvre qfx3000 qfx3500s mag8600 mag6611 mag6610 ex4200-48px ex4200-24px srx110h-wl srx110h-va-wl srx210be srx210he srx210he-poe ex2200-c-12t-2g qfx5000 ex2200-24t-dc-4g srx110h-vb-wl ex6210 ex3300-24t ex3300-24p ex3300-48t ex3300-48p ex3300-24t-dc ex3300-48t-bf srx210he-p-m ex2200-c-12p-2g mx5-t mx10-t mx40-t mx80-t vjx1000 ex4550-32f ex4550-32t srx550 mx80-p acx1000 acx2000 acx4000 qfx3600-16q qfx3600-i qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4600-40f ex4300-32f qfx5100-96s-8q vmx qfx5100-24q-2pf qfx5100-48s-6qf qfx5100-48t-6qf qfx5100-24q-2p qfx5100-48t-6q srx5400 qfx5100-24q-aa pvi-model vrr ptx1000 qfx10004 qfx10008 qfx10016 vqfx-10000 qfx5100-24q-2pi qfx7100-i qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 qfx10016 acx6160-t ptx10001-27cd ptx10008 qfx10008 qfx5220-32cd qfx5220-128c csrx ptx10003-81cd srx380-poe-ac crpd cmgd ptx10001-36mr acx753 qfx5130-32cd ptx10004 ex4300-48mp QFX7100-48L ACX7100-32C ACX7100-48L r6273 qfx5700 acx753 r6273 mx10008 mx10016 cbng acx7509 wbonl qfx5009 mx304 acx7908 ACX7024 ptx10002-36qdd mx10004 acx7900 cpcepadaptor qfx5230-64cd acx7332 acx7348 acx7340 ACX724 qfx5130-48c qfx5130-48cm ACX7024X qfx5240-64od qfx5240-64qd qfx5130e-32cd qfx5240-64xOSFP qfx5240-64xQSFPDD ptx10002-96c ptx-xxxxxx ptx10001-36mr-k ptx12008 srx4700 ACX7020_AC ACX7020_DC ACX7020X_AC ACX7020X_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5245-128cd qfx5121-32c qfx5121-48y qfx5121-48ym qfx5121-48t qfx5250-64oe qfx5250-64oe-l mx9608 qfx5340-64od qfx5340-64qd ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 EX5807 EX5810 ex4400-24mp ex4400-24p ex4400-24t ex4400-48f ex4400-48mp ex4400-48p ex4400-48t ex4400-24x ex4400-48mxp ex4400-48xp ptx12012 ptx10002-36-od ";
         }
       }
     }
   }
   augment "/jgs:genstate" {
     description
       "Adds mpls-lsp-defaults-information container to top-level genstate 
       container";
     uses mpls-lsp-defaults-information-top;
   }
 }
