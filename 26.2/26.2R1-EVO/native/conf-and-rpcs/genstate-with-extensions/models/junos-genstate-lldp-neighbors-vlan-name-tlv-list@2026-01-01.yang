module junos-genstate-lldp-neighbors-vlan-name-tlv-list {
   yang-version 1;
   namespace "http://yang.juniper.net/junos/genstate/lldp-neighbors-vlan-name-tlv-list";
   prefix jglnvntl;

   import junos-genstate {
     prefix jgs;
     revision-date 2026-01-01;
   }

   import junos-common-types {
     prefix jt;
     revision-date 2026-01-01;
   }

   import junos-extension {
     prefix junos;
   }

   organization
     "Juniper Networks, Inc.";

   contact
     "Juniper Networks, Inc.

      1133 Innovation Way
      Sunnyvale, CA 94089

      +1 888 314-5822

      E-mail: yang-support@juniper.net";

   description
      "Junos genstate Yang module for lldp-neighbors-vlan-name-tlv-list.

      Copyright (c) 2026 Juniper Networks, Inc.
      All rights reserved.";

   revision 2026-01-01 {
     description "Junos: 26.2R1.7-EVO";
   }

   grouping lldp-neighbors-vlan-name-tlv-list-top {
     description
       "Top-level grouping";
     container lldp-neighbors-vlan-name-tlv-list {
       description
         "Top-level container";
       junos:product "olive t640 t320 TX Matrix mx960 mx480 srx5800 srx5600 mx240 txp srx3600 srx3400 fx1600_48 fx2160_48 qfx3500 dc_olive ptx5000 srx1400 mx80 mx80-48t ptx9000 qfx3008-i fx-jvre qfx3500s mx5-t mx10-t mx40-t mx80-t srx550 mx80-p acx1000 acx2000 acx4000 qfx3600-16q qfx3600-i qfx3600-16qs mx2020 mx2010 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2pf qfx5100-48s-6qf qfx5100-24q-2p srx5400 qfx5100-24q-aa pvi-model vrr ptx1000 qfx10004 qfx10008 qfx10016 vqfx-10000 qfx5100-24q-2pi qfx10000-elit sng_olive vsrx acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac crpd ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
       list lldp-interface-information-list {
         key "lldp-local-interface-name";
         junos:product "olive t640 t320 TX Matrix mx960 mx480 srx5800 srx5600 mx240 txp srx3600 srx3400 fx1600_48 fx2160_48 qfx3500 dc_olive ptx5000 srx1400 mx80 mx80-48t ptx9000 qfx3008-i fx-jvre qfx3500s mx5-t mx10-t mx40-t mx80-t srx550 mx80-p acx1000 acx2000 acx4000 qfx3600-16q qfx3600-i qfx3600-16qs mx2020 mx2010 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2pf qfx5100-48s-6qf qfx5100-24q-2p srx5400 qfx5100-24q-aa pvi-model vrr ptx1000 qfx10004 qfx10008 qfx10016 vqfx-10000 qfx5100-24q-2pi qfx10000-elit sng_olive vsrx acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac crpd ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
         leaf lldp-local-interface-name {
           type string;
         }
         list lldp-remote-interface-information {
           key "lldp-remote-chassis-id";
           junos:product "olive t640 t320 TX Matrix mx960 mx480 srx5800 srx5600 mx240 txp srx3600 srx3400 fx1600_48 fx2160_48 qfx3500 dc_olive ptx5000 srx1400 mx80 mx80-48t ptx9000 qfx3008-i fx-jvre qfx3500s mx5-t mx10-t mx40-t mx80-t srx550 mx80-p acx1000 acx2000 acx4000 qfx3600-16q qfx3600-i qfx3600-16qs mx2020 mx2010 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2pf qfx5100-48s-6qf qfx5100-24q-2p srx5400 qfx5100-24q-aa pvi-model vrr ptx1000 qfx10004 qfx10008 qfx10016 vqfx-10000 qfx5100-24q-2pi qfx10000-elit sng_olive vsrx acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac crpd ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
           leaf lldp-remote-chassis-id-subtype {
             type string;
             description
               "LLDP remote chassis ID subtype";
             junos:product "olive t640 t320 TX Matrix mx960 mx480 srx5800 srx5600 mx240 txp srx3600 srx3400 fx1600_48 fx2160_48 qfx3500 dc_olive ptx5000 srx1400 mx80 mx80-48t ptx9000 qfx3008-i fx-jvre qfx3500s mx5-t mx10-t mx40-t mx80-t srx550 mx80-p acx1000 acx2000 acx4000 qfx3600-16q qfx3600-i qfx3600-16qs mx2020 mx2010 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2pf qfx5100-48s-6qf qfx5100-24q-2p srx5400 qfx5100-24q-aa pvi-model vrr ptx1000 qfx10004 qfx10008 qfx10016 vqfx-10000 qfx5100-24q-2pi qfx10000-elit sng_olive vsrx acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac crpd ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
           }
           leaf lldp-remote-chassis-id {
             type string;
             description
               "LLDP remote chassis ID";
             junos:product "olive t640 t320 TX Matrix mx960 mx480 srx5800 srx5600 mx240 txp srx3600 srx3400 fx1600_48 fx2160_48 qfx3500 dc_olive ptx5000 srx1400 mx80 mx80-48t ptx9000 qfx3008-i fx-jvre qfx3500s mx5-t mx10-t mx40-t mx80-t srx550 mx80-p acx1000 acx2000 acx4000 qfx3600-16q qfx3600-i qfx3600-16qs mx2020 mx2010 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2pf qfx5100-48s-6qf qfx5100-24q-2p srx5400 qfx5100-24q-aa pvi-model vrr ptx1000 qfx10004 qfx10008 qfx10016 vqfx-10000 qfx5100-24q-2pi qfx10000-elit sng_olive vsrx acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac crpd ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
           }
           leaf lldp-remote-port-description {
             type string;
             description
               "LLDP remote port ID";
             junos:product "olive t640 t320 TX Matrix mx960 mx480 srx5800 srx5600 mx240 txp srx3600 srx3400 fx1600_48 fx2160_48 qfx3500 dc_olive ptx5000 srx1400 mx80 mx80-48t ptx9000 qfx3008-i fx-jvre qfx3500s mx5-t mx10-t mx40-t mx80-t srx550 mx80-p acx1000 acx2000 acx4000 qfx3600-16q qfx3600-i qfx3600-16qs mx2020 mx2010 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2pf qfx5100-48s-6qf qfx5100-24q-2p srx5400 qfx5100-24q-aa pvi-model vrr ptx1000 qfx10004 qfx10008 qfx10016 vqfx-10000 qfx5100-24q-2pi qfx10000-elit sng_olive vsrx acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac crpd ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
           }
           leaf lldp-remote-system-name {
             type string;
             description
               "Administratively assigned host name of remote neighbor";
             junos:product "olive t640 t320 TX Matrix mx960 mx480 srx5800 srx5600 mx240 txp srx3600 srx3400 fx1600_48 fx2160_48 qfx3500 dc_olive ptx5000 srx1400 mx80 mx80-48t ptx9000 qfx3008-i fx-jvre qfx3500s mx5-t mx10-t mx40-t mx80-t srx550 mx80-p acx1000 acx2000 acx4000 qfx3600-16q qfx3600-i qfx3600-16qs mx2020 mx2010 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2pf qfx5100-48s-6qf qfx5100-24q-2p srx5400 qfx5100-24q-aa pvi-model vrr ptx1000 qfx10004 qfx10008 qfx10016 vqfx-10000 qfx5100-24q-2pi qfx10000-elit sng_olive vsrx acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac crpd ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
           }
           leaf lldp-vlan-name-tlv-oui {
             type string;
             description
               "Organizationally Unique Identifier globally unique 
               assignednumber of the information received from the remote 
               system";
             junos:product "olive t640 t320 TX Matrix mx960 mx480 srx5800 srx5600 mx240 txp srx3600 srx3400 fx1600_48 fx2160_48 qfx3500 dc_olive ptx5000 srx1400 mx80 mx80-48t ptx9000 qfx3008-i fx-jvre qfx3500s mx5-t mx10-t mx40-t mx80-t srx550 mx80-p acx1000 acx2000 acx4000 qfx3600-16q qfx3600-i qfx3600-16qs mx2020 mx2010 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2pf qfx5100-48s-6qf qfx5100-24q-2p srx5400 qfx5100-24q-aa pvi-model vrr ptx1000 qfx10004 qfx10008 qfx10016 vqfx-10000 qfx5100-24q-2pi qfx10000-elit sng_olive vsrx acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac crpd ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
           }
           leaf lldp-vlan-name-tlv-subtype {
             type string;
             description
               "IEEE 802.1 VLAN name subtype VLAN name value of 
               theorganizationally defined information received from the 
               remote system";
             junos:product "olive t640 t320 TX Matrix mx960 mx480 srx5800 srx5600 mx240 txp srx3600 srx3400 fx1600_48 fx2160_48 qfx3500 dc_olive ptx5000 srx1400 mx80 mx80-48t ptx9000 qfx3008-i fx-jvre qfx3500s mx5-t mx10-t mx40-t mx80-t srx550 mx80-p acx1000 acx2000 acx4000 qfx3600-16q qfx3600-i qfx3600-16qs mx2020 mx2010 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2pf qfx5100-48s-6qf qfx5100-24q-2p srx5400 qfx5100-24q-aa pvi-model vrr ptx1000 qfx10004 qfx10008 qfx10016 vqfx-10000 qfx5100-24q-2pi qfx10000-elit sng_olive vsrx acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac crpd ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
           }
           list lldp-neighbor-vlan-name-tlv-list {
             key "lldp-vlan-name-tlv-name";
             junos:product "olive t640 t320 TX Matrix mx960 mx480 srx5800 srx5600 mx240 txp srx3600 srx3400 fx1600_48 fx2160_48 qfx3500 dc_olive ptx5000 srx1400 mx80 mx80-48t ptx9000 qfx3008-i fx-jvre qfx3500s mx5-t mx10-t mx40-t mx80-t srx550 mx80-p acx1000 acx2000 acx4000 qfx3600-16q qfx3600-i qfx3600-16qs mx2020 mx2010 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2pf qfx5100-48s-6qf qfx5100-24q-2p srx5400 qfx5100-24q-aa pvi-model vrr ptx1000 qfx10004 qfx10008 qfx10016 vqfx-10000 qfx5100-24q-2pi qfx10000-elit sng_olive vsrx acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac crpd ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             leaf lldp-vlan-name-tlv-tag {
               type uint32;
               description
                 "VLAN tag";
               junos:product "olive t640 t320 TX Matrix mx960 mx480 srx5800 srx5600 mx240 txp srx3600 srx3400 fx1600_48 fx2160_48 qfx3500 dc_olive ptx5000 srx1400 mx80 mx80-48t ptx9000 qfx3008-i fx-jvre qfx3500s mx5-t mx10-t mx40-t mx80-t srx550 mx80-p acx1000 acx2000 acx4000 qfx3600-16q qfx3600-i qfx3600-16qs mx2020 mx2010 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2pf qfx5100-48s-6qf qfx5100-24q-2p srx5400 qfx5100-24q-aa pvi-model vrr ptx1000 qfx10004 qfx10008 qfx10016 vqfx-10000 qfx5100-24q-2pi qfx10000-elit sng_olive vsrx acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac crpd ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             }
             leaf lldp-vlan-name-tlv-name {
               type string;
               description
                 "VLAN name";
               junos:product "olive t640 t320 TX Matrix mx960 mx480 srx5800 srx5600 mx240 txp srx3600 srx3400 fx1600_48 fx2160_48 qfx3500 dc_olive ptx5000 srx1400 mx80 mx80-48t ptx9000 qfx3008-i fx-jvre qfx3500s mx5-t mx10-t mx40-t mx80-t srx550 mx80-p acx1000 acx2000 acx4000 qfx3600-16q qfx3600-i qfx3600-16qs mx2020 mx2010 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2pf qfx5100-48s-6qf qfx5100-24q-2p srx5400 qfx5100-24q-aa pvi-model vrr ptx1000 qfx10004 qfx10008 qfx10016 vqfx-10000 qfx5100-24q-2pi qfx10000-elit sng_olive vsrx acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac crpd ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             }
             leaf lldp-vlan-name-tlv-remote-index {
               type uint32;
               description
                 "Value used by agent to identify a particular 
                 unrecognizedorganizationally defined information";
               junos:product "olive t640 t320 TX Matrix mx960 mx480 srx5800 srx5600 mx240 txp srx3600 srx3400 fx1600_48 fx2160_48 qfx3500 dc_olive ptx5000 srx1400 mx80 mx80-48t ptx9000 qfx3008-i fx-jvre qfx3500s mx5-t mx10-t mx40-t mx80-t srx550 mx80-p acx1000 acx2000 acx4000 qfx3600-16q qfx3600-i qfx3600-16qs mx2020 mx2010 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2pf qfx5100-48s-6qf qfx5100-24q-2p srx5400 qfx5100-24q-aa pvi-model vrr ptx1000 qfx10004 qfx10008 qfx10016 vqfx-10000 qfx5100-24q-2pi qfx10000-elit sng_olive vsrx acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac crpd ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             }
           }
         }
       }
     }
   }
   augment "/jgs:genstate" {
     description
       "Adds lldp-neighbors-vlan-name-tlv-list container to top-level 
       genstate container";
     uses lldp-neighbors-vlan-name-tlv-list-top;
   }
 }
