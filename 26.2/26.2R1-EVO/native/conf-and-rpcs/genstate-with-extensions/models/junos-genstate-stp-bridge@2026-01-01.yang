module junos-genstate-stp-bridge {
   yang-version 1;
   namespace "http://yang.juniper.net/junos/genstate/stp-bridge";
   prefix jgsb;

   import junos-genstate {
     prefix jgs;
     revision-date 2026-01-01;
   }

   import junos-common-types {
     prefix jt;
     revision-date 2026-01-01;
   }

   import junos-extension {
     prefix junos;
   }

   organization
     "Juniper Networks, Inc.";

   contact
     "Juniper Networks, Inc.

      1133 Innovation Way
      Sunnyvale, CA 94089

      +1 888 314-5822

      E-mail: yang-support@juniper.net";

   description
      "Junos genstate Yang module for stp-bridge.

      Copyright (c) 2026 Juniper Networks, Inc.
      All rights reserved.";

   revision 2026-01-01 {
     description "Junos: 26.2R1.7-EVO";
   }

   grouping stp-bridge-top {
     description
       "Top-level grouping";
     container stp-bridge {
       description
         "Information about STP bridge parameters";
       junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
       list routing-instance-information {
         key "routing-instance-name";
         junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
         leaf routing-instance-name {
           type string;
           description
             "Routing instance name";
         }
         leaf context-id {
           type int32;
           description
             "Context identifier";
         }
         leaf bpdu-destination-mac-address {
           type string;
           description
             "Destination MAC address in the spanning tree BPDUs";
         }
         leaf protocol {
           type string;
           description
             "Enabled protocol";
         }
         container cist-bridge-parameters {
           description
             "STP bridge parameters for Common and Internal Spanning Tree";
           junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
           leaf cist-id {
             type int32;
             description
               "CIST identifier";
           }
           leaf root-port {
             type string;
             description
               "Root port";
           }
           leaf root-cost {
             type uint32;
             description
               "Root cost";
           }
           leaf internal-root-cost {
             type uint32;
             description
               "CIST internal root cost";
           }
           leaf hello-time-learned {
             type int32;
             description
               "Hello time";
           }
           leaf max-age-learned {
             type int32;
             description
               "Maximum age for received BPDUs";
           }
           leaf forward-delay-learned {
             type int32;
             description
               "Forward delay";
           }
           leaf msg-age {
             type int32;
             description
               "Age of the received BPDU";
           }
           leaf hop-count {
             type int32;
             description
               "Hop count received from the root bridge";
           }
           leaf time-since-last-tc {
             type int32;
             description
               "Time since last topology change";
           }
           leaf topology-change-count {
             type int32;
             description
               "Number of topology changes";
           }
           leaf extended-system-id {
             type int32;
             description
               "Extended system identifier";
           }
           leaf internal-instance-id {
             type int32;
             description
               "Internal instance identifier";
           }
           leaf hello-time-configured {
             type int32;
             description
               "Hello time configured on this bridge";
           }
           leaf max-age-configured {
             type int32;
             description
               "Maximum age configured on this bridge";
           }
           leaf forward-delay-configured {
             type int32;
             description
               "Forward delay configured on this bridge";
           }
           leaf max-hop-count-configured {
             type int32;
             description
               "Maximum hop count configured on this bridge";
           }
           leaf path-cost-method {
             type string;
             description
               "Type of path cost method currently in use";
           }
           container root-bridge {
             description
               "Root bridge identifier";
             junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             leaf bridge-priority {
               type int32;
               description
                 "Bridge priority";
               junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             }
             leaf bridge-mac {
               type string;
               description
                 "Media access control address of bridge";
               junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             }
           }
           container regional-root-bridge {
             description
               "CIST regional root bridge identifier";
             junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             leaf bridge-priority {
               type int32;
               description
                 "Bridge priority";
               junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             }
             leaf bridge-mac {
               type string;
               description
                 "Media access control address of bridge";
               junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             }
           }
           container this-bridge {
             description
               "ID of bridge";
             junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             leaf bridge-priority {
               type int32;
               description
                 "Bridge priority";
               junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             }
             leaf bridge-mac {
               type string;
               description
                 "Media access control address of bridge";
               junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             }
           }
         }
         list msti-bridge-parameters {
           key "msti-id";
           description
             "STP bridge parameters for Multiple Spanning Tree instances";
           junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
           leaf msti-id {
             type int32;
             description
               "MSTI ID";
           }
           leaf root-port {
             type string;
             description
               "Root port";
           }
           leaf root-cost {
             type uint32;
             description
               "Root cost";
           }
           leaf hello-time-learned {
             type int32;
             description
               "Hello time";
           }
           leaf max-age-learned {
             type int32;
             description
               "Maximum age for received BPDUs";
           }
           leaf forward-delay-learned {
             type int32;
             description
               "Forward delay";
           }
           leaf max-hop-count-configured {
             type int32;
             description
               "Maximum hop count configured on this bridge";
           }
           leaf hop-count {
             type int32;
             description
               "Hop count received from the root bridge";
           }
           leaf time-since-last-tc {
             type int32;
             description
               "Time since last topology change";
           }
           leaf topology-change-count {
             type int32;
             description
               "Number of topology changes";
           }
           leaf internal-instance-id {
             type int32;
             description
               "Internal instance identifier";
           }
           container msti-regional-root-bridge {
             description
               "MSTI regional root identifier";
             junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             leaf bridge-priority {
               type int32;
               description
                 "Bridge priority";
               junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             }
             leaf bridge-mac {
               type string;
               description
                 "Media access control address of bridge";
               junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             }
           }
           container this-bridge {
             description
               "ID of bridge";
             junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             leaf bridge-priority {
               type int32;
               description
                 "Bridge priority";
               junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             }
             leaf bridge-mac {
               type string;
               description
                 "Media access control address of bridge";
               junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             }
           }
         }
         list vst-bridge-parameters {
           key "vlan-id";
           description
             "STP bridge parameters for VLAN Spanning Tree";
           junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
           leaf vlan-id {
             type int32;
             description
               "VLAN identifier";
           }
           leaf root-port {
             type string;
             description
               "Root port";
           }
           leaf root-cost {
             type uint32;
             description
               "Root cost";
           }
           leaf hello-time-learned {
             type int32;
             description
               "Hello time";
           }
           leaf max-age-learned {
             type int32;
             description
               "Maximum age for received BPDUs";
           }
           leaf forward-delay-learned {
             type int32;
             description
               "Forward delay";
           }
           leaf msg-age {
             type int32;
             description
               "Age of the received BPDU";
           }
           leaf time-since-last-tc {
             type int32;
             description
               "Time since last topology change";
           }
           leaf topology-change-count {
             type int32;
             description
               "Number of topology changes";
           }
           leaf extended-system-id {
             type int32;
             description
               "Extended system identifier";
           }
           leaf hello-time-configured {
             type int32;
             description
               "Hello time configured on this bridge";
           }
           leaf max-age-configured {
             type int32;
             description
               "Maximum age configured on this bridge";
           }
           leaf forward-delay-configured {
             type int32;
             description
               "Forward delay configured on this bridge";
           }
           leaf path-cost-method {
             type string;
             description
               "Type of path cost method currently in use";
           }
           container root-bridge {
             description
               "Root bridge identifier";
             junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             leaf bridge-priority {
               type int32;
               description
                 "Bridge priority";
               junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             }
             leaf bridge-mac {
               type string;
               description
                 "Media access control address of bridge";
               junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             }
           }
           container this-bridge {
             description
               "ID of bridge";
             junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             leaf bridge-priority {
               type int32;
               description
                 "Bridge priority";
               junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             }
             leaf bridge-mac {
               type string;
               description
                 "Media access control address of bridge";
               junos:product "olive mx960 mx480 srx5800 srx5600 mx240 srx3600 srx3400 srx210b srx210h srx210h-poe srx210h-p-m srx240b srx240h srx240h-poe srx240h-p-m srx630 srx650 srx680 srx100b srx100h srx110b-va srx110h-va srx110b-vb srx110h-vb srx110b-wl srx220h srx220h-poe srx220h-p-m ln1000-v dc_olive ptx5000 srx1400 mx80 mx80-48t ptx9000 srx240h-dc qfx3500s srx110h-wl srx110h-va-wl srx210be srx210he srx210he-poe srx110h-vb-wl srx210he-p-m mx5-t mx10-t mx40-t mx80-t srx550 mx80-p acx1000 acx2000 acx4000 qfx3600-16qs mx2020 mx2010 ln2600 ex8208-j ex8216-j ex4300-24p ex4300-24t ex4300-48p ex4300-48t ex4300-48t-bf ex4300-48t-dc ex4300-48t-dc-bf ex9204 ex9208 ex9214 mx104 acx2100 acx2200 acx1100 ptx3000 qfx5100-48s-6q ex4300-32f qfx5100-96s-8q vmx qfx5100-24q-2p srx5400 qfx5100-24q-aa pvi-model vrr ptx1000 qfx10004 qfx10008 qfx10016 vqfx-10000 qfx10000-elit sng_olive srx240b2 srx240h2 srx240h2-poe srx240h2-dc vsrx srx100h2 srx110h2-va srx110h2-vb srx210he2 srx210he2-poe srx220h2 srx220h2-poe acx500-o-poe-dc acx500-o-poe-ac acx500-o-dc acx500-o-ac acx500-dc acx500-ac ptx21000 srxtvp srx550m qfx5200-32c-32q acx5048 acx5096 srx300 srx300-lem srx320 srx320-lem srx320-poe srx320-poe-lem srx340 srx340-lem srx345 srx345-lem mx2008 mxtsr80 mx10001 mx10002 ptx10003-160c srx320-lte-aa srx320-lte-ae srx320-poe-lte-aa srx320-poe-lte-ae srx345-dual-ac srx345-dc ex9251 ex9253 qfx10002-60c ptx10003-80c qfx10003-160c qfx10003-80c ptx10016 ptx10001-27cd ptx10008 qfx5220-32cd qfx5220-128c ptx10003-81cd srx380-poe-ac ptx10001-36mr acx753 qfx5130-32cd ptx10004 QFX7100-48L ACX7100-32C ACX7100-48L r6273 qfx5700 acx7509 wbonl qfx5009 mx304 acx7908 ACX7024 ptx10002-36qdd qfx5230-64cd acx7332 acx7348 qfx5130-48c qfx5130-48cm ACX7024X qfx5240-64od qfx5240-64qd qfx5130e-32cd ptx10001-36mr-k ptx12008 ACX7020_AC ACX7020_DC ptx12000 qfx5241-32od qfx5241-32qd qfx5241-64od qfx5241-64qd ACX7100-32C-K ACX7100-48L-K mx301 ACX7332X ACX7372XC ACX73102XC ptx10002-60mr ptx10002-36cd qfx5241e_64od qfx5241e_64qd qfx5140-24cd8o ACX7122X qfx5250-64oe qfx5250-64oe-l ptx10002kx UFISPACE_S9600_32X UFISPACE_S9600_72XC UFISPACE_S9600_102XC UFISPACE_S9500_22XST srx400 srx400-c srx400-w-us srx400-w-ww srx400-cw-us srx400-cw-ww srx440 srx440-2ac srx440-c srx440-c-2ac ACX7048 ACX7030 ptx12012 ptx10002-36-od ";
             }
           }
         }
       }
     }
   }
   augment "/jgs:genstate" {
     description
       "Adds stp-bridge container to top-level genstate container";
     uses stp-bridge-top;
   }
 }
