module jnx-aug-openconfig-if-ip {

    yang-version "1";

    namespace "http://yang.juniper.net/openconfig/augment/if-ip";

    prefix "jnx-oc-ip";

    import openconfig-interfaces { prefix oc-if; }
    import openconfig-if-ip { prefix oc-ip; }
    import openconfig-yang-types { prefix oc-yang; }

    organization "Juniper Networks";

    revision "2016-06-20" {
	description "ARP + ND + IPv6 RA Extensions";
	reference "TBD";
    }

    grouping jnx-ipv4-state-neighbor {
	leaf host-name {
	    type string;
	    description "Host name for this neighbor entry";

	}

	leaf table-id {
	    type uint32;
	    description "Routing table ID for this neighbor entry";
	    
	}

	leaf neighbor-state {
	    type enumeration {
		enum INCOMPLETE {
		  description
		  "Address resolution is in progress, and the link-layer
		  address of the neighbor has not yet been
		  determined."; 
		}
		enum REACHABLE {
		    description
		    "Roughly speaking, the neighbor is known to have been
		    reachable recently (within tens of seconds ago).";
		}
		enum PROBE {
		    description
		    "The neighbor is no longer known to be reachable, and
		    unicast Neighbor Solicitation probes are being sent
		    to verify reachability.";
		}
		enum PERM {
		    description
		    "The neighbor is statically configured";
		}
	    }
	    description "ARP neighbor FSM state";

	}

	leaf expiry {
	    type uint32;
	    description "lifetime of ARP neighbor entry";
	}

	leaf is-publish {
	    type boolean;
	    description "whether the ARP neighbor is a published one";
	}

	leaf interface-name {
	    type string;
	    description "interface on which this neighbor entry was learnt";
	}

	leaf logical-router-id {
	    type uint8;
	    description "logical router ID for this neighbor entry";
	}

    }


    grouping jnx-ipv6-state-neighbor {
	leaf table-id {
	    type uint32;
	    description "Routing table ID for this neighbor entry";

	}

	leaf is-secure {
	    type boolean;
	    description "whether the neighbor was learnt from a secure NS message";
	}

	leaf expiry {
	    type uint32;
	    description "lifetime of this NDP entry";
	}

	leaf is-publish {
	    type boolean;
	    description "whether the NDP neighbor is a published one";
	}

	leaf interface-name {
	    type string;
	    description "interface on which this neighbor entry was learnt";
	}

	leaf logical-router-id {
	    type uint8;
	    description "logical router ID for this neighbor entry";
	}

    }

    grouping jnx-ipv6-ra-interface {
      leaf name { 
          type string;
          description "Name of the interface"; 
      }
      leaf initial-adv-sent { 
          type uint16; 
          description "Number of initial advertisements sent";
      }
      leaf adv-sent { 
          type uint64; 
          description "Number of advertisements sent";
      }
      leaf adv-received { 
          type uint64; 
          description "Number of advertisements received";
      }
      leaf solicits-received { 
          type uint64; 
          description "Number of solicits received";
      }
      leaf last-adv-time { 
          type uint32; 
          description "Time (in seconds) since last advertisement sent";
      }
      leaf last-solicit-time { 
          type uint32; 
          description "Time (in seconds) since last solicit received";
      }
    }

    augment "/oc-if:interfaces/oc-if:interface/oc-if:subinterfaces/" +
	    "oc-if:subinterface" +
	    "/oc-ip:ipv4/oc-ip:neighbors/oc-ip:neighbor/oc-ip:state" {

	    uses jnx-ipv4-state-neighbor;
    }

    augment "/oc-if:interfaces/oc-if:interface/oc-if:subinterfaces/" +
	    "oc-if:subinterface" +
	    "/oc-ip:ipv6/oc-ip:neighbors/oc-ip:neighbor/oc-ip:state" {

	    uses jnx-ipv6-state-neighbor;
    }

}
