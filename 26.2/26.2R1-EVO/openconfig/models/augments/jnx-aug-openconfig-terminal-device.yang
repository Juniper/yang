module jnx-aug-openconfig-terminal-device {
    yang-version "1";

    namespace "http://yang.juniper.net/openconfig/augment/terminal-device";

    prefix "jnx-oc-terminal-device";

    import openconfig-platform { prefix oc-platform; }
    import openconfig-terminal-device { prefix oc-terminal-device;}
    import openconfig-yang-types { prefix oc-yang; }
    import junos-extension { prefix junos; }

    organization "Juniper Networks";

    description
       "This module contains JUNOS augments to OpenConfig terminal-device model";

    revision "2024-08-30" {
        description "Augmenting new leaves to support OC-terminal-devices to native config translation";
    }

    augment "/oc-terminal-device:terminal-device" {
      junos:translation-script "openconfig-terminal-device.slax";
    }
}
