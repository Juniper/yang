/*
 * Copyright (c) 2019 Juniper Networks, Inc.
 * All rights reserved.
 */
 module junos-rpc-firewall {
   namespace "http://yang.juniper.net/junos/rpc/firewall";

   prefix firewall;

   import junos-common-types {
     prefix jt;
   }

   organization "Juniper Networks, Inc.";

   contact "yang-support@juniper.net";

   description "Junos RPC YANG module for firewall command(s)";

   revision 2019-01-01 {
     description "Junos: 18.2R3";
   }

   rpc get-firewall-information {
     description "Show firewall information";
     input {
       uses command-forwarding;
       leaf application {
         description "Owner application";
         type enumeration {
           enum "cfm" {
             description "Statistics for implicit filters for CFM";
           }
           enum "rmps" {
             description "Statistics for implicit filters for RMPS";
           }
           enum "eswd" {
             description "Statistics for implicit filters for eswd";
           }
           enum "lsp" {
             description "Statistics for implicit filters for lsp";
           }
         }
       }
       leaf terse {
         description "Show filter names only";
         type empty;
       }
       leaf detail {
         description "Show filter statistics with enhanced policer statistics";
         type empty;
       }
     }
     output {
       choice output_c {
         case output-tag {
           leaf output {
             type string;
           }
         }
         case actual-tag {
           anyxml firewall-information;
         }
         case multichassis-tag {
           anyxml multi-routing-engine-results;
         }
       }
     }
   }
   rpc get-firewall-counter-information {
     description "Counter name";
     input {
       uses command-forwarding;
       leaf countername {
         description "Counter name";
         type string;
         mandatory true;
       }
       leaf filter {
         description "Filter name";
         type string;
         mandatory true;
       }
       leaf detail {
         description "Show filter statistics with enhanced policer statistics";
         type empty;
       }
       leaf application {
         description "Owner application";
         type enumeration {
           enum "cfm" {
             description "Statistics for implicit filters for CFM";
           }
           enum "rmps" {
             description "Statistics for implicit filters for RMPS";
           }
           enum "eswd" {
             description "Statistics for implicit filters for eswd";
           }
           enum "lsp" {
             description "Statistics for implicit filters for lsp";
           }
         }
       }
     }
     output {
       choice output_c {
         case output-tag {
           leaf output {
             type string;
           }
         }
         case actual-tag {
           anyxml firewall-information;
         }
         case multichassis-tag {
           anyxml multi-routing-engine-results;
         }
       }
     }
   }
   rpc get-firewall-filter-information {
     description "Filter name";
     input {
       uses command-forwarding;
       leaf filtername {
         description "Filter name";
         type string;
         mandatory true;
       }
       leaf counter {
         description "Counter name";
         type string;
       }
       leaf detail {
         description "Show filter statistics with enhanced policer statistics";
         type empty;
       }
       leaf application {
         description "Owner application";
         type enumeration {
           enum "cfm" {
             description "Statistics for implicit filters for CFM";
           }
           enum "rmps" {
             description "Statistics for implicit filters for RMPS";
           }
           enum "eswd" {
             description "Statistics for implicit filters for eswd";
           }
           enum "lsp" {
             description "Statistics for implicit filters for lsp";
           }
         }
       }
     }
     output {
       choice output_c {
         case output-tag {
           leaf output {
             type string;
           }
         }
         case actual-tag {
           anyxml firewall-information;
         }
         case multichassis-tag {
           anyxml multi-routing-engine-results;
         }
       }
     }
   }
   rpc get-filter-version {
     description "Show filter version installed";
     input {
       leaf filtername {
         description "Filter name";
         type string;
       }
     }
     output {
       choice output_c {
         case output-tag {
           leaf output {
             type string;
           }
         }
         case actual-tag {
           anyxml firewall-information;
         }
         case multichassis-tag {
           anyxml multi-routing-engine-results;
         }
       }
     }
   }
   rpc get-firewall-filter-regex-information {
     description "Show filter using regular expression";
     input {
       leaf filtername {
         description "Regular expression of filter names";
         type jt:regular-expression;
       }
       leaf logical-system {
         description "Name of logical system, or 'all'";
         type string {
         }
       }
     }
     output {
       choice output_c {
         case output-tag {
           leaf output {
             type string;
           }
         }
         case actual-tag {
           anyxml firewall-information;
         }
         case multichassis-tag {
           anyxml multi-routing-engine-results;
         }
       }
     }
   }
   rpc get-firewall-log-information {
     description "Show log entries for firewall activity";
     input {
       leaf get-firewall-log-detailed-information {
         description "Display detailed output";
         type empty;
       }
       leaf interface {
         description "Interface name";
         type string;
       }
       leaf logical-system {
         description "Name of logical system, or 'all'";
         type string {
         }
       }
     }
     output {
       choice output_c {
         case output-tag {
           leaf output {
             type string;
           }
         }
         case actual-tag {
           anyxml firewall-log-information;
         }
         case multichassis-tag {
           anyxml multi-routing-engine-results;
         }
       }
     }
   }
   rpc get-firewall-prefix-action-information {
     description "Show prefix-action statistics for a filter";
     input {
       leaf filter {
         description "Filter name";
         type string;
         mandatory true;
       }
       leaf prefix-action {
         description "Prefix-action name";
         type string;
         mandatory true;
       }
       leaf from {
         description "Starting counter or policer";
         default "0";
         type union {
           type string {
             pattern "<.*>|$.*";
           }
           type uint32 {
             range "0 .. 65535";
           }
         }
       }
       leaf to {
         description "Ending counter or policer";
         default "65535";
         type union {
           type string {
             pattern "<.*>|$.*";
           }
           type uint32 {
             range "0 .. 65535";
           }
         }
       }
       leaf logical-system {
         description "Name of logical system, or 'all'";
         type string {
         }
       }
     }
     output {
       choice output_c {
         case output-tag {
           leaf output {
             type string;
           }
         }
         case actual-tag {
           anyxml firewall-prefix-action-information;
         }
         case multichassis-tag {
           anyxml multi-routing-engine-results;
         }
       }
     }
   }
   rpc get-firewall-templates-reference-counts {
     description "Show filter templates reference count for subscribers";
     output {
       choice output_c {
         case output-tag {
           leaf output {
             type string;
           }
         }
         case actual-tag {
           anyxml firewall-templates-in-use;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
