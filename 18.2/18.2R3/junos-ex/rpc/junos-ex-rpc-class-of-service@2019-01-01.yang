/*
 * Copyright (c) 2019 Juniper Networks, Inc.
 * All rights reserved.
 */
 module junos-ex-rpc-class-of-service {
   namespace "http://yang.juniper.net/junos-ex/rpc/class-of-service";

   prefix class-of-service;

   import junos-common-types {
     prefix jt;
   }

   organization "Juniper Networks, Inc.";

   contact "yang-support@juniper.net";

   description "Junos RPC YANG module for class-of-service command(s)";

   revision 2019-01-01 {
     description "Junos: 18.2R3";
   }

   rpc get-cos-information {
     description "Show class-of-service (CoS) information";
     output {
       choice output_c {
         case output-tag {
           leaf output {
             type string;
           }
         }
         case actual-tag {
           anyxml cos-information;
         }
         case multichassis-tag {
           anyxml multi-routing-engine-results;
         }
       }
     }
   }
   rpc get-cos-forwarding-class-information {
     description "Show mapping of forwarding class names to queue numbers";
     output {
       choice output_c {
         case output-tag {
           leaf output {
             type string;
           }
         }
         case actual-tag {
           anyxml cos-forwarding-class-information;
         }
         case multichassis-tag {
           anyxml multi-routing-engine-results;
         }
       }
     }
   }
   rpc get-cos-drop-profile-information {
     description "Show interpolated data points of named drop profile";
     input {
       leaf profile-name {
         description "Name of drop profile";
         type string;
       }
     }
     output {
       choice output_c {
         case output-tag {
           leaf output {
             type string;
           }
         }
         case actual-tag {
           anyxml cos-drop-profile-information;
         }
         case multichassis-tag {
           anyxml multi-routing-engine-results;
         }
       }
     }
   }
   rpc get-cos-classifier-information {
     description "Show mapping of code point to forwarding class/loss priority";
     input {
       leaf classifier-name {
         description "Name of classifier";
         type string;
       }
       leaf type {
         description "Type of classifier";
         type enumeration {
           enum "dscp" {
             description "Differentiated Services code point (DSCP)";
           }
           enum "dscp-ipv6" {
             description "Differentiated Services code point (DSCP) for IPv6";
           }
           enum "exp" {
             description "MPLS experimental code point";
           }
           enum "ieee-802.1" {
             description "IEEE-802.1 code point";
           }
           enum "inet-precedence" {
             description "IPv4 precedence code point";
           }
           enum "ieee-802.1ad" {
             description "IEEE-802.1ad (DEI) code point";
           }
           enum "inet6-precedence" {
             description "IPv6 precedence code point";
           }
         }
       }
     }
     output {
       choice output_c {
         case output-tag {
           leaf output {
             type string;
           }
         }
         case actual-tag {
           anyxml cos-classifier-information;
         }
         case multichassis-tag {
           anyxml multi-routing-engine-results;
         }
       }
     }
   }
   rpc get-cos-rewrite-information {
     description "Show mapping of forwarding class/loss priority to code point";
     input {
       leaf rewrite-rule-name {
         description "Name of rewrite rule";
         type string;
       }
       leaf type {
         description "Type of rewrite rule";
         type enumeration {
           enum "dscp" {
             description "Differentiated Services code point (DSCP)";
           }
           enum "dscp-ipv6" {
             description "Differentiated Services code point (DSCP) for IPv6";
           }
           enum "exp" {
             description "MPLS experimental code point";
           }
           enum "ieee-802.1" {
             description "IEEE-802.1 code point";
           }
           enum "inet-precedence" {
             description "IPv4 precedence code point";
           }
           enum "frame-relay-de" {
             description "Frame relay discard eligible bit code point";
           }
           enum "ieee-802.1ad" {
             description "IEEE-802.1ad (DEI) code point";
           }
           enum "inet6-precedence" {
             description "IPv6 precedence code point";
           }
         }
       }
     }
     output {
       choice output_c {
         case output-tag {
           leaf output {
             type string;
           }
         }
         case actual-tag {
           anyxml cos-rewrite-information;
         }
         case multichassis-tag {
           anyxml multi-routing-engine-results;
         }
       }
     }
   }
   rpc get-cos-multi-destination-information {
     description "Show multi destination";
     output {
       choice output_c {
         case output-tag {
           leaf output {
             type string;
           }
         }
         case actual-tag {
           anyxml cos-multi-destination-information;
         }
         case multichassis-tag {
           anyxml multi-routing-engine-results;
         }
       }
     }
   }
   rpc get-cos-code-point-map-information {
     description "Show mapping of symbolic name to code point bit pattern";
     input {
       leaf type {
         description "Type of code point alias";
         type enumeration {
           enum "dscp" {
             description "Differentiated Services code point (DSCP)";
           }
           enum "dscp-ipv6" {
             description "Differentiated Services code point (DSCP) for IPv6";
           }
           enum "exp" {
             description "MPLS experimental code point";
           }
           enum "ieee-802.1" {
             description "IEEE-802.1 code point";
           }
           enum "inet-precedence" {
             description "IPv4 precedence code point";
           }
           enum "ieee-802.1ad" {
             description "IEEE-802.1ad (DEI) code point";
           }
           enum "inet6-precedence" {
             description "IPv6 precedence code point";
           }
         }
       }
     }
     output {
       choice output_c {
         case output-tag {
           leaf output {
             type string;
           }
         }
         case actual-tag {
           anyxml cos-code-point-map-information;
         }
         case multichassis-tag {
           anyxml multi-routing-engine-results;
         }
       }
     }
   }
   rpc get-cos-scheduler-map-information {
     description "Show mapping of forwarding classes to schedulers";
     input {
       leaf scheduler-map-name {
         description "Name of scheduler map";
         type string;
       }
     }
     output {
       choice output_c {
         case output-tag {
           leaf output {
             type string;
           }
         }
         case actual-tag {
           anyxml cos-scheduler-map-information;
         }
         case multichassis-tag {
           anyxml multi-routing-engine-results;
         }
       }
     }
   }
   rpc get-cos-traffic-control-profile-information {
     description "Show traffic control profiles";
     input {
       leaf traffic-control-profile-name {
         description "Name of traffic control profile";
         type string;
       }
     }
     output {
       choice output_c {
         case output-tag {
           leaf output {
             type string;
           }
         }
         case actual-tag {
           anyxml cos-traffic-control-profile-information;
         }
         case multichassis-tag {
           anyxml multi-routing-engine-results;
         }
       }
     }
   }
   rpc get-cos-fragmentation-map-information {
     description "Show mapping of forwarding classes to fragmentation options";
     input {
       leaf fragmentation-map-name {
         description "Name of fragmentation map";
         type string;
       }
     }
     output {
       choice output_c {
         case output-tag {
           leaf output {
             type string;
           }
         }
         case actual-tag {
           anyxml cos-fragmentation-map-information;
         }
         case multichassis-tag {
           anyxml multi-routing-engine-results;
         }
       }
     }
   }
   rpc get-cos-interface-map-information {
     description "Show mapping of CoS objects to interfaces";
     input {
       leaf interface-name {
         description "Name of interface";
         type string;
       }
       leaf level {
         type enumeration {
           enum "comprehensive" {
             description "Show interface, filter, policer and CoS information comprehensively";
           }
           enum "detail" {
             description "Show interface information, filter, policer and CoS object names";
           }
         }
       }
     }
     output {
       choice output_c {
         case output-tag {
           leaf output {
             type string;
           }
         }
         case actual-tag {
           anyxml cos-interface-information;
         }
         case multichassis-tag {
           anyxml multi-routing-engine-results;
         }
       }
     }
   }
   rpc get-cos-routing-instance-map-information {
     description "Show mapping of CoS objects to routing instance";
     input {
       leaf routing-instance-name {
         description "Name of routing instance";
         type string;
       }
     }
     output {
       choice output_c {
         case output-tag {
           leaf output {
             type string;
           }
         }
         case actual-tag {
           anyxml cos-routing-instance-information;
         }
         case multichassis-tag {
           anyxml multi-routing-engine-results;
         }
       }
     }
   }
   rpc get-cos-table-information {
     description "Show forwarding table information";
     output {
       choice output_c {
         case output-tag {
           leaf output {
             type string;
           }
         }
         case actual-tag {
           anyxml cos-table-information;
         }
         case multichassis-tag {
           anyxml multi-routing-engine-results;
         }
       }
     }
   }
   rpc get-cos-classifier-table-information {
     description "Show classifier information";
     output {
       choice output_c {
         case output-tag {
           leaf output {
             type string;
           }
         }
         case actual-tag {
           anyxml cos-classifier-table-information;
         }
         case multichassis-tag {
           anyxml multi-routing-engine-results;
         }
       }
     }
   }
   rpc get-cos-classifier-table-map-information {
     description "Show mapping of interfaces to classifiers";
     output {
       choice output_c {
         case output-tag {
           leaf output {
             type string;
           }
         }
         case actual-tag {
           anyxml cos-classifier-table-map-information;
         }
         case multichassis-tag {
           anyxml multi-routing-engine-results;
         }
       }
     }
   }
   rpc get-cos-scheduler-map-table-information {
     description "Show scheduler map";
     output {
       choice output_c {
         case output-tag {
           leaf output {
             type string;
           }
         }
         case actual-tag {
           anyxml cos-scheduler-map-table-information;
         }
         case multichassis-tag {
           anyxml multi-routing-engine-results;
         }
       }
     }
   }
   rpc get-scheduler-map-table-map-information {
     description "Show mapping of scheduler-maps to interfaces";
     output {
       choice output_c {
         case output-tag {
           leaf output {
             type string;
           }
         }
         case actual-tag {
           anyxml cos-scheduler-map-table-information;
         }
         case multichassis-tag {
           anyxml multi-routing-engine-results;
         }
       }
     }
   }
   rpc get-cos-policer-table-map-information {
     description "Show policer";
     output {
       choice output_c {
         case output-tag {
           leaf output {
             type string;
           }
         }
         case actual-tag {
           anyxml cos-policer-table-map-information;
         }
         case multichassis-tag {
           anyxml multi-routing-engine-results;
         }
       }
     }
   }
   rpc get-cos-shaper-table-map-information {
     description "Show shaper";
     output {
       choice output_c {
         case output-tag {
           leaf output {
             type string;
           }
         }
         case actual-tag {
           anyxml cos-shaper-table-map-information;
         }
         case multichassis-tag {
           anyxml multi-routing-engine-results;
         }
       }
     }
   }
   rpc get-cos-red-information {
     description "Show random early detection drop profile";
     output {
       choice output_c {
         case output-tag {
           leaf output {
             type string;
           }
         }
         case actual-tag {
           anyxml cos-red-information;
         }
         case multichassis-tag {
           anyxml multi-routing-engine-results;
         }
       }
     }
   }
   rpc get-cos-rewrite-table-information {
     description "Show rewrite information";
     output {
       choice output_c {
         case output-tag {
           leaf output {
             type string;
           }
         }
         case actual-tag {
           anyxml cos-rewrite-table-information;
         }
         case multichassis-tag {
           anyxml multi-routing-engine-results;
         }
       }
     }
   }
   rpc get-cos-rewrite-table-map-information {
     description "Show interface to rewrite rule mapping";
     output {
       choice output_c {
         case output-tag {
           leaf output {
             type string;
           }
         }
         case actual-tag {
           anyxml cos-rewrite-table-map-information;
         }
         case multichassis-tag {
           anyxml multi-routing-engine-results;
         }
       }
     }
   }
   rpc get-cos-fwtab-fabric-scheduler-map-information {
     description "Show fabric scheduler map";
     output {
       choice output_c {
         case output-tag {
           leaf output {
             type string;
           }
         }
         case actual-tag {
           anyxml cos-fabric-scheduler-map-table-information;
         }
         case multichassis-tag {
           anyxml multi-routing-engine-results;
         }
       }
     }
   }
   rpc get-fabric-queue-information {
     description "Show fabric queue statistics";
     input {
       leaf destination {
         description "Destination FPC for which to show details";
         type union {
           type string {
             pattern "<.*>|$.*";
           }
           type int32;
         }
       }
       leaf source {
         description "Source FPC for which to show details";
         type union {
           type string {
             pattern "<.*>|$.*";
           }
           type int32;
         }
       }
       leaf summary {
         description "Display summary output";
         type empty;
       }
     }
     output {
       choice output_c {
         case output-tag {
           leaf output {
             type string;
           }
         }
         case actual-tag {
           anyxml fabric-queue-information;
         }
         case multichassis-tag {
           anyxml multi-routing-engine-results;
         }
       }
     }
   }
   rpc get-cos-fabric-scheduler-map-information {
     description "Show fabric scheduler map information";
     output {
       choice output_c {
         case output-tag {
           leaf output {
             type string;
           }
         }
         case actual-tag {
           anyxml cos-fabric-scheduler-map-information;
         }
         case multichassis-tag {
           anyxml multi-routing-engine-results;
         }
       }
     }
   }
   rpc get-cos-congestion-notification-information {
     description "Show congestion-notification information";
     input {
       leaf cnp-name {
         description "Name of congestion notification profile";
         type string;
       }
     }
     output {
       choice output_c {
         case output-tag {
           leaf output {
             type string;
           }
         }
         case actual-tag {
           anyxml cos-congestion-notification-information;
         }
         case multichassis-tag {
           anyxml multi-routing-engine-results;
         }
       }
     }
   }
   rpc get-host-outbound-traffic-information {
     description "Show host outbound traffic information";
     output {
       choice output_c {
         case output-tag {
           leaf output {
             type string;
           }
         }
         case actual-tag {
           anyxml cos-information;
         }
         case multichassis-tag {
           anyxml multi-routing-engine-results;
         }
       }
     }
   }
   rpc get-host-outbound-protocol-traffic-information {
     description "Show protocol specific host outbound traffic information";
     input {
       leaf protocol-name {
         description "Name of protocol";
         type enumeration {
           enum "isis-over-gre" {
             description "ISIS over GRE";
           }
           enum "default" {
             description "Default values";
           }
         }
         mandatory true;
       }
     }
     output {
       choice output_c {
         case output-tag {
           leaf output {
             type string;
           }
         }
         case actual-tag {
           anyxml cos-information;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
