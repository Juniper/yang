/*
 * Copyright (c) 2021 Juniper Networks, Inc.
 * All rights reserved.
 */
 module junos-es-rpc-file {
   namespace "http://yang.juniper.net/junos-es/rpc/file";

   prefix file;

   import junos-common-ddl-extensions {
     prefix junos;
     revision-date 2019-01-01;
   }

   import junos-common-odl-extensions {
     prefix junos-odl;
     revision-date 2019-01-01;
   }

   import junos-common-types {
     prefix jt;
     revision-date 2019-01-01;
   }

   organization "Juniper Networks, Inc.";

   contact "yang-support@juniper.net";

   description "Junos RPC YANG module for file command(s)";

   revision 2019-01-01 {
     description "Junos: 21.4R1.12";
   }

   rpc get-checksum-information {
     description "Calculate MD5 checksum of a file";
     input {
       leaf path {
         description "Path to filename";
         type string;
         mandatory true;
       }
       leaf method {
         type enumeration {
           enum "md5" {
             description "Calculate MD5 checksum of a file";
           }
           enum "sha1" {
             description "Calculate SHA1 checksum of a file";
           }
           enum "sha-256" {
             description "Calculate SHA-256 checksum of a file";
           }
         }
       }
     }
     output {
       choice output_c {
         case output-tag {
           leaf output {
             type string;
           }
         }
         case actual-tag {
           anyxml checksum-information;
         }
         case multichassis-tag {
           anyxml multi-routing-engine-results;
         }
       }
     }
   }
   rpc get-sha1-checksum-information {
     description "Calculate SHA1 checksum of a file";
     input {
       leaf path {
         description "Path to filename";
         type string;
         mandatory true;
       }
     }
     output {
       choice output_c {
         case output-tag {
           leaf output {
             type string;
           }
         }
         case actual-tag {
           anyxml checksum-information;
         }
         case multichassis-tag {
           anyxml multi-routing-engine-results;
         }
       }
     }
   }
   rpc get-sha256-checksum-information {
     description "Calculate SHA-256 checksum of a file";
     input {
       leaf path {
         description "Path to filename";
         type string;
         mandatory true;
       }
     }
     output {
       choice output_c {
         case output-tag {
           leaf output {
             type string;
           }
         }
         case actual-tag {
           anyxml checksum-information;
         }
         case multichassis-tag {
           anyxml multi-routing-engine-results;
         }
       }
     }
   }
   rpc file-list {
     description "List file information";
     input {
       leaf style {
         type enumeration {
           enum "detail" {
             description "Display detailed output (like 'ls -l')";
           }
           enum "recursive" {
             description "Descend recursively through directory hierarchy";
           }
         }
       }
       leaf path {
         description "Path to list";
         type string {
           junos:posix-pattern "! =;|()<>";
           junos:pattern-message "Should not conatin any special characters";
         }
       }
     }
     output {
       choice output_c {
         case output-tag {
           leaf output {
             type string;
           }
         }
         case actual-tag {
           anyxml directory-list;
         }
         case multichassis-tag {
           anyxml multi-routing-engine-results;
         }
       }
     }
   }
   rpc file-delete {
     description "Delete files from the system";
     input {
       leaf purge {
         description "Overwrite regular files before deleting them";
         type empty;
       }
       leaf path {
         description "Path to delete";
         type string;
         mandatory true;
       }
     }
     output {
       choice output_c {
         case output-tag {
           leaf output {
             type string;
           }
         }
         case multichassis-tag {
           anyxml multi-routing-engine-results;
         }
       }
     }
   }
   rpc file-show {
     description "Show file contents";
     input {
       leaf filename {
         description "Filename to show";
         type jt:filename;
         mandatory true;
       }
       leaf encoding {
         description "Encode file contents";
         type enumeration {
           enum "base64" {
             description "Encode file with base64 encoding";
           }
           enum "raw" {
             description "Show raw text from file";
           }
         }
       }
     }
     output {
       choice output_c {
         case output-tag {
           leaf output {
             type string;
           }
         }
         case actual-tag {
           anyxml file-content;
         }
         case multichassis-tag {
           anyxml multi-routing-engine-results;
         }
       }
     }
   }
   rpc file-compare {
     description "Compare files";
     input {
       leaf style {
         type enumeration {
           enum "context" {
             description "Context style output format";
           }
           enum "unified" {
             description "Unified style output format";
           }
         }
       }
       leaf ignore-white-space {
         description "Ignore changes in amount of white space";
         type empty;
       }
       leaf from-file {
         description "File to compare";
         type string;
       }
       leaf to-file {
         description "File to compare against";
         type string;
       }
     }
     output {
       choice output_c {
         case output-tag {
           leaf output {
             type string;
           }
         }
         case multichassis-tag {
           anyxml multi-routing-engine-results;
         }
       }
     }
   }
   rpc file-rename {
     description "Rename files";
     input {
       leaf source {
         description "Source URL";
         type string;
         mandatory true;
       }
       leaf destination {
         description "Destination URL";
         type string;
         mandatory true;
       }
     }
     output {
       choice output_c {
         case output-tag {
           leaf output {
             type string;
           }
         }
         case multichassis-tag {
           anyxml multi-routing-engine-results;
         }
       }
     }
   }
   rpc file-archive {
     description "Archives files from the system";
     input {
       leaf compress {
         description "Compresses the archived file using GNU gzip (.tgz)";
         type empty;
       }
       leaf destination {
         description "Name of created archive (URL, local, remote, or floppy)";
         type string;
         mandatory true;
       }
       leaf source {
         description "Path of directory to archive";
         type string;
         mandatory true;
       }
       leaf source-address {
         description "Local address to use in originating the connection";
         type string;
       }
       leaf routing-instance {
         description "Name of the routing-instance";
         type string;
       }
       leaf exclude {
         description "File pattern to exclude";
         type string;
       }
     }
     output {
       choice output_c {
         case output-tag {
           leaf output {
             type string;
           }
         }
         case multichassis-tag {
           anyxml multi-routing-engine-results;
         }
       }
     }
   }
   rpc extract-file {
     description "Extract a tar file";
     input {
       leaf source {
         description "Path of tar file to be extracted";
         type string;
         mandatory true;
       }
       leaf delete {
         description "Delete tar file after extracting it";
         type empty;
       }
       leaf destination {
         description "Path where files have to be extracted";
         type string;
       }
     }
     output {
       choice output_c {
         case output-tag {
           leaf output {
             type string;
           }
         }
         case multichassis-tag {
           anyxml multi-routing-engine-results;
         }
       }
     }
   }
   rpc file-change-permission {
     description "Change permission of file";
     input {
       leaf filename {
         description "Filename to change mode";
         type jt:filename;
         mandatory true;
       }
       leaf permission {
         description "File permission,either as symbolic(go+rw) or octal(642)";
         type string;
         mandatory true;
       }
     }
     output {
       choice output_c {
         case output-tag {
           leaf output {
             type string;
           }
         }
         case multichassis-tag {
           anyxml multi-routing-engine-results;
         }
       }
     }
   }
   rpc file-change-owner {
     description "Change owner of file";
     input {
       leaf filename {
         description "Filename to change owner";
         type jt:filename;
         mandatory true;
       }
       leaf user {
         description "New owner of the file";
         type string;
       }
       leaf group {
         description "New group of the file";
         type string;
       }
       leaf to {
         description "New owner:group of the file";
         type string;
       }
       leaf recurse {
         description "Operate recursively";
         type empty;
       }
     }
     output {
       choice output_c {
         case output-tag {
           leaf output {
             type string;
           }
         }
         case multichassis-tag {
           anyxml multi-routing-engine-results;
         }
       }
     }
   }
   rpc make-directory {
     description "Create a new directory";
     input {
       leaf directory {
         description "Path of the directory to be created";
         type string;
         mandatory true;
       }
       leaf with-path {
         description "Create parent directories if needed";
         type empty;
       }
     }
     output {
       choice output_c {
         case output-tag {
           leaf output {
             type string;
           }
         }
         case multichassis-tag {
           anyxml multi-routing-engine-results;
         }
       }
     }
   }
   rpc delete-directory {
     description "Delete a directory";
     input {
       leaf directory {
         description "Directory to be deleted";
         type string;
         mandatory true;
       }
       leaf recurse {
         description "Delete recursively";
         type empty;
       }
     }
     output {
       choice output_c {
         case output-tag {
           leaf output {
             type string;
           }
         }
         case multichassis-tag {
           anyxml multi-routing-engine-results;
         }
       }
     }
   }
   rpc file-link {
     description "Create link between files";
     input {
       leaf source {
         description "Source file name";
         type string;
         mandatory true;
       }
       leaf destination {
         description "Destination link name";
         type string;
         mandatory true;
       }
       leaf symbolic-link {
         description "Create a symbolic link";
         type empty;
       }
     }
     output {
       choice output_c {
         case output-tag {
           leaf output {
             type string;
           }
         }
         case multichassis-tag {
           anyxml multi-routing-engine-results;
         }
       }
     }
   }
   rpc file-compress {
     description "Compress file";
     input {
       leaf file {
         description "File to compress";
         type string;
         mandatory true;
       }
     }
     output {
       choice output_c {
         case output-tag {
           leaf output {
             type string;
           }
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
