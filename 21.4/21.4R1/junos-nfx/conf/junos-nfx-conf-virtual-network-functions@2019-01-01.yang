/*
 * Copyright (c) 2021 Juniper Networks, Inc.
 * All rights reserved.
 */
 module junos-nfx-conf-virtual-network-functions {
   namespace "http://yang.juniper.net/junos-nfx/conf/virtual-network-functions";

   prefix jc-virtual-network-functions;

   import junos-common-types {
     prefix jt;
     revision-date 2019-01-01;
   }

   import junos-nfx-conf-root {
     prefix jc;
     revision-date 2019-01-01;
   }

   organization "Juniper Networks, Inc.";

   contact "yang-support@juniper.net";

   description "Junos virtual-network-functions configuration module";

   revision 2019-01-01 {
     description "Junos: 21.4R1.12";
   }

   augment /jc:configuration {
     uses virtual-network-functions-group;
   }
   augment /jc:configuration/jc:groups {
     uses virtual-network-functions-group;
   }
   grouping virtual-network-functions-group {
     list virtual-network-functions {
       key name;
       ordered-by user;
       description "Virtual network functions configuration";
       leaf name {
         description "VNF name";
         type string;
       }
       uses apply-advanced;
       container type {
         description "VNF type";
         uses apply-advanced;
         leaf vnf_type {
           description "VNF type";
           type enumeration {
             enum "virtual-machine" {
               description "Virtual Machine";
             }
           }
         }
       }
       container image {
         description "Image file path";
         uses apply-advanced;
         leaf file-path {
           description "File path";
           type string {
             length "1 .. 256";
           }
         }
         leaf image-type {
           description "Image type";
           default "qcow2";
           type enumeration {
             enum "qcow2" {
               description "Qcow2 image format";
             }
             enum "raw" {
               description "Raw image format";
             }
           }
         }
         leaf bus-type {
           description "Bus type";
           default "virtio";
           type enumeration {
             enum "virtio" {
               description "Virtio";
             }
             enum "ide" {
               description "Ide";
             }
           }
         }
         leaf driver-cache {
           description "Driver cache mode";
           type enumeration {
             enum "none" {
               description "Cache type none";
             }
             enum "writethrough" {
               description "Cache type writethrough";
             }
             enum "writeback" {
               description "Cache type writeback";
             }
             enum "directsync" {
               description "Cache type directsync";
             }
             enum "unsafe" {
               description "Cache type unsafe";
             }
             enum "default-cache" {
               description "Cache type default";
             }
           }
         }
       }
       container init-descriptor {
         description "Initialization Descriptor file path";
         uses apply-advanced;
         leaf file-path {
           description "File path";
           type string {
             length "1 .. 256";
           }
         }
       }
       container uuid {
         description "VNF UUID";
         uses apply-advanced;
         leaf vnf_uuid {
           description "UUID string";
           type string {
           }
         }
       }
       container virtual-cpu {
         description "Virtual cpu configuration";
         uses apply-advanced;
         list vcpu-number {
           key name;
           uses vcpu_set;
         }
         leaf count {
           description "Number of virtual CPUs";
           type union {
             type uint32;
             type string {
               pattern "<.*>|$.*";
             }
           }
         }
         container features {
           description "Features";
           uses apply-advanced;
           leaf hardware-virtualization {
             description "Hardware Virtualization";
             type empty;
           }
         }
       }
       leaf no-default-interfaces {
         description "Do not autoprovision any interfaces to VNF";
         type empty;
       }
       list interfaces {
         key name;
         ordered-by user;
         description "Interfaces configuration";
         leaf name {
           description "Interface name";
           type string;
         }
         uses apply-advanced;
         container link {
           description "Vnf interface link disable";
           uses apply-advanced;
           choice enable-disable {
             case case_1 {
               leaf disable {
                 description "Disable the VNF interface";
                 type empty;
               }
             }
           }
         }
         leaf description {
           description "Text description of interface";
           type string;
         }
         leaf mac-address {
           description "Mac-address for the VNF interface";
           type jt:mac-addr;
         }
         leaf mtu {
           description "The Maximum Transfer Unit size in bytes";
           default "1500";
           type enumeration {
             enum "1500" {
               description "Set 1500 as mtu";
             }
             enum "2048" {
               description "Set 2048 as mtu";
             }
             enum "9216" {
               description "Set 9216 as mtu";
             }
           }
         }
         leaf pci-address {
           description "Target PCI address for the VNF interface";
           type string {
           }
         }
         leaf management {
           description "VNF interface management configuration";
           type enumeration {
             enum "internal" {
               description "Internal Management";
             }
             enum "out-of-band" {
               description "Out Of Band Management";
             }
           }
         }
         leaf analyzer {
           description "Analyzer interface";
           type empty;
         }
         container mapping {
           description "Attach to a physical interface or VLAN";
           uses apply-advanced;
           container interface {
             description "Attach to a physical interface";
             uses apply-advanced;
             leaf interface-name {
               description "Set heth-x-y or hsxe interface";
               type string {
               }
             }
             container virtual-function {
               presence "enable virtual-function";
               description "Attach using SR-IOV";
               uses apply-advanced;
               leaf vlan-id {
                 description "VLAN Id";
                 type union {
                   type string {
                     pattern "<.*>|$.*";
                   }
                   type uint32 {
                     range "1 .. 4094";
                   }
                 }
               }
               leaf trust {
                 description "Enable trust mode";
                 type empty;
               }
             }
           }
           container vlan {
             description "Attach VNF interface to VLAN";
             uses apply-advanced;
             leaf mode {
               description "Type of interface mode";
               default "access";
               type enumeration {
                 enum "access" {
                   description "Interface mode is access";
                 }
                 enum "trunk" {
                   description "Interface mode is trunk";
                 }
               }
             }
             leaf-list members {
               ordered-by user;
               description "Membership for this interface";
               type string;
             }
             leaf native-vlan-id {
               description "Virtual LAN identifier for untagged frames";
               type union {
                 type string {
                   pattern "<.*>|$.*";
                 }
                 type uint32 {
                   range "1 .. 4094";
                 }
               }
             }
           }
           leaf-list peer-interfaces {
             ordered-by user;
             description "Virtual peer interface(s) for this interface";
             type string;
           }
         }
         container forwarding-options {
           description "Forwarding-options on this interface";
           uses apply-advanced;
           leaf deny-forwarding {
             description "Deny forwarding traffic on this interface";
             type empty;
           }
         }
         container offloads {
           description "Offloads configuration for the VNF interface";
           uses apply-advanced;
           choice enable-disable {
             case case_1 {
               leaf disable {
                 description "Disable offloads for the VNF interface";
                 type empty;
               }
             }
           }
         }
       }
       container memory {
         description "Memory configuration";
         uses apply-advanced;
         leaf size {
           description "Size in kilobytes";
           type union {
             type uint32;
             type string {
               pattern "<.*>|$.*";
             }
           }
         }
         container features {
           description "Features";
           uses apply-advanced;
           container hugepages {
             presence "enable hugepages";
             description "Hugepages";
             uses apply-advanced;
             leaf page-size {
               description "Page size";
               default "1024";
               type enumeration {
                 enum "1024" {
                   description "Pagesize of 1GB";
                 }
                 enum "2" {
                   description "Pagesize of 2MB";
                 }
               }
             }
           }
         }
         list virtual-numa-node {
           key name;
           ordered-by user;
           description "Specify virtual numa node";
           leaf name {
             type union {
               type string {
                 pattern "<.*>|$.*";
               }
               type uint32 {
                 range "0 .. 1";
               }
             }
           }
           uses apply-advanced;
           leaf size {
             description "Size in kilobytes";
             type union {
               type uint32;
               type string {
                 pattern "<.*>|$.*";
               }
             }
           }
         }
       }
       list storage {
         key name;
         ordered-by user;
         description "Storage configuration";
         leaf name {
           description "Target device name";
           type string {
           }
         }
         uses apply-advanced;
         container type {
           description "Disk type";
           uses apply-advanced;
           choice types {
             case case_1 {
               container cdrom {
                 description "CDROM";
                 uses storage_attrib;
               }
             }
             case case_2 {
               container disk {
                 description "Harddisk";
                 uses storage_attrib_disk;
               }
             }
             case case_3 {
               container usb {
                 description "USB";
                 uses storage_attrib;
               }
             }
           }
         }
       }
       leaf no-autostart {
         description "Do not autostart VNF on commit";
         type empty;
       }
       container config-data {
         description "Pass config while spawning vnf";
         uses apply-advanced;
         container source {
           presence "enable source";
           uses apply-advanced;
           list file {
             key name;
             ordered-by user;
             description "Files to pass config data";
             leaf name {
               description "Path to the file";
               type jt:filename;
             }
             uses apply-advanced;
           }
           container directory {
             presence "enable directory";
             description "Directory to pass config data";
             uses apply-advanced;
             leaf directory-name {
               description "Enter the directory name";
               type jt:filename;
             }
           }
           container template {
             description "Template to pass config data";
             uses apply-advanced;
             list template_files {
               key name;
               uses templates;
             }
           }
         }
         container target {
           presence "enable target";
           uses apply-advanced;
           container device-name {
             presence "enable device-name";
             description "Target device name";
             uses apply-advanced;
             leaf target-device-name {
               description "Target device name";
               type string {
               }
             }
           }
           leaf device-type {
             description "Device type to be attached to vnf";
             type enumeration {
               enum "cdrom" {
                 description "Attach as cdrom";
               }
               enum "usb" {
                 description "Attach as disk";
               }
               enum "disk" {
                 description "Attach as disk";
               }
             }
           }
           leaf device-label {
             description "Label to be attached to iso";
             type string;
           }
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping macro-data-type {
     leaf name {
       description "Keyword part of the keyword-value pair";
       type string;
     }
     leaf value {
       description "Value part of the keyword-value pair";
       type string;
     }
   }
   grouping storage_attrib {
     description "Storage attributes";
     uses apply-advanced;
     container source {
       description "Source for disk";
       uses apply-advanced;
       leaf file {
         description "File name";
         type string {
           length "1 .. 256";
         }
       }
     }
   }
   grouping storage_attrib_disk {
     description "Storage attributes";
     uses apply-advanced;
     container source {
       description "Source for disk";
       uses apply-advanced;
       leaf file {
         description "File name";
         type string {
           length "1 .. 256";
         }
       }
     }
     leaf bus-type {
       description "Bus type";
       default "virtio";
       type enumeration {
         enum "virtio" {
           description "Virtio";
         }
         enum "ide" {
           description "Ide";
         }
       }
     }
     leaf file-type {
       description "File type";
       default "qcow2";
       type enumeration {
         enum "qcow2" {
           description "Qcow2";
         }
         enum "raw" {
           description "Raw";
         }
       }
     }
     leaf driver-cache {
       description "Driver cache types";
       default "default-cache";
       type enumeration {
         enum "none" {
           description "Cache type none";
         }
         enum "writethrough" {
           description "Cache type writethrough";
         }
         enum "writeback" {
           description "Cache type writeback";
         }
         enum "directsync" {
           description "Cache type directsync";
         }
         enum "unsafe" {
           description "Cache type unsafe";
         }
         enum "default-cache" {
           description "Cache type default";
         }
       }
     }
   }
   grouping templates {
     description "Templates";
     leaf name {
       description "Template name";
       type string;
     }
     uses apply-advanced;
     container file {
       presence "enable file";
       description "Path to template file";
       uses apply-advanced;
       leaf file-path {
         description "Path to template file";
         type jt:filename;
       }
     }
     list parameters {
       key name;
       ordered-by user;
       description "Pass parameters for the template";
       leaf name {
         description "Key of the parameter";
         type string;
       }
       uses apply-advanced;
       leaf data {
         description "Value of key";
         type string;
       }
     }
     container target {
       presence "enable target";
       description "Template name to be generated";
       uses apply-advanced;
       leaf target-filename {
         description "Target filename";
         type jt:filename;
       }
     }
   }
   grouping vcpu_set {
     description "VCPU number";
     leaf name {
       description "VCPU number";
       type union {
         type uint32;
         type string {
           pattern "<.*>|$.*";
         }
       }
     }
     uses apply-advanced;
     container virtual-numa-node {
       description "Specify virtual numa node";
       uses apply-advanced;
       leaf virtual-numa-node-name {
         description "Specify virtual numa node";
         type union {
           type string {
             pattern "<.*>|$.*";
           }
           type uint32 {
             range "0 .. 1";
           }
         }
       }
       leaf virtual-core {
         description "Specify the virtual core";
         type union {
           type string {
             pattern "<.*>|$.*";
           }
           type uint32 {
             range "0 .. 9";
           }
         }
       }
     }
     leaf-list physical-cpu {
       description "Physical CPUs";
       type string;
     }
   }
 }
