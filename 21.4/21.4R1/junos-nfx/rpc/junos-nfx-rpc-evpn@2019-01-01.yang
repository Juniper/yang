/*
 * Copyright (c) 2021 Juniper Networks, Inc.
 * All rights reserved.
 */
 module junos-nfx-rpc-evpn {
   namespace "http://yang.juniper.net/junos-nfx/rpc/evpn";

   prefix evpn;

   import junos-common-types {
     prefix jt;
     revision-date 2019-01-01;
   }

   organization "Juniper Networks, Inc.";

   contact "yang-support@juniper.net";

   description "Junos RPC YANG module for evpn command(s)";

   revision 2019-01-01 {
     description "Junos: 21.4R1.12";
   }

   rpc get-evpn-instance-information {
     description "Show EVPN instance information";
     input {
       choice daemon-select {
         case logical-system {
           leaf logical-system {
             description "Name of logical system, or 'all'";
             type string {
             }
           }
         }
       }
       leaf instance-name {
         description "Name of EVPN instance";
         default "all";
         type string;
       }
       leaf neighbor {
         description "Address of EVPN neighbor";
         type jt:ipaddr;
       }
       leaf esi {
         description "Ethernet segment identifier";
         type string;
       }
       leaf verbosity {
         type enumeration {
           enum "brief" {
             description "Display brief version of output";
           }
           enum "extensive" {
             description "Display extensive version of output";
           }
           enum "designated-forwarder" {
             description "Display only designated forwarder information";
           }
           enum "backup-forwarder" {
             description "Display only backup forwarder information";
           }
           enum "esi-info" {
             description "Display only ESI information";
           }
           enum "neighbor-info" {
             description "Display only neighbor information";
           }
           enum "bridge-domains" {
             description "Display detailed bridge-domain information";
           }
         }
       }
       leaf get-evpn-instance-dci-information {
         description "Display dci information";
         type empty;
       }
     }
     output {
       choice output_c {
         case output-tag {
           leaf output {
             type string;
           }
         }
         case actual-tag {
           anyxml evpn-instance-information;
         }
         case multichassis-tag {
           anyxml multi-routing-engine-results;
         }
       }
     }
   }
   rpc get-evpn-database-information {
     description "Show EVPN internal MAC database";
     input {
       choice daemon-select {
         case logical-system {
           leaf logical-system {
             description "Name of logical system, or 'all'";
             type string {
             }
           }
         }
       }
       leaf mac-address {
         description "Display a specifc MAC address";
         type jt:mac-addr;
       }
       leaf instance {
         description "Display MAC address from a specific EVPN instance";
         type string;
       }
       leaf l2-domain-id {
         description "Display MAC address with a specific VLAN or VNI or ISID";
         type union {
           type string {
             pattern "<.*>|$.*";
           }
           type int32 {
             range "1 .. 16777214";
           }
         }
       }
       leaf esi {
         description "Ethernet segment identifier";
         type string;
       }
       choice origin-choice {
         case neighbor {
           leaf neighbor {
             description "Display MAC address learned from a specific neighbor";
             type jt:ipaddr;
           }
         }
         case interface {
           leaf interface {
             description "Display MAC address learned from a specific interface";
             type string;
           }
         }
         case origin {
           leaf origin {
             description "Display MAC address with a specific origin";
             type enumeration {
               enum "local" {
                 description "Display local MAC address";
               }
               enum "remote" {
                 description "Display remote MAC address";
               }
               enum "dci-remote" {
                 description "Display MAC addresses received from DCI";
               }
             }
           }
         }
       }
       leaf state {
         description "Display MAC address with a specific state";
         type enumeration {
           enum "default-gateway" {
             description "Display default gateway MAC address";
           }
           enum "static" {
             description "Display static MAC address";
           }
           enum "pinned" {
             description "Display pinned MAC address";
           }
           enum "duplicate" {
             description "Display duplicate MAC address";
           }
           enum "dci-adv" {
             description "Display MAC advertised to DCI";
           }
           enum "dc-adv" {
             description "Display MAC advertised to DC";
           }
         }
       }
       leaf verbosity {
         type enumeration {
           enum "extensive" {
             description "Display extensive version of output";
           }
         }
       }
     }
     output {
       choice output_c {
         case output-tag {
           leaf output {
             type string;
           }
         }
         case actual-tag {
           anyxml evpn-database-information;
         }
         case multichassis-tag {
           anyxml multi-routing-engine-results;
         }
       }
     }
   }
   rpc get-evpn-p2mp-information {
     description "Show EVPN p2mp information";
     input {
       choice daemon-select {
         case logical-system {
           leaf logical-system {
             description "Name of logical system, or 'all'";
             type string {
             }
           }
         }
       }
       leaf instance {
         description "Display p2mp information for a specific EVPN instance";
         type string;
       }
       leaf verbosity {
         type enumeration {
           enum "extensive" {
             description "Display extensive version of output";
           }
         }
       }
     }
     output {
       choice output_c {
         case output-tag {
           leaf output {
             type string;
           }
         }
         case actual-tag {
           anyxml evpn-p2mp-information;
         }
         case multichassis-tag {
           anyxml multi-routing-engine-results;
         }
       }
     }
   }
   rpc get-evpn-l3-context-information {
     description "Show EVPN L3 context information";
     input {
       choice daemon-select {
         case logical-system {
           leaf logical-system {
             description "Name of logical system, or 'all'";
             type string {
             }
           }
         }
       }
       leaf l3-context-name {
         description "Name of EVPN L3 context";
         default "all";
         type string;
       }
       leaf verbosity {
         type enumeration {
           enum "brief" {
             description "Display brief version of output";
           }
           enum "extensive" {
             description "Display extensive version of output";
           }
         }
       }
     }
     output {
       choice output_c {
         case output-tag {
           leaf output {
             type string;
           }
         }
         case actual-tag {
           anyxml evpn-l3-context-information;
         }
         case multichassis-tag {
           anyxml multi-routing-engine-results;
         }
       }
     }
   }
   rpc get-evpn-ip-prefix-database-information {
     description "Show EVPN internal IP prefix database";
     input {
       choice daemon-select {
         case logical-system {
           leaf logical-system {
             description "Name of logical system, or 'all'";
             type string {
             }
           }
         }
       }
       leaf l3-context {
         description "Display IP prefix from a specific EVPN L3 context";
         type string;
       }
       leaf family {
         description "Display IP prefix with a specific address family";
         type enumeration {
           enum "inet" {
             description "Display IPv4 prefixes";
           }
           enum "inet6" {
             description "Display IPv6 prefixes";
           }
         }
       }
       leaf direction {
         description "Display IP prefix with a specific import/export direction";
         type enumeration {
           enum "imported" {
             description "Display imported EVPN IP prefixes";
           }
           enum "exported" {
             description "Display exported IP prefixes";
           }
         }
       }
       leaf prefix {
         description "Display a specifc IP prefix";
         type jt:ipprefix;
       }
       leaf ethernet-tag {
         description "Display IP prefix with a specific ethernet tag";
         type union {
           type string {
             pattern "<.*>|$.*";
           }
           type int32 {
             range "0 .. 16777214";
           }
         }
       }
       leaf gateway {
         description "Display IP prefix with a specific overlay gateway address";
         type jt:ipaddr;
       }
       leaf esi {
         description "Display IP prefix with a specific overlay ESI";
         type string;
       }
       leaf nexthop {
         description "Display IP prefix with a specific underlay nexthop";
         type jt:ipaddr;
       }
       leaf verbosity {
         type enumeration {
           enum "extensive" {
             description "Display extensive version of output";
           }
         }
       }
     }
     output {
       choice output_c {
         case output-tag {
           leaf output {
             type string;
           }
         }
         case actual-tag {
           anyxml evpn-ip-prefix-database-information;
         }
         case multichassis-tag {
           anyxml multi-routing-engine-results;
         }
       }
     }
   }
   rpc get-evpn-multicast-snooping-status {
     description "Show general status";
     input {
       leaf instance {
         description "Display for a specific EVPN instance";
         type string;
       }
       leaf l2-domain-id {
         description "Display for a specific VLAN or VNI or ISID";
         type union {
           type string {
             pattern "<.*>|$.*";
           }
           type int32 {
             range "1 .. 16777214";
           }
         }
       }
       leaf verbosity {
         type enumeration {
           enum "extensive" {
             description "Display extensive version of output";
           }
         }
       }
     }
     output {
       choice output_c {
         case output-tag {
           leaf output {
             type string;
           }
         }
         case actual-tag {
           anyxml evpn-multicast-snooping-status;
         }
         case multichassis-tag {
           anyxml multi-routing-engine-results;
         }
       }
     }
   }
   rpc get-evpn-multicast-snooping-ar-nexthops-data {
     description "Show next-hops information";
     input {
       leaf instance {
         description "Display for a specific EVPN instance";
         type string;
       }
       leaf l2-domain-id {
         description "Display for a specific VLAN or VNI or ISID";
         type union {
           type string {
             pattern "<.*>|$.*";
           }
           type int32 {
             range "1 .. 16777214";
           }
         }
       }
       leaf index {
         description "Display for a specific nexthop id";
         type union {
           type uint32;
           type string {
             pattern "<.*>|$.*";
           }
         }
       }
     }
     output {
       choice output_c {
         case output-tag {
           leaf output {
             type string;
           }
         }
         case actual-tag {
           anyxml evpn-multicast-snooping-ar-nexthops-data;
         }
         case multichassis-tag {
           anyxml multi-routing-engine-results;
         }
       }
     }
   }
   rpc get-evpn-multicast-snooping-ar-mh-peers-data {
     description "Show multi-homed peers";
     input {
       leaf instance {
         description "Display for a specific EVPN instance";
         type string;
       }
       leaf verbosity {
         type enumeration {
           enum "extensive" {
             description "Display extensive version of output";
           }
         }
       }
     }
     output {
       choice output_c {
         case output-tag {
           leaf output {
             type string;
           }
         }
         case actual-tag {
           anyxml evpn-multicast-snooping-ar-mh-peers-data;
         }
         case multichassis-tag {
           anyxml multi-routing-engine-results;
         }
       }
     }
   }
   rpc get-evpn-multicast-snooping-ar-replicators-data {
     description "Show replicators";
     input {
       leaf instance {
         description "Display for a specific EVPN instance";
         type string;
       }
       leaf l2-domain-id {
         description "Display for a specific VLAN or VNI or ISID";
         type union {
           type string {
             pattern "<.*>|$.*";
           }
           type int32 {
             range "1 .. 16777214";
           }
         }
       }
     }
     output {
       choice output_c {
         case output-tag {
           leaf output {
             type string;
           }
         }
         case actual-tag {
           anyxml evpn-multicast-snooping-ar-replicators-data;
         }
         case multichassis-tag {
           anyxml multi-routing-engine-results;
         }
       }
     }
   }
   rpc get-evpn-multicast-next-hops-information {
     description "Show EVPN multicast-snooping nexthops table";
     input {
       leaf verbosity_level {
         default "brief";
         type enumeration {
           enum "terse" {
             description "Display terse output";
           }
           enum "brief" {
             description "Display brief output (default)";
           }
           enum "detail" {
             description "Display detailed output";
           }
         }
       }
       leaf identifier {
         description "ID of next hop";
         type union {
           type uint32;
           type string {
             pattern "<.*>|$.*";
           }
         }
       }
     }
     output {
       choice output_c {
         case output-tag {
           leaf output {
             type string;
           }
         }
         case actual-tag {
           anyxml multicast-next-hops-information;
         }
         case multichassis-tag {
           anyxml multi-routing-engine-results;
         }
       }
     }
   }
   rpc get-evpn-igmp-snooping-proxy-information {
     description "Show EVPN igmp snooping proxy";
     input {
       choice daemon-select {
         case logical-system {
           leaf logical-system {
             description "Name of logical system, or 'all'";
             type string {
             }
           }
         }
       }
       leaf instance {
         description "Display for a specific EVPN instance";
         type string;
       }
       leaf l2-domain-id {
         description "Display for a specific VLAN or VNI or ISID";
         type union {
           type string {
             pattern "<.*>|$.*";
           }
           type int32 {
             range "1 .. 16777214";
           }
         }
       }
       leaf group {
         description "Group address";
         type jt:ipaddr;
       }
       leaf verbosity {
         type enumeration {
           enum "extensive" {
             description "Display extensive version of output";
           }
         }
       }
     }
     output {
       choice output_c {
         case output-tag {
           leaf output {
             type string;
           }
         }
         case actual-tag {
           anyxml evpn-igmp-snooping-information;
         }
         case multichassis-tag {
           anyxml multi-routing-engine-results;
         }
       }
     }
   }
   rpc get-evpn-igmp-snooping-database-information {
     description "Show EVPN igmp snooping database";
     input {
       choice daemon-select {
         case logical-system {
           leaf logical-system {
             description "Name of logical system, or 'all'";
             type string {
             }
           }
         }
       }
       leaf instance {
         description "Display for a specific EVPN instance";
         type string;
       }
       leaf l2-domain-id {
         description "Display for a specific VLAN or VNI or ISID";
         type union {
           type string {
             pattern "<.*>|$.*";
           }
           type int32 {
             range "1 .. 16777214";
           }
         }
       }
       leaf esi {
         description "Ethernet segment identifier";
         type string;
       }
       leaf group {
         description "Group address";
         type jt:ipaddr;
       }
       leaf interface {
         description "Display for a specific interface";
         type string;
       }
       leaf verbosity {
         type enumeration {
           enum "extensive" {
             description "Display extensive version of output";
           }
         }
       }
     }
     output {
       choice output_c {
         case output-tag {
           leaf output {
             type string;
           }
         }
         case actual-tag {
           anyxml evpn-igmp-snooping-information;
         }
         case multichassis-tag {
           anyxml multi-routing-engine-results;
         }
       }
     }
   }
   rpc get-evpn-mld-snooping-proxy-information {
     description "Show EVPN mld snooping proxy";
     input {
       leaf instance {
         description "Display for a specific EVPN instance";
         type string;
       }
       leaf l2-domain-id {
         description "Display for a specific VLAN or VNI or ISID";
         type union {
           type string {
             pattern "<.*>|$.*";
           }
           type int32 {
             range "1 .. 16777214";
           }
         }
       }
       leaf group {
         description "Group address";
         type jt:ipaddr;
       }
       leaf verbosity {
         type enumeration {
           enum "extensive" {
             description "Display extensive version of output";
           }
         }
       }
     }
     output {
       choice output_c {
         case output-tag {
           leaf output {
             type string;
           }
         }
         case actual-tag {
           anyxml evpn-mld-snooping-information;
         }
         case multichassis-tag {
           anyxml multi-routing-engine-results;
         }
       }
     }
   }
   rpc get-evpn-mld-snooping-database-information {
     description "Show EVPN mld snooping database";
     input {
       leaf instance {
         description "Display for a specific EVPN instance";
         type string;
       }
       leaf l2-domain-id {
         description "Display for a specific VLAN or VNI or ISID";
         type union {
           type string {
             pattern "<.*>|$.*";
           }
           type int32 {
             range "1 .. 16777214";
           }
         }
       }
       leaf esi {
         description "Ethernet segment identifier";
         type string;
       }
       leaf group {
         description "Group address";
         type jt:ipaddr;
       }
       leaf interface {
         description "Display for a specific interface";
         type string;
       }
       leaf verbosity {
         type enumeration {
           enum "extensive" {
             description "Display extensive version of output";
           }
         }
       }
     }
     output {
       choice output_c {
         case output-tag {
           leaf output {
             type string;
           }
         }
         case actual-tag {
           anyxml evpn-mld-snooping-information;
         }
         case multichassis-tag {
           anyxml multi-routing-engine-results;
         }
       }
     }
   }
   rpc get-evpn-oism-information {
     description "Show EVPN OISM information";
     input {
       choice daemon-select {
         case logical-system {
           leaf logical-system {
             description "Name of logical system, or 'all'";
             type string {
             }
           }
         }
       }
       leaf l3-context {
         description "Name of specific EVPN L3 context";
         type string;
       }
       leaf verbosity {
         type enumeration {
           enum "brief" {
             description "Display brief version of output";
           }
           enum "extensive" {
             description "Display extensive version of output";
           }
         }
       }
     }
     output {
       choice output_c {
         case output-tag {
           leaf output {
             type string;
           }
         }
         case actual-tag {
           anyxml evpn-oism-information;
         }
         case multichassis-tag {
           anyxml multi-routing-engine-results;
         }
       }
     }
   }
   rpc get-evpn-vpws-information {
     description "Show EVPN VPWS instance information";
     input {
       choice daemon-select {
         case logical-system {
           leaf logical-system {
             description "Name of logical system, or 'all'";
             type string {
             }
           }
         }
       }
       leaf instance-name {
         description "Name of EVPN VPWS instance";
         default "all";
         type string;
       }
     }
     output {
       choice output_c {
         case output-tag {
           leaf output {
             type string;
           }
         }
         case actual-tag {
           anyxml evpn-vpws-information;
         }
         case multichassis-tag {
           anyxml multi-routing-engine-results;
         }
       }
     }
   }
   rpc get-evpn-mac-ip-table {
     description "Show IP table for EVPN instances";
     input {
       leaf logical-system {
         description "Name of logical system, or 'all'";
         default "all";
         type string {
         }
       }
       leaf instance {
         description "Display information for a specified instance";
         default "all";
         type string;
       }
       leaf address {
         description "MAC address";
         default "all";
         type jt:mac-addr;
       }
       leaf show-choice {
         default "brief";
         type enumeration {
           enum "detail" {
             description "Display detailed output";
           }
           enum "brief" {
             description "Display brief output";
           }
           enum "extensive" {
             description "Display extensive output";
           }
           enum "count" {
             description "Display count only";
           }
         }
       }
     }
     output {
       choice output_c {
         case output-tag {
           leaf output {
             type string;
           }
         }
         case actual-tag {
           anyxml l2ald-rtb-mac-ip-db;
         }
         case multichassis-tag {
           anyxml multi-routing-engine-results;
         }
       }
     }
   }
   rpc get-evpn-mac-ip-table-kernel {
     description "Entries present in kernel";
     input {
       leaf verbosity {
         default "brief";
         type enumeration {
           enum "detail" {
             description "Display detailed output";
           }
           enum "brief" {
             description "Display brief output";
           }
           enum "extensive" {
             description "Display extensive output";
           }
         }
       }
     }
     output {
       choice output_c {
         case output-tag {
           leaf output {
             type string;
           }
         }
         case actual-tag {
           anyxml l2ald-rtb-mac-ip-kernel-db;
         }
         case multichassis-tag {
           anyxml multi-routing-engine-results;
         }
       }
     }
   }
   rpc get-evpn-mac-ip-table-kernel-ipv4 {
     description "IPv4 entries present in kernel";
     input {
       leaf bd-id {
         description "Display IP address under particular bd-id";
         type string;
       }
       leaf ipv4-addr {
         description "Display kernel information for ip";
         default "all";
         type jt:ipv4addr;
       }
       leaf verbosity {
         default "brief";
         type enumeration {
           enum "detail" {
             description "Display detailed output";
           }
           enum "brief" {
             description "Display brief output";
           }
           enum "extensive" {
             description "Display extensive output";
           }
         }
       }
     }
     output {
       choice output_c {
         case output-tag {
           leaf output {
             type string;
           }
         }
         case actual-tag {
           anyxml l2ald-rtb-mac-ip-kernel-db;
         }
         case multichassis-tag {
           anyxml multi-routing-engine-results;
         }
       }
     }
   }
   rpc get-evpn-mac-ip-table-kernel-ipv6 {
     description "IPv6 entries present in kernel";
     input {
       leaf bd-id {
         description "Display IP address under particular bd-id";
         type string;
       }
       leaf ipv6-addr {
         description "Display kernel information for ip";
         default "all";
         type jt:ipv6addr;
       }
       leaf verbosity {
         default "brief";
         type enumeration {
           enum "detail" {
             description "Display detailed output";
           }
           enum "brief" {
             description "Display brief output";
           }
           enum "extensive" {
             description "Display extensive output";
           }
         }
       }
     }
     output {
       choice output_c {
         case output-tag {
           leaf output {
             type string;
           }
         }
         case actual-tag {
           anyxml l2ald-rtb-mac-ip-kernel-db;
         }
         case multichassis-tag {
           anyxml multi-routing-engine-results;
         }
       }
     }
   }
   rpc get-evpn-mac-table {
     description "Show media access control table";
     input {
       leaf instance {
         description "Display information for a specified vpls";
         default "all";
         type string;
       }
       leaf logical-system {
         description "Name of logical system, or 'all'";
         default "all";
         type string {
         }
       }
       leaf vlan-id {
         description "Display MAC address learned on a specified VLAN";
         type string;
       }
       leaf isid {
         description "Display Information for specified ISID or all ISID(s)";
         type string;
       }
       leaf address {
         description "MAC address";
         default "all";
         type jt:mac-addr;
       }
       leaf show-choice {
         default "brief";
         type enumeration {
           enum "detail" {
             description "Display detailed output";
           }
           enum "brief" {
             description "Display brief output";
           }
           enum "extensive" {
             description "Display extensive output";
           }
           enum "count" {
             description "Display count only";
           }
           enum "age" {
             description "Display age of a single mac-address";
           }
           enum "summary" {
             description "Display summary output";
           }
         }
       }
     }
     output {
       choice output_c {
         case output-tag {
           leaf output {
             type string;
           }
         }
         case actual-tag {
           anyxml l2ald-rtb-macdb;
         }
         case multichassis-tag {
           anyxml multi-routing-engine-results;
         }
       }
     }
   }
   rpc get-evpn-interface-mac-table {
     description "Display MAC table for a specified interface";
     input {
       choice interface-choice {
         case interface-name {
           leaf interface-name {
             description "Name of interface for which to display table";
             type string;
           }
         }
         case all {
           leaf all {
             description "Display MAC table for all the interfaces";
             type empty;
           }
         }
       }
       leaf show-choice {
         default "brief";
         type enumeration {
           enum "detail" {
             description "Display detailed output";
           }
           enum "brief" {
             description "Display brief output";
           }
           enum "extensive" {
             description "Display extensive output";
           }
           enum "count" {
             description "Display count only";
           }
           enum "age" {
             description "Display age of a single mac-address";
           }
           enum "summary" {
             description "Display summary output";
           }
         }
       }
     }
     output {
       choice output_c {
         case output-tag {
           leaf output {
             type string;
           }
         }
         case actual-tag {
           anyxml l2ald-interface-macdb;
         }
         case multichassis-tag {
           anyxml multi-routing-engine-results;
         }
       }
     }
   }
   rpc get-evpn-flood-information {
     description "Show EVPN flooding information";
     input {
       leaf logical-system {
         description "Name of logical system, or 'all'";
         default "all";
         type string {
         }
       }
       leaf instance {
         description "Display information for a specified vpls";
         default "all";
         type string;
       }
       leaf verbosity {
         default "detail";
         type enumeration {
           enum "detail" {
             description "Display detailed output";
           }
           enum "brief" {
             description "Display brief output";
           }
           enum "extensive" {
             description "Display extensive output";
           }
         }
       }
     }
     output {
       choice output_c {
         case output-tag {
           leaf output {
             type string;
           }
         }
         case actual-tag {
           anyxml l2ald-vpls-flood-instance;
         }
         case multichassis-tag {
           anyxml multi-routing-engine-results;
         }
       }
     }
   }
   rpc get-evpn-ce-flood-route-information {
     description "Show customer edge flood route";
     input {
       leaf interface {
         description "Interface for which to show CE flood route";
         type union {
           type jt:interface-unit;
           type string {
             pattern "<.*>|$.*";
           }
         }
         mandatory true;
       }
     }
     output {
       choice output_c {
         case output-tag {
           leaf output {
             type string;
           }
         }
         case actual-tag {
           anyxml l2ald-vpls-flood-route-information;
         }
         case multichassis-tag {
           anyxml multi-routing-engine-results;
         }
       }
     }
   }
   rpc get-evpn-all-flood-route-information {
     description "Show route for flooding traffic from customer edge router";
     input {
       leaf logical-system {
         description "Name of logical system";
         type string {
         }
       }
       leaf instance {
         description "Display information for a specified vpls";
         type string;
         mandatory true;
       }
     }
     output {
       choice output_c {
         case output-tag {
           leaf output {
             type string;
           }
         }
         case actual-tag {
           anyxml l2ald-vpls-flood-route-information;
         }
         case multichassis-tag {
           anyxml multi-routing-engine-results;
         }
       }
     }
   }
   rpc get-evpn-all-ce-flood-route-information {
     description "Show route for flooding traffic to all CE routers";
     input {
       leaf logical-system {
         description "Name of logical system";
         type string {
         }
       }
       leaf instance {
         description "Display information for a specified vpls";
         type string;
         mandatory true;
       }
     }
     output {
       choice output_c {
         case output-tag {
           leaf output {
             type string;
           }
         }
         case actual-tag {
           anyxml l2ald-vpls-flood-route-information;
         }
         case multichassis-tag {
           anyxml multi-routing-engine-results;
         }
       }
     }
   }
   rpc get-evpn-re-flood-route-information {
     description "Show route for Routing Engine flooding to all interfaces";
     input {
       leaf logical-system {
         description "Name of logical system";
         type string {
         }
       }
       leaf instance {
         description "Display information for a specified vpls";
         type string;
         mandatory true;
       }
     }
     output {
       choice output_c {
         case output-tag {
           leaf output {
             type string;
           }
         }
         case actual-tag {
           anyxml l2ald-vpls-flood-route-information;
         }
         case multichassis-tag {
           anyxml multi-routing-engine-results;
         }
       }
     }
   }
   rpc get-evpn-mlp-flood-route-information {
     description "Show route for flooding traffic to MAC learning chips";
     input {
       leaf logical-system {
         description "Name of logical system";
         type string {
         }
       }
       leaf instance {
         description "Display information for a specified vpls";
         type string;
         mandatory true;
       }
     }
     output {
       choice output_c {
         case output-tag {
           leaf output {
             type string;
           }
         }
         case actual-tag {
           anyxml l2ald-vpls-flood-route-information;
         }
         case multichassis-tag {
           anyxml multi-routing-engine-results;
         }
       }
     }
   }
   rpc get-evpn-alt-root-flood-route-information {
     description "Show STP alt-root flooding route used for interface";
     input {
       leaf interface {
         description "Interface for which to show alternate-root flooding route";
         type union {
           type jt:interface-unit;
           type string {
             pattern "<.*>|$.*";
           }
         }
         mandatory true;
       }
     }
     output {
       choice output_c {
         case output-tag {
           leaf output {
             type string;
           }
         }
         case actual-tag {
           anyxml l2ald-vpls-flood-route-information;
         }
         case multichassis-tag {
           anyxml multi-routing-engine-results;
         }
       }
     }
   }
   rpc get-evpn-event-queue-information {
     description "Show queue of pending EVPN flood events";
     output {
       choice output_c {
         case output-tag {
           leaf output {
             type string;
           }
         }
         case actual-tag {
           anyxml l2ald-vpls-flood-event-queue;
         }
         case multichassis-tag {
           anyxml multi-routing-engine-results;
         }
       }
     }
   }
   rpc get-evpn-arp-table {
     description "Show ARP entries associated with MACs learned";
     input {
       leaf logical-system {
         description "Name of logical system, or 'all'";
         default "all";
         type string {
         }
       }
       leaf instance {
         description "Display information for a specified vpls";
         default "all";
         type string;
       }
       leaf address {
         description "MAC address";
         default "all";
         type jt:mac-addr;
       }
       leaf show-choice {
         default "brief";
         type enumeration {
           enum "detail" {
             description "Display detailed output";
           }
           enum "brief" {
             description "Display brief output";
           }
           enum "extensive" {
             description "Display extensive output";
           }
           enum "count" {
             description "Display count only";
           }
         }
       }
     }
     output {
       choice output_c {
         case output-tag {
           leaf output {
             type string;
           }
         }
         case actual-tag {
           anyxml l2rtb-evpn-arp-db;
         }
         case multichassis-tag {
           anyxml multi-routing-engine-results;
         }
       }
     }
   }
   rpc get-evpn-nd-table {
     description "Show ND entries associated with MACs learned";
     input {
       leaf logical-system {
         description "Name of logical system, or 'all'";
         default "all";
         type string {
         }
       }
       leaf instance {
         description "Display information for a specified vpls";
         default "all";
         type string;
       }
       leaf address {
         description "MAC address";
         default "all";
         type jt:mac-addr;
       }
       leaf show-choice {
         default "brief";
         type enumeration {
           enum "detail" {
             description "Display detailed output";
           }
           enum "brief" {
             description "Display brief output";
           }
           enum "extensive" {
             description "Display extensive output";
           }
           enum "count" {
             description "Display count only";
           }
         }
       }
     }
     output {
       choice output_c {
         case output-tag {
           leaf output {
             type string;
           }
         }
         case actual-tag {
           anyxml l2rtb-evpn-nd-db;
         }
         case multichassis-tag {
           anyxml multi-routing-engine-results;
         }
       }
     }
   }
   rpc get-evpn-peer-gateway-mac {
     description "Show MAC addresses installed as gateway MACs";
     input {
       leaf instance {
         description "Display information for a specified instance";
         default "all";
         type string;
       }
       leaf address {
         description "MAC address";
         default "all";
         type jt:mac-addr;
       }
     }
     output {
       choice output_c {
         case output-tag {
           leaf output {
             type string;
           }
         }
         case actual-tag {
           anyxml l2rtb-peer-gateway-macdb;
         }
         case multichassis-tag {
           anyxml multi-routing-engine-results;
         }
       }
     }
   }
   rpc get-evpn-statistics-information {
     description "Show EVPN statistics";
     input {
       leaf instance {
         description "Name of EVPN instance";
         type string;
         mandatory true;
       }
     }
     output {
       choice output_c {
         case output-tag {
           leaf output {
             type string;
           }
         }
         case actual-tag {
           anyxml evpn-statistics-information;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
